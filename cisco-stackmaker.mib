-- $Id: CISCO-STACKMAKER.MIB 1.1 2005/03/14 16:31:00Z aminchew Exp $
-- $Source: v:/mksroot/rcs/CISCO-STACKMAKER.MIB $
-- *****************************************************************
-- MIBS/CISCO-STACKMAKER-MIB.my:  StackMaker MIB
--
-- December 1996, Wenyu Lin
--
-- Copyright (c) 1996-1997 by cisco Systems, Inc.
-- All rights reserved.
-- *****************************************************************
-- $Log: CISCO-STACKMAKER.MIB $
-- Revision 1.1  2005/03/14 16:31:00Z  aminchew
-- Initial revision
-- Revision 1.1.2.1  2005/02/08 01:45:10  bruceg
-- CGESM_12_2_25
--
-- *****************************************************************
-- $Endlog$
--

CISCO-STACKMAKER-MIB DEFINITIONS ::= BEGIN
 
IMPORTS
     ciscoMgmt
	FROM CISCO-SMI
     MODULE-IDENTITY, OBJECT-TYPE, IpAddress
 	FROM SNMPv2-SMI
     DisplayString
 	FROM SNMPv2-TC
     MODULE-COMPLIANCE, OBJECT-GROUP
 	FROM SNMPv2-CONF;
 
 
ciscoStackMakerMIB MODULE-IDENTITY
 	LAST-UPDATED "9610311200Z"
 	ORGANIZATION "Cisco Systems, Inc."
 	CONTACT-INFO
 	    "Postal: Cisco Systems, Inc.
 	     170 West Tasman Drive
 	     San Jose, CA 95134-1706
 	     USA
 
 	     Tel: +1 408 526 4000
 
 	     E-mail: cs-stacks@cisco.com"
 	DESCRIPTION
 	    "The MIB module for Cisco Systems' StackMaker."
 	::= { ciscoMgmt 59 }
 
 
ciscoStackMakerMIBObjects   
 	OBJECT IDENTIFIER ::= { ciscoStackMakerMIB 1 }
ciscoStackMakerConf
 	OBJECT IDENTIFIER ::= { ciscoStackMakerMIBObjects 1 }
 
csmStackName            OBJECT-TYPE
 	SYNTAX          DisplayString (SIZE (0..32))
 	MAX-ACCESS      read-write
 	STATUS          current
 	DESCRIPTION
 		" A descriptive string used by the network administrator
 		one stack at any given time. If this entry is empty,
 		the device is not a member of a stack.
 
 		Changing the value of this object will move the device
 		to a different stack. If the value is cleared, the device
 		is no longer a member of any stack."
 	::= { ciscoStackMakerConf 1 }
 
csmClearStackTable      OBJECT-TYPE
 	SYNTAX          INTEGER {
 				clearTable(1),
 				noClearTable(2)
 			}
 	MAX-ACCESS      read-write
 	STATUS          current
 	DESCRIPTION
 		"This object is used to clear the csmStackTable
 		with a single SNMP operation. The application will clear
 		the table and re-write the table to accommodate new
 		or modified table entries.
 		Setting this object to noClearTable has no effect.
 		The agent will always return the value of noClearTable
 		when this object is read."
 	::= { ciscoStackMakerConf 2 }
 
csmStackTable           OBJECT-TYPE
 	SYNTAX          SEQUENCE OF CsmStackEntry
 	MAX-ACCESS      not-accessible
 	STATUS          current
 	DESCRIPTION
 		"The table of IP addresses for the devices which are
 		members of the stack. Individual entries can be added
 		to the table to add devices in the stack either through
 		SNMP Set operations or through the device's command line
 		interface. However, the agent need not support deletion
 		of individual entries, since the table is first cleared
 		before any modifications are made, using the
 		csmClearStackTable object. The agent will return
 		the error badValue if an SNMP Set operation is
 		attempted on an existing row.
 		
 		It is the responsibility of the network administrator to
 		ensure that a device does not belong to more than one stack
 		and to maintain referential integrity across devices. A
 		device will take no action upon the information stored in
 		this table other than to guarantee its persistence over
 		device reboots."
 	::= { ciscoStackMakerConf 3 }
 
csmStackEntry           OBJECT-TYPE
 	SYNTAX          CsmStackEntry
 	MAX-ACCESS      not-accessible
 	STATUS          current
 	DESCRIPTION
 		"An entry for each device which is member of the stack."
 	INDEX   { csmStackIndex }
 	::= { csmStackTable 1 }
 
CsmStackEntry   ::= SEQUENCE {
 	csmStackIndex           INTEGER,
 	csmStackIpAddress        IpAddress
 }
 
csmStackIndex           OBJECT-TYPE 
 	SYNTAX          INTEGER (1..32)
 	MAX-ACCESS      not-accessible
 	STATUS          current
 	DESCRIPTION
 		"Index in the StackMaker table. Entries should be
 		consecutive since updating this table is made by
 		first clearing the table and reconfiguring it."
 	::= { csmStackEntry 1 }
 
csmStackIpAddress       OBJECT-TYPE
 	SYNTAX          IpAddress
 	MAX-ACCESS      read-create
 	STATUS          current
-- 	STATUS          mandatory
 	DESCRIPTION
 		"IP Address of a stack member."
 	::= { csmStackEntry 2 }
 
 
 -- conformance information
 
ciscoStackMakerMIBConformance
 	OBJECT IDENTIFIER ::= { ciscoStackMakerMIB 3 }
 
ciscoStackMakerMIBCompliances
 	OBJECT IDENTIFIER ::= { ciscoStackMakerMIBConformance 1 }
 
ciscoStackMakerMIBGroups
 	OBJECT IDENTIFIER ::= { ciscoStackMakerMIBConformance 2 }
 
 
 -- compliance statements
 
ciscoStackMakerMIBCompliance MODULE-COMPLIANCE
 	STATUS  current
 	DESCRIPTION
 	    "The compliance statement for Cisco Systems entities which
 	    implement the StackMaker model. Every Cisco stackable
 	    device must implement the StackMaker MIB."
 	MODULE  -- this module
 	MANDATORY-GROUPS { ciscoStackMakerBasicGroup }
 	::= { ciscoStackMakerMIBCompliances 1 }
 
 
 -- units of conformance
 
ciscoStackMakerBasicGroup OBJECT-GROUP
 	OBJECTS { csmStackName,
 	      csmClearStackTable,
 	      csmStackIpAddress }
 	STATUS  current
 	DESCRIPTION
 	    "A collection of objects providing identification for
 	    a Cisco Systems' entity which implements the
 	    StackMaker MIB."
 	::= { ciscoStackMakerMIBGroups 1 }
 
END
