-- ***************************************************************************
-- 	
-- Name: Web Configuration Management MIB
--  
-- This MIB is meant to be generic enough to fit the web configuration of 
-- any wireless LAN family product.
--  
-- WEB Configuration Mangement MIB is for 3Com Wireless LAN products.
-- This MIB contains management objects for WEB configuration. 
-- It will be useful to third parties.
--	
-- Also, the users can configure those managed objects thourgh the web.
--
-- History
-- Date         Who         Reason for Change
-- 09/06/2001   Yuli      	Initial Draft 
--  
-- ***************************************************************************
--      Copyright 3Com Technologies Limited. ( 2001 )

SRAP-WCM-MIB DEFINITIONS ::= BEGIN

IMPORTS
	MODULE-IDENTITY, OBJECT-TYPE, NOTIFICATION-TYPE, IpAddress, Counter32, Integer32, Gauge32 
		FROM SNMPv2-SMI
	OBJECT-GROUP, NOTIFICATION-GROUP
		FROM SNMPv2-CONF
    MacAddress
        FROM SNMPv2-TC
	ifIndex                                 
		FROM RFC1213-MIB
	a3Com
		FROM A3Com-products-MIB
	srAPWCM, srAPModules
		FROM SRAP-GLOBAL-REG;

srAPWCMMIBModule MODULE-IDENTITY
	LAST-UPDATED	"9905260000Z"
	ORGANIZATION	"3Com"
	CONTACT-INFO	"
		 Name: 		Yuli Hou
		 Mail Stop: 4240
		 Address:	5400 Bayfront Plaza
		 Zip:		CA 95052
		 City:		Santa Clara, 
		 Country:	USA
		 Phone:		+001-408-326-1191
		 Fax:		+001-408-326-6555
		 e-mail:	Yuli_Hou@3com.com"
	DESCRIPTION
		"The 3COM Wireless LAN Products Web Configuration Management MIB Module."
	::= { srAPModules 5 }

-- the group containing general SNMP objects
wcmMIB		OBJECT IDENTIFIER ::= { srAPWCM 1 }

-- conformance and compliance specifications
wcmConf  				OBJECT IDENTIFIER ::= { wcmMIB 1 }
apConfigMgmtGroups 		OBJECT IDENTIFIER ::= { wcmConf 1 }
apPerformMgmtGroups		OBJECT IDENTIFIER ::= { wcmConf 2 }
apFaultMgmtGroups    	OBJECT IDENTIFIER ::= { wcmConf 3 }
apSecurityMgmtGroups  	OBJECT IDENTIFIER ::= { wcmConf 4 }
apEventGroups  			OBJECT IDENTIFIER ::= { wcmConf 5 }

-- the tree for managed objects
wcmObjs OBJECT IDENTIFIER ::= { wcmMIB 2 }
-- the subtree for config managed objects
apConfigMgmt    	OBJECT IDENTIFIER ::= { wcmObjs 1 }
apManufactureInfo      OBJECT IDENTIFIER ::= { apConfigMgmt 1 }
apSystemConfig         OBJECT IDENTIFIER ::= { apConfigMgmt 2 }
apSNMPInfo             OBJECT IDENTIFIER ::= { apConfigMgmt 3 }
apRFConfig             OBJECT IDENTIFIER ::= { apConfigMgmt 4 }
-- the subtree for perform managed objects
apPerformMgmt   	OBJECT IDENTIFIER ::= { wcmObjs 2 }
--apEthernetStatistics   OBJECT IDENTIFIER ::= { apPerformMgmt 1 }
apRFStatistics         OBJECT IDENTIFIER ::= { apPerformMgmt 1 }    
apEtherItfStat		       OBJECT IDENTIFIER ::= { apPerformMgmt 2 } 
apRFItfStat		       OBJECT IDENTIFIER ::= { apPerformMgmt 3 }  
apTrafficMatrix		   OBJECT IDENTIFIER ::= { apPerformMgmt 4 }   
 



-- the subtree for Fault managed objects
apFaultMgmt     OBJECT IDENTIFIER ::= { wcmObjs 3 }
-- the subtree for Security managed objects
apSecurityMgmt  OBJECT IDENTIFIER ::= { wcmObjs 4 }

-- subtree for events and notifications
wcmEvents	 	OBJECT IDENTIFIER ::= { wcmMIB 3 }
wcmEventsV2 	OBJECT IDENTIFIER ::= { wcmEvents 0 }

--
-- ACCESS Point Configuration Management (1)
--
--
-- ACCESS Point Manufacturer Information Group (1.1)
--
-- This group specifies the manufacturer information on the ACCESS
-- Point for identification only. These data may not be altered by 
-- users.
--

apModelnumber OBJECT-TYPE
		SYNTAX  OCTET STRING (SIZE (1..32))
    	MAX-ACCESS  read-only
    	STATUS  current
    	DESCRIPTION
    		"The Model Number of the ACCESS Point device."
    	::= { apManufactureInfo 1 }

apSerialnumber OBJECT-TYPE
		SYNTAX  OCTET STRING (SIZE (1..16))
		MAX-ACCESS  read-only
		STATUS  current
		DESCRIPTION
    		"The Serial Number of the ACCESS Point system."
    	::= { apManufactureInfo 2 }

apMyMacAddr OBJECT-TYPE
		SYNTAX  MacAddress
    	MAX-ACCESS  read-only
    	STATUS  current
    	DESCRIPTION
    		"The MAC address of the ACCESS Point."
		::= { apManufactureInfo 3 }
 
apFirmwareVer OBJECT-TYPE
    	SYNTAX  OCTET STRING (SIZE (1..32))
    	MAX-ACCESS  read-only
    	STATUS  current
    	DESCRIPTION
    		"The current version of the ACCESS Point firmware."
    	::= { apManufactureInfo 4 }

apWebUiVer OBJECT-TYPE
		SYNTAX  OCTET STRING (SIZE (0..16))
		MAX-ACCESS  read-only
		STATUS  current
		DESCRIPTION
			"The current version of the ACCESS Point WEB Configration System."
		::= { apManufactureInfo 5 }

apMfgDate OBJECT-TYPE
    	SYNTAX  OCTET STRING (SIZE (1..8))
    	MAX-ACCESS  read-only
    	STATUS  current
    	DESCRIPTION
    		"The Date of this ACCESS Point was manufactured."
    	::= { apManufactureInfo 6 }

apProductName OBJECT-TYPE
    	SYNTAX  OCTET STRING (SIZE (1..32))
    	MAX-ACCESS  read-only
    	STATUS  current
    	DESCRIPTION
    		"The Product Name of this ACCESS Point."
    	::= { apManufactureInfo 7 }

apMfgName OBJECT-TYPE
    	SYNTAX  OCTET STRING (SIZE (1..32))
    	MAX-ACCESS  read-only
    	STATUS  current
    	DESCRIPTION
    		"The Manufacture Name of this ACCESS Point."
    	::= { apManufactureInfo 8 }

apHardwareRev OBJECT-TYPE
    	SYNTAX  INTEGER(0..4294967295)
    	MAX-ACCESS  read-only
    	STATUS  current
    	DESCRIPTION
    		"The Hardware Revision of this ACCESS Point."
    	::= { apManufactureInfo 9 }

--
-- ACCESS Point System Configuration Information Group (1.2)
--
-- This group contains the ACCESS Point System Configuration Information
-- which is used for controlling the ACCESS Point system operations.
--

apDeviceName	OBJECT-TYPE
		SYNTAX  OCTET STRING (SIZE (1..256))
   		MAX-ACCESS  read-write
   		STATUS  current
   		DESCRIPTION
       		"An ASCII string to identify the Device Name of this ACCESS Point (up to 
       		255 characters)."
   		::= { apSystemConfig  1 }

apDeviceLoc	OBJECT-TYPE
		SYNTAX  OCTET STRING (SIZE (1..256))
   		MAX-ACCESS  read-write
   		STATUS  current
   		DESCRIPTION
       		"An ASCII string to identify the Location of this ACCESS Point (up to 
       		255 characters)."
   		::= { apSystemConfig  2 }

apHelpFilePath	OBJECT-TYPE
		SYNTAX  OCTET STRING (SIZE (1..256))
   		MAX-ACCESS  read-write
   		STATUS  current
   		DESCRIPTION
       		"An ASCII string to identify the Location of this ACCESS Point (up to 
       		255 characters)."
   		::= { apSystemConfig  3 }

apMyIPAddr	OBJECT-TYPE
   		SYNTAX  IpAddress
   		MAX-ACCESS  read-write
   		STATUS  current
		DESCRIPTION
			"The IP address for the Access Point. 
			It can be set when apStaticIPAddrEnable is set to is enabled."
		::= { apSystemConfig  4 }

apSubnetMask	OBJECT-TYPE
		SYNTAX  IpAddress
		MAX-ACCESS  read-write
		STATUS  current
		DESCRIPTION
			"The subnet mask for the Access Point.
			It can be set when apStaticIPAddrEnable is set to enabled."
		::= { apSystemConfig  5 }

apGatewayIPAddr	OBJECT-TYPE
		SYNTAX  IpAddress
		MAX-ACCESS  read-write
		STATUS  current
		DESCRIPTION
			"The IP address of the gateway for the Access Point."
		::= { apSystemConfig  6 }
 
apAdditionalGatewaysTableLength OBJECT-TYPE
	SYNTAX		Integer32
	MAX-ACCESS	read-only
	STATUS		current
	DESCRIPTION
		"The maximum number of entries in the Additional Gateways Table."
	::= { apSystemConfig 7 }

apAdditionalGatewaysTable OBJECT-TYPE
		SYNTAX  SEQUENCE OF ApAdditionalGatewaysEntry
        MAX-ACCESS  not-accessible
        STATUS  current
        DESCRIPTION
             "A table of information for additional Gateways.
			 The current number of entries is 4(that mean aditional gateway is 3)."
        ::= { apSystemConfig 8 }
 
apAdditionalGatewaysEntry OBJECT-TYPE
		SYNTAX  ApAdditionalGatewaysEntry
		MAX-ACCESS  not-accessible
		STATUS  current
		DESCRIPTION
             "An entry in the table of information for additional
			 gateways for this ACCESS Point.
			 A row in this table cannot be created or deleted by
			 SNMP operations on columns of the table."
		INDEX { additionalGatewaysIndex }
    	::= { apAdditionalGatewaysTable 1}
 
ApAdditionalGatewaysEntry ::= SEQUENCE {
		additionalGatewaysIndex
			INTEGER,
    	apAdditionalGatewaysIPAddr
    		IpAddress
}
 
additionalGatewaysIndex OBJECT-TYPE
    	SYNTAX  INTEGER (1..3) 
    	MAX-ACCESS  not-accessible
    	STATUS  current
    	DESCRIPTION
        	"Specific Gateway information Table index.
			 Range (1..3)."
    	::= { apAdditionalGatewaysEntry 1 }
 
apAdditionalGatewaysIPAddr OBJECT-TYPE
    	SYNTAX  IpAddress
    	MAX-ACCESS  read-write
    	STATUS  current
    	DESCRIPTION
    		"The IP address of the Gateway used for this Access Point."
    	::= { apAdditionalGatewaysEntry 2 }

apDHCPEnable	OBJECT-TYPE
		SYNTAX  INTEGER {
                       	enabled(1),
                       	disabled(2)     
        		      	}
        MAX-ACCESS  read-write
        STATUS  current
        DESCRIPTION
             "Enables/Disables Wireless DHCP mode for the Access Point. 
             Default is disabled(2)."
        ::= { apSystemConfig 9 }

apStaticIPAddrEnable    OBJECT-TYPE
        SYNTAX  INTEGER {
                       	enabled(1),
                       	disabled(2)     
        		      	} 
        MAX-ACCESS  read-write
        STATUS  current
        DESCRIPTION
           	"Enables/Disables Static IP of ACCESS Point .
			 Default is disabled(2). Before issuing this command, set 'apMyIPAddr', 
			 'apSubnetMask', and 'apGatewayIPAddr' to the proper values."
        ::= { apSystemConfig  10 }

-- 
--  The ACCESS Point SNMP Configuration Information Group (1.3) 
--
--  This group contains the SNMP configuration information which is
--  used for SNMP operations on the Access Point. A trap receiver table 
--  allows users to set the Network Manager addresses for receiving
--  the traps (i.e. Alert/Alarm/Event) from ACCESS Point devices.
-- 

apSNMPRequests OBJECT-TYPE
		SYNTAX  Counter32
        MAX-ACCESS  read-only
        STATUS  current
        DESCRIPTION
            "Indicates the number of SNMP requests to 
			this SNMP Agent."
        ::= { apSNMPInfo 1 }

apSNMPTraps OBJECT-TYPE
        SYNTAX  Counter32
        MAX-ACCESS  read-only
        STATUS  current
        DESCRIPTION
           	"Indicates the number of Traps that were generated 
			by this SNMP Agent."
        ::= { apSNMPInfo 2 }
  
apAllTrapsEnable OBJECT-TYPE
        SYNTAX  INTEGER {
                    	enabled(1),   
	    	          	disabled(2)  
            		  	}
        MAX-ACCESS  read-write
        STATUS  current
        DESCRIPTION
           	"Enables/Disables all SNMP traps. Default is enabled(1)."
        ::= { apSNMPInfo 3 }
 
apColdBootTrapEnable OBJECT-TYPE
		SYNTAX  INTEGER {
	                  	disabled(1),     
    	               	trapHost1(2),
        	          	trapHost2(3),     
            	      	allTrapHosts(4)     			     
        	    	  	}
        MAX-ACCESS  read-write
        STATUS  current
        DESCRIPTION
             "Enables/Disables ACCESS Point Cold Boot trap. Default 
			 is allTrapHosts(4). This is a generic-trap and the trap 
			 code is 0.
			 
			 When not disabled the trap could be directed to TrapHost1,
			 TrapHost2 or all TrapHosts. 
			 
			 The apAllTrapsEnable mib variable should be enabled for this trap 
			 to be issued."
        ::= { apSNMPInfo 4 }


apAuthenFailureTrapEnable OBJECT-TYPE
        SYNTAX  INTEGER {
                  	disabled(1),     
                   	trapHost1(2),
                  	trapHost2(3),     
                  	allTrapHosts(4)     			     
        	      	}
        MAX-ACCESS  read-write
        STATUS  current
        DESCRIPTION
             "Enables/Disables authentication failure trap. Default
			 is allTrapHosts(4). This is a generic-trap and the trap 
			 code is 4.
			 
			 When not disabled the trap could be directed to TrapHost1,
			 TrapHost2 or all TrapHosts. 
			 
			 The apAllTrapsEnable mib variable should be enabled for this trap 
			 to be issued."
        ::= { apSNMPInfo 5 }

apRFTrapEnable OBJECT-TYPE
        SYNTAX  INTEGER {
          				disabled(1),     
               			trapHost1(2),
           			  	trapHost2(3),     
        		     	allTrapHosts(4)     			     
        		      	}
        MAX-ACCESS  read-write
        STATUS  current
        DESCRIPTION
             "Enables/Disables ACCESS Point RF driver startup trap. 
			 Default is allTrapHosts(4). This is an a3com enterprise-specific trap.
			 
			 When not disabled the trap could be directed to TrapHost1,
			 TrapHost2 or all TrapHosts. 
			 
			 The apAllTrapsEnable mib variable should be enabled for this trap 
			 to be issued."
        ::= { apSNMPInfo 6 }


apWarmBootTrapEnable OBJECT-TYPE
		SYNTAX  INTEGER {
	                  	disabled(1),     
    	               	trapHost1(2),
        	          	trapHost2(3),     
            	      	allTrapHosts(4)     			     
        	    	  	}
        MAX-ACCESS  read-write
        STATUS  current
        DESCRIPTION
             "Enables/Disables Warm Boot trap. Default 
			 is allTrapHosts(4). This is a generic-trap and the trap 
			 code is 0.
			 
			 When not disabled the trap could be directed to TrapHost1,
			 TrapHost2 or all TrapHosts. 
			 
			 The apAllTrapsEnable mib variable should be enabled for this trap 
			 to be issued."
        ::= { apSNMPInfo 7 }

apWCMaxAssocTrapEnable OBJECT-TYPE
		SYNTAX  INTEGER {
	                  	disabled(1),     
    	               	trapHost1(2),
        	          	trapHost2(3),     
            	      	allTrapHosts(4)     			     
        	    	  	}
        MAX-ACCESS  read-write
        STATUS  current
        DESCRIPTION
             "Enables/Disables apWCMaxAssoc Trap. Default is allTrapHosts(4). 
			 
			 When not disabled the trap could be directed to TrapHost1,
			 TrapHost2 or all TrapHosts. 
			 
			 The apAllTrapsEnable mib variable should be enabled for this trap 
			 to be issued."
        ::= { apSNMPInfo 8 }


apThresholdAssociatedEnable OBJECT-TYPE
		SYNTAX  INTEGER {
	                  	disabled(1),     
    	               	trapHost1(2),
        	          	trapHost2(3),     
            	      	allTrapHosts(4)     			     
        	    	  	}
        MAX-ACCESS  read-write
        STATUS  current
        DESCRIPTION
             "Enables/Disables apThresholdAssociated Trap. Default 
			 is allTrapHosts(4). 
			 
			 When not disabled the trap could be directed to TrapHost1,
			 TrapHost2 or all TrapHosts. 
			 
			 The apAllTrapsEnable mib variable should be enabled for this trap 
			 to be issued."
        ::= { apSNMPInfo 9 }
                    

dslSecurityViolationEnable OBJECT-TYPE
		SYNTAX  INTEGER {
	                  	disabled(1),     
    	               	trapHost1(2),
        	          	trapHost2(3),     
            	      	allTrapHosts(4)     			     
        	    	  	}
        MAX-ACCESS  read-write
        STATUS  current
        DESCRIPTION
             "Enables/Disables dslSecurityViolation Trap. Default 
			 is allTrapHosts(4). 
			 
			 When not disabled the trap could be directed to TrapHost1,
			 TrapHost2 or all TrapHosts. 
			 
			 The apAllTrapsEnable MIB variable should be enabled for this trap 
			 to be issued."
        ::= { apSNMPInfo 10 }


--
--  The ACCESS Point RF Configuration Information Group (1.4)
--
--  This group contains AP Radio Frequency interface configuration 
--  information.
--
apWlanServiceArea OBJECT-TYPE
		SYNTAX  OCTET STRING (SIZE (1..32))
		MAX-ACCESS  read-write
		STATUS  current
		DESCRIPTION
    		"The WLAN Service Area of the ACCESS Point."
    	::= { apRFConfig 1 }
  
apCountryName OBJECT-TYPE
        SYNTAX  OCTET STRING (SIZE (1..16))
        MAX-ACCESS  read-only
        STATUS  current
        DESCRIPTION
           	"The country for which the ACCESS Point radio is 
			 configured. It is set at the factory and may not be 
			 altered."
        ::= { apRFConfig 2 }
	
apWEPAlgorithm    OBJECT-TYPE
		SYNTAX  INTEGER{ 
				openSystem(1),
				wep40bShareKey(2),
				wep128bShareKey(3),	
				wep128bpasswordsessionKey(4),	
				wepEAPMD5Authenticationwithnoencryption(5),	
				wepEAPMD5Authenticationwith40bsharedkey(6),	
				wepEAPMD5Authenticationwith128bsharedkey(7),	
				wepEAPMD5Authenticationwith128bpasswordsessionkey(8),	
				wepEAPTLSAuthenticationwith40bsessionkey(9),	
				wepEAPTLSAuthenticationwith128bsessionkey(10),	
				wepSerialAuthenticationwith40bsessionkey(11),	
				wepSerialAuthenticationwith128bsessionkey(12)	
	            }
        MAX-ACCESS  read-only
        STATUS  current
        DESCRIPTION
			"This attribute is a set of all the shared key WEP algorithms 
			 supported by the STAs. The following are the default values
			 and the associated algorithm.    
			  			Value = 1: open system  
        		    	Value = 2: 40 bit Key
        		        Value = 3: 128 bit Key
			 IMPORTANT NOTE: The 128 bit WEP key ENcryption is currently
			 restricted by U.S. laws."
        ::= { apRFConfig 3 }

apShortPreamble  OBJECT-TYPE
		SYNTAX  INTEGER{ 
    					enabled(1),
						disabled(2)
	    				}
		MAX-ACCESS  read-write
		STATUS  current
		DESCRIPTION
			"This attribute is a set to enable short preamble for compatibility 
			 within the 802.11 community. Setting it to enabled shall 
			 result in performance enhancement. Default is disabled."
    	::= { apRFConfig 4 }

apMaxWCTrigger  OBJECT-TYPE
        SYNTAX  INTEGER (1..255)
        MAX-ACCESS  read-write
        STATUS  current
        DESCRIPTION
        	"Indicates the trigger point for sending  
			apWCMaxAssocTrap trap. Range (1..255)
			The default value is 255."
        ::= { apRFConfig 5 }

apRadioAutoSense  OBJECT-TYPE
		SYNTAX  INTEGER{ 
    					enabled(1),
						disabled(2)
	    				}
		MAX-ACCESS  read-write
		STATUS  current
		DESCRIPTION
			"This attribute is a set to enable Radio Auto Sense.
			Default is enabled."
    	::= { apRFConfig 6 }

apRadioChannel  OBJECT-TYPE
		SYNTAX  INTEGER (1..14)
		MAX-ACCESS  read-write
		STATUS  current
		DESCRIPTION
			"This attribute is Radio Channel.
			This attribute can be written when apRadioAutoSense is disabled."
    	::= { apRFConfig 7 }

apHighPerformance  OBJECT-TYPE
		SYNTAX  INTEGER{ 
    					enabled(1),
						disabled(2)
	    				}
		MAX-ACCESS  read-write
		STATUS  current
		DESCRIPTION
			"This attribute is a set to enable Radio High Performance.
			Default is disabled."
    	::= { apRFConfig 8 }

apTransmitPower OBJECT-TYPE
  		SYNTAX  INTEGER 
  						{ 
  						high(1),
  						medium(2),
  						low(3)                    
  						}
      	MAX-ACCESS  read-write
  		STATUS  current
  		DESCRIPTION
  			"This attribute is a set the transmit power from 1-100 micro watts."
      	::= { apRFConfig 9 }     
      	 
apRadioAntenna  OBJECT-TYPE
  		SYNTAX  INTEGER {    
  		                 enabledoneantenna(1),
  		                 bothantennaon(2)
  						}
      	MAX-ACCESS  read-write
  		STATUS  current
  		DESCRIPTION
  			"This attribute is a set the section of radio antenna."
      	::= { apRFConfig 10 }      

thresholdAssociated  OBJECT-TYPE
  		SYNTAX  INTEGER (1..256)
      	MAX-ACCESS  read-write
  		STATUS  current
  		DESCRIPTION
  			"This attribute is a set the threshold of Associated Wireless Client.
  			The default is 200."
      	::= { apRFConfig 11 }

apDataRateMgmt  OBJECT-TYPE
  		SYNTAX  INTEGER {    
  		                 auto(1),
  		                 manual(2)
  						}
      	MAX-ACCESS  read-write
  		STATUS  current
  		DESCRIPTION
  			"This attribute is automatically  or manually set the best data rate ."
      	::= { apRFConfig 12 }      

apDataRate5  OBJECT-TYPE
  		SYNTAX  INTEGER {    
  		                 optional(1),
  		                 required(2)
  						}
      	MAX-ACCESS  read-write
  		STATUS  current
  		DESCRIPTION
  			"This attribute is a set the data rate to 5.5 Mb/sec ."
      	::= { apRFConfig 13 }      

apDataRate11  OBJECT-TYPE
  		SYNTAX  INTEGER {    
  		                 optional(1),
  		                 required(2)
  						}
      	MAX-ACCESS  read-write
  		STATUS  current
  		DESCRIPTION
  			"This attribute is a set the data rate to 11.0 Mb/sec ."
      	::= { apRFConfig 14 }      
      	     
--
--  Access Point Performance Management (2)
--
--
--       
--  Radio Frequency Interface Statistics Group (2.4)
--
--  This group contains statistics/counters information specific to
--  the Access Point Radio Frequency Interface.
--
rfTxUcastFrms OBJECT-TYPE
		SYNTAX  Counter32
        MAX-ACCESS  read-only
        STATUS  current
       	DESCRIPTION
           	" The number of Unicast frames successfully transmitted."
        ::= { apRFStatistics 1 }

rfRxUcastFrms OBJECT-TYPE
       	SYNTAX  Counter32
        MAX-ACCESS  read-only
        STATUS  current
       	DESCRIPTION
           	" The number of Unicast frames successfully received "
        ::= { apRFStatistics 2 }
 
rfTxBcastFrms OBJECT-TYPE
        SYNTAX Counter32
        MAX-ACCESS  read-only
        STATUS  current
        DESCRIPTION
        	" The number of Broadcast frames transmitted "
        ::= { apRFStatistics 3 }
 
rfRxBcastFrms OBJECT-TYPE
       	SYNTAX Counter32
       	MAX-ACCESS  read-only
       	STATUS  current
       	DESCRIPTION
           	" The number of Broadcast frames received."
       	::= { apRFStatistics 4 }
 
rfTxMcastFrms  OBJECT-TYPE
       	SYNTAX  Counter32
       	MAX-ACCESS  read-only
       	STATUS  current
       	DESCRIPTION
           	" The number of Multicast frames transmitted."
       	::= { apRFStatistics 5 }

rfRxMcastFrms  OBJECT-TYPE
		SYNTAX  Counter32
        MAX-ACCESS  read-only
       	STATUS  current
        DESCRIPTION
           	" The number of Multicast frames received."
        ::= { apRFStatistics 6 }

rfTxEncryptFrms OBJECT-TYPE
        SYNTAX  Counter32
        MAX-ACCESS  read-only 
        STATUS  current
        DESCRIPTION
           	" The number of Encrypted frames transmitted."
        ::= { apRFStatistics 7 }

rfRxEncryptFrms OBJECT-TYPE
        SYNTAX  Counter32
        MAX-ACCESS  read-only
        STATUS  current
        DESCRIPTION
             " The number of Encrypted frames received."
        ::= { apRFStatistics 8 }

rfTxFragFrms OBJECT-TYPE
        SYNTAX Counter32
        MAX-ACCESS  read-only
        STATUS  current
        DESCRIPTION
             " The number of frames fragments transmitted."
        ::= { apRFStatistics 9 }
 
rfRxFragFrms OBJECT-TYPE
        SYNTAX Counter32
        MAX-ACCESS  read-only
        STATUS  current
        DESCRIPTION 
           	" The number of frames fragments received."
        ::= {apRFStatistics 10 }
 
rfTxBeacons OBJECT-TYPE
		SYNTAX  Counter32
        MAX-ACCESS  read-only
        STATUS  current
        DESCRIPTION
             " The number of Beacon frames transmitted."
        ::= { apRFStatistics 11 }

rfRxBeacons OBJECT-TYPE
        SYNTAX  Counter32
        MAX-ACCESS  read-only
        STATUS  current
        DESCRIPTION
            " The number of Beacon frames received."
        ::= { apRFStatistics 12 }
 
rfTxACK OBJECT-TYPE
        SYNTAX  Counter32
        MAX-ACCESS  read-only
        STATUS  current
        DESCRIPTION
             "The number of ACK frames transmitted in response to successfully received frames."
        ::= { apRFStatistics 13 }
 
rfRxACK OBJECT-TYPE
        SYNTAX  Counter32
        MAX-ACCESS  read-only
        STATUS  current
        DESCRIPTION
             " The number of frames transmitted that had their corresponding ACK frames successfully received frames."
        ::= { apRFStatistics 14 }
 
rfTxRTS OBJECT-TYPE
        SYNTAX  Counter32
        MAX-ACCESS  read-only
        STATUS  current
        DESCRIPTION
             " The number of RTS frames that were successfully transmitted."
        ::= { apRFStatistics 15 }
 
rfRxRTS OBJECT-TYPE
        SYNTAX  Counter32
       	MAX-ACCESS  read-only
        STATUS  current
        DESCRIPTION
             " The number of RTS received frames."
        ::= { apRFStatistics 16 }
 
rfCTSFailures OBJECT-TYPE
        SYNTAX  Counter32
        MAX-ACCESS  read-only
        STATUS  current
        DESCRIPTION
             " The number of frames for which no CTS frames was received in response to a RTS frames being sent."
        ::= { apRFStatistics 17 }
 
rfRxCTS OBJECT-TYPE
		SYNTAX  Counter32
        MAX-ACCESS  read-only
        STATUS  current
        DESCRIPTION
             " The number of CTS frames received in response to a RTS." 
        ::= { apRFStatistics 18 }
 
rfTxACKFailures OBJECT-TYPE
        SYNTAX  Counter32
        MAX-ACCESS  read-only
        STATUS  current
        DESCRIPTION
              " The number of frames transmitted that did not have their corresponding ACK packets successfully received."
        ::= { apRFStatistics 19 }
 
rfTxRetrys OBJECT-TYPE
        SYNTAX  Counter32
        MAX-ACCESS  read-only
        STATUS  current
        DESCRIPTION
           	" The number of frames that were retransmitted."
        ::= { apRFStatistics 20 }
 
rfFCSErrors OBJECT-TYPE
		SYNTAX  Counter32
        MAX-ACCESS  read-only
        STATUS  current
        DESCRIPTION
        	" The number of frames received with checksum error."
        ::= { apRFStatistics 21 }

rfRxDuplicateFrms OBJECT-TYPE
		SYNTAX  Counter32
        MAX-ACCESS  read-only
        STATUS  current
        DESCRIPTION
        	" The number of duplicate frames received."
        ::= { apRFStatistics 22 }

rfWEPUndecryptFrms OBJECT-TYPE
        SYNTAX  Counter32
        MAX-ACCESS  read-only
        STATUS  current
       	 DESCRIPTION
             " The number of frames received with the WEP sub-field of the Frame Control field set to one and the WEPOn value for the key mapped to the TA's MAC address indicates that the frame should not have been encrypted or that frame is discarded due to the receiving STA not implementing the privacy option."
        ::= { apRFStatistics 23 }

rfWEPICVErrors OBJECT-TYPE
		SYNTAX  Counter32
        MAX-ACCESS  read-only
        STATUS  current
        DESCRIPTION
        	" The number of frames received with the WEP sub-field of the Frame Control field set to one and the value of the ICV as received in the frame does not match the ICV value that is calculated for the contents of the received frame."
        ::= { apRFStatistics 24 }



--       
--  Ethernet Interface Statistics Group 
--
        
apEtherPacketsIns OBJECT-TYPE
         	SYNTAX  Counter32
          	MAX-ACCESS  read-only
           	STATUS  current
           	DESCRIPTION
           	"Indicates the number of good packets received on the 
			 Ethernet interface."
          	::= { apEtherItfStat 1 }

apEtherPacketsOuts OBJECT-TYPE
			SYNTAX  Counter32
          	MAX-ACCESS  read-only
            STATUS  current
            DESCRIPTION
            "Indicates the number of packets successfully 
			 transmitted on the Ethernet interface."
          	::= { apEtherItfStat 2 }

apEtherOctetsIns OBJECT-TYPE
          	SYNTAX  Counter32
          	MAX-ACCESS  read-only
            STATUS  current
            DESCRIPTION
            "Indicates the number of good bytes received on the 
			 Ethernet interface."
           	::= { apEtherItfStat 3 }

apEtherOctetsOuts OBJECT-TYPE
         	SYNTAX  Counter32
          	MAX-ACCESS  read-only
           	STATUS  current
          	DESCRIPTION
           	"Indicates the number of bytes successfully transmitted
			 on the Ethernet interface."
           	::= { apEtherItfStat 4 }
 
apEtherPktsInPerSec OBJECT-TYPE
            SYNTAX  Gauge32
            MAX-ACCESS  read-only
            STATUS  current
            DESCRIPTION
            "Indicates the number of good packets per second 
			 received on the Ethernet Interface."
            ::= { apEtherItfStat 5 }

apEtherPktsOutPerSec OBJECT-TYPE
            SYNTAX  Gauge32
            MAX-ACCESS  read-only
            STATUS  current
            DESCRIPTION
            "Indicates the number of packets per second successfully
			 transmitted on the Ethernet interface."
          	::= { apEtherItfStat 6 }
 
apEtherOctInPerSec OBJECT-TYPE
           	SYNTAX  Gauge32
           	MAX-ACCESS  read-only
           	STATUS  current
           	DESCRIPTION
           	"Indicates the number of good bytes per second 
			 received on the Ethernet Interface."
           	::= { apEtherItfStat 7 }
 
apEtherOctOutPerSec OBJECT-TYPE
          	SYNTAX  Gauge32
           	MAX-ACCESS  read-only
           	STATUS  current
           	DESCRIPTION
           	"Indicates the number of bytes per second successfully
			 transmitted on the Ethernet interface."
           	::= { apEtherItfStat 8 }
--       
--  Radio Frequency Interface Statistics Group (2.4)
--
--  This group contains statistics/counters information specific to
--  the Access Point Radio Frequency Interface.
--

apRFFrmsIns OBJECT-TYPE
         	SYNTAX  Counter32
          	MAX-ACCESS  read-only
           	STATUS  current
           	DESCRIPTION
           	"Indicates the number of good packets received on the 
			 RF interface."
          	::= { apRFItfStat 1 }

apRFFrmsOuts OBJECT-TYPE
			SYNTAX  Counter32
          	MAX-ACCESS  read-only
            STATUS  current
            DESCRIPTION
            "Indicates the number of packets successfully 
			 transmitted on the RF interface."
          	::= { apRFItfStat 2 }

apRFOctetsIns OBJECT-TYPE
          	SYNTAX  Counter32
          	MAX-ACCESS  read-only
            STATUS  current
            DESCRIPTION
            "Indicates the number of good bytes received on the 
			 RF interface."
           	::= { apRFItfStat 3 }

apRFOctetsOuts OBJECT-TYPE
         	SYNTAX  Counter32
          	MAX-ACCESS  read-only
           	STATUS  current
          	DESCRIPTION
           	"Indicates the number of bytes successfully transmitted
			 on the RF interface."
           	::= { apRFItfStat 4 }
 
apRFFrmsInPerSec OBJECT-TYPE
            SYNTAX  Gauge32
            MAX-ACCESS  read-only
            STATUS  current
            DESCRIPTION
            "Indicates the number of good packets per second 
			 received on the RF Interface."
            ::= { apRFItfStat 5 }

apRFFrmsOutPerSec OBJECT-TYPE
            SYNTAX  Gauge32
            MAX-ACCESS  read-only
            STATUS  current
            DESCRIPTION
            "Indicates the number of packets per second successfully
			 transmitted on the RF interface."
          	::= { apRFItfStat 6 }
 
apRFOctInPerSec OBJECT-TYPE
           	SYNTAX  Gauge32
           	MAX-ACCESS  read-only
           	STATUS  current
           	DESCRIPTION
           	"Indicates the number of good bytes per second 
			 received on the RF Interface."
           	::= { apRFItfStat 7 }
 
apRFOctOutPerSec OBJECT-TYPE
          	SYNTAX  Gauge32
           	MAX-ACCESS  read-only
           	STATUS  current
           	DESCRIPTION
           	"Indicates the number of bytes per second successfully
			 transmitted on the RF interface."
           	::= { apRFItfStat 8 }   

--
-- Forwarding count between RF interface to Ethernet Interface       
--
apEnetsNPktsToEnets OBJECT-TYPE
        	SYNTAX  Counter32
       		MAX-ACCESS  read-only
          	STATUS  current
           	DESCRIPTION
           	"Indicates the number of packets sent from the Ethernet 
           	 Interface the Ethernet Interface.  Must be 0"
			 ::= { apTrafficMatrix 1 }  
			 
apRFNPktsToEnets OBJECT-TYPE
        	SYNTAX  Counter32
       		MAX-ACCESS  read-only
           	STATUS  current
           	DESCRIPTION
           	"Indicates the number of packets sent from the RF 
           	 Interface to the Ethernet Interface."
           	::= { apTrafficMatrix 2 }      
           	
apEnetsNPktsToRF OBJECT-TYPE
        	SYNTAX  Counter32
       		MAX-ACCESS  read-only
          	STATUS  current
          	DESCRIPTION
          	"Indicates the number of packets sent from Ethernet
          	 Interface to the RF Interface. "
          	 ::= { apTrafficMatrix 3 }      
           	
apRFNPktsToRF OBJECT-TYPE
        	SYNTAX  Counter32
       		MAX-ACCESS  read-only
           	STATUS  current
           	DESCRIPTION
           	"Indicates the number of packets sent from the RF
           	 Interfaceto the RF Interface. Must be 0"
			::= { apTrafficMatrix 4 }

	--
	--  Access Point RF Per Frequency Statistics Table Group 
	--  for DSSS System
	--  This group contains the Access Point Radio Frequency Per 
	--  Frequency statistics/counters information based on the 
	--  historical frequency records used by this Access Point.
	--

apDSPerFreqStatTable OBJECT-TYPE
          	SYNTAX SEQUENCE OF ApDSPerFreqStatEntry
           	MAX-ACCESS not-accessible
           	STATUS current
                DESCRIPTION
                     	"A table of Radio Per Frequency statistics, which is 
			 based on the historical frequency records used by this
			 Access Point.
			 The current number of entries is 78."
                ::= { apPerformMgmt 5 }
 
apDSPerFreqStatEntry OBJECT-TYPE
            	SYNTAX ApDSPerFreqStatEntry
               	MAX-ACCESS not-accessible
           	STATUS current
                DESCRIPTION
                     	"An entry in the table of Radio per frequency 
			 statistics.
			 A row in this table cannot be created or deleted by
			 SNMP operations on columns of the table."
                INDEX { rfDSFrequency}
                ::= { apDSPerFreqStatTable 1 }
 
ApDSPerFreqStatEntry ::= SEQUENCE {
               	rfDSFrequency         
			INTEGER,
              	rfDSPerFqPktsSents      
			Counter32,
                rfDSPerFqPktsRcvds      
			Counter32,
                rfDSPerFqRetries       
			Counter32
   	}
 
rfDSFrequency OBJECT-TYPE
               	SYNTAX  INTEGER (1..14)
          	MAX-ACCESS  read-only
                STATUS  current
                DESCRIPTION
                     	"Radio Frequency channel number."
                ::= { apDSPerFreqStatEntry 1 }

rfDSPerFqPktsSents OBJECT-TYPE
                SYNTAX  Counter32
          	MAX-ACCESS  read-only
                STATUS  current
                DESCRIPTION
                     	"Counter for the packets sent per frequency." 
             	::= { apDSPerFreqStatEntry 2 }

rfDSPerFqPktsRcvds OBJECT-TYPE
                SYNTAX  Counter32
          	MAX-ACCESS  read-only
                STATUS  current
                DESCRIPTION
                     	"Counter for the packets received per frequency." 
             	::= { apDSPerFreqStatEntry 3 }

rfDSPerFqRetries OBJECT-TYPE
                SYNTAX  Counter32
          	MAX-ACCESS  read-only
                STATUS  current
                DESCRIPTION
                     	"Counter for the retries per frequency." 
             	::= { apDSPerFreqStatEntry 4 }

--	
--  Access Point Fault Management (3)
--

apUpdateTemplateStatus  OBJECT-TYPE
  		SYNTAX  INTEGER {
  						downloadSuccessful(1),
  						downloadUnknownError(2),
  						downloadTimeout(3),
  						badFileName(4),
  						badMacAddrForRestoreFile(5),
  						incorrectFileImage(6),
  						tftpFileNotFound(7),
  						tftpAccessViolation(8),
  						tftpDiskfullOrAllocationExceeded(9),
  						tftpIllegalTFTPoperation(10),
  						tftpUnknownTransferID(11),
  						tftpFileAlreadyExists(12),
  						tftpNoSuchUser(13),
  						fileDownloadOrUpload(14)
  						}
        MAX-ACCESS  read-only
        STATUS  current
        DESCRIPTION
           	"Reports the Firmware/HTML file download and
  			 update status." 
        ::= { apFaultMgmt 1 }

apBackupFileName	OBJECT-TYPE
       	SYNTAX  OCTET STRING (SIZE (1..256))
       	MAX-ACCESS  read-write
       	STATUS  current
       	DESCRIPTION
           	"The name of the file to be backuped to the TFTP Server. 
           	(Including path name and total up to 255 characters.)"
       	::= { apFaultMgmt 2 }

apTemplateOperation OBJECT-TYPE
        SYNTAX  INTEGER {
						startBackup(1),
						startTemplate(2),
						startRestore(3),
						uploadingData(4),
						downloadingData(5),
						notDownloading(6),
						idle(7)
						}
        MAX-ACCESS  read-write
        STATUS  current
        DESCRIPTION
			"startBackup(1) -  Backup the AP configuration through TFTP server. 
			The AP backup configuration, named as apBackupFileName, 
			will be saved in the default location of TFTP server. 
			Before issuing this command, set 'apBackupFileName', 
			and 'apTFTPServer' to the proper values. 
			
			startTemplate(2) - This allows the network management platform 
			to restore the template configuration of a AP, from one of it's previous backups. 
			It is expected that common Parameters of AP in the backup configuration file, 
			named as apRestoreFileName, will be restored to the AP.
			Before issuing this command, set 'apRestoreFileName', 
			and 'apTFTPServer' to the proper values.
			
			startRestore(3) - This allows the network management platform to restore 
			the full configuration of a AP, from one of it's previous backups.  
			It is expected that full of the data in the backup configuration file, 
			named as apRestoreFileName, will be restored to the AP.
			Before issuing this command, set 'apRestoreFileName', 
			and 'apTFTPServer' to the proper values."
        ::= { apFaultMgmt 3 }
 

apRestoreFileName	OBJECT-TYPE
       	SYNTAX  OCTET STRING (SIZE (1..256))
      	MAX-ACCESS  read-write
      	STATUS  current
       	DESCRIPTION
	      	"The name of the file to be restored to the AP. 
	      	(Including path name and total up to 255 characters.)"
        ::= { apFaultMgmt 4 }

apSyslogDstIpAddressTableLength OBJECT-TYPE
		SYNTAX		Integer32
		MAX-ACCESS	read-only
		STATUS		current
		DESCRIPTION
			"The maximum number of entries in the Syslog Destination Ip Address Table."
		::= { apFaultMgmt 5 }

apSyslogDstIpAddressTable OBJECT-TYPE
		SYNTAX  SEQUENCE OF ApSyslogDstIpAddressEntry
        MAX-ACCESS  not-accessible
        STATUS  current
        DESCRIPTION
             "A table of Syslog Destination Ip Address.
			 The current number of entries is 2."
        ::= { apFaultMgmt 6 }
 
apSyslogDstIpAddressEntry OBJECT-TYPE
		SYNTAX  ApSyslogDstIpAddressEntry
		MAX-ACCESS  not-accessible
		STATUS  current
		DESCRIPTION
             "An entry in the table of Syslog Destination Ip Address
			 for this ACCESS Point.
			 A row in this table cannot be created or deleted by
			 SNMP operations on columns of the table."
		INDEX { apSyslogDstIpAddressIndex }
    	::= { apSyslogDstIpAddressTable 1 }
 
ApSyslogDstIpAddressEntry ::= SEQUENCE {
		apSyslogDstIpAddressIndex
			INTEGER,
    	apSyslogDstIpAddress
    		IpAddress
}
 
apSyslogDstIpAddressIndex OBJECT-TYPE
    	SYNTAX  INTEGER (1..2) 
    	MAX-ACCESS  not-accessible
    	STATUS  current
    	DESCRIPTION
        	"Specific Syslog Destination Ip Address Table index.
			 Range (1..2)."
    	::= { apSyslogDstIpAddressEntry 1 }
 
apSyslogDstIpAddress OBJECT-TYPE
    	SYNTAX  IpAddress
    	MAX-ACCESS  read-write
    	STATUS  current
    	DESCRIPTION
    		"The IP address of Syslog Destination used for this Access Point."
    	::= { apSyslogDstIpAddressEntry 2 }

apSyslogEnable	OBJECT-TYPE
		SYNTAX  INTEGER {
                       	enabled(1),
                       	disabled(2)     
        		      	}
        MAX-ACCESS  read-write
        STATUS  current
        DESCRIPTION
             "Enables/Disables syslog for the Access Point. 
             Default is disabled(2)."
        ::= { apFaultMgmt 7 }


--
--  Access Point Security Management (4)
--

apACLViolations  OBJECT-TYPE
		SYNTAX  Counter32
        MAX-ACCESS  read-only
        STATUS  current
        DESCRIPTION
             "Indicates the number of Access Control violations 
			 occurred."
        ::= { apSecurityMgmt 1 }
   
apEAPSupport OBJECT-TYPE
		SYNTAX  INTEGER {
     						disabled (1),
 							eap (2),
     						serialauth (3)
     						}
        MAX-ACCESS  read-write
        STATUS  current
        DESCRIPTION
            "The AP supprt the Extensive Authentication Protocol is enabled or disabled. 
   			 Default is enabled."
             ::= { apSecurityMgmt 2 }
  
apAuthServerSupportNumber OBJECT-TYPE
	  	  	SYNTAX		Integer32
    		MAX-ACCESS	read-only
  		  	STATUS		current
    		DESCRIPTION
  		  	"The maximum number of entries in the Authenicator Server Table."
  		  	::= { apSecurityMgmt 3 }   
  		  	
apKeyServerSupportNumber OBJECT-TYPE
		  	SYNTAX		Integer32
 			MAX-ACCESS	read-only
  	  		STATUS		current
    		DESCRIPTION
  		  	"The maximum number of entries in the Key Server Table."
  		  	::= { apSecurityMgmt 4 }
    
apAccountServerSupportNumber OBJECT-TYPE
	  	  	SYNTAX		Integer32
    		MAX-ACCESS	read-only
    		STATUS		current
    		DESCRIPTION
  		  	"The maximum number of entries in the Accounting Server Table."
  		  	::= { apSecurityMgmt 5 }  
  		  	
apAuthServerTable OBJECT-TYPE
	  	  	SYNTAX  SEQUENCE OF ApAuthServerEntry
    	    MAX-ACCESS  not-accessible
        	STATUS  current
          	DESCRIPTION
            "A table of information for Authenticator Servers. Now support number of entries is 2."
  	        ::= { apSecurityMgmt 6 }
     
apAuthServerEntry OBJECT-TYPE
	  	  	SYNTAX  ApAuthServerEntry
    		MAX-ACCESS  not-accessible
    		STATUS  current
    		DESCRIPTION
            "An entry in the table of information for Authenticator Servers for this Access Point."
    		INDEX { apAuthServerIndex }
        		::= { apAuthServerTable 1}
     
ApAuthServerEntry ::= SEQUENCE {
    		apAuthServerIndex		Integer32,
        	apAuthServerIPAddr		IpAddress,
    		apAuthServerPortNumber	Integer32,
    		apAuthSharedSecret		OCTET STRING,
    		apAuthServerRetransmit	Integer32,
    		apAuthServerTimeout		Integer32
}
    
apAuthServerIndex	OBJECT-TYPE
	  	 	SYNTAX		Integer32 (1..2147483647)
    		MAX-ACCESS	not-accessible
    		STATUS  	current
    		DESCRIPTION
    			"A number uniquely identifying each Authenticator server."
    			::= { apAuthServerEntry 	1 }
    
apAuthServerIPAddr	OBJECT-TYPE
  	  		SYNTAX		IpAddress
    		MAX-ACCESS	read-write
    		STATUS  	current
    		DESCRIPTION
    			"The IP address of the Authenticator server referred to in this table entry."
    			::= { apAuthServerEntry 	2 }
    
apAuthServerPortNumber	OBJECT-TYPE
    		SYNTAX		Integer32 (0..65535)
    		MAX-ACCESS	read-write
    		STATUS  	current
    		DESCRIPTION
    		"The UDP port the client is using to send requests to this Authenticator server."
  	  		::= { apAuthServerEntry 	3 }

apAuthSharedSecret	OBJECT-TYPE
			SYNTAX	OCTET STRING (SIZE(0..20))
			ACCESS	read-write
			STATUS	mandatory
			DESCRIPTION
				"This values indicates the shared key used by the 
				authentication server."
			::= { apAuthServerEntry 4 }       

apAuthServerRetransmit	OBJECT-TYPE
    		SYNTAX		Integer32 (1..30)
    		MAX-ACCESS	read-write
    		STATUS  	current
    		DESCRIPTION
    		"The number of times the access point tries to authenticate logon access."
  	  		::= { apAuthServerEntry 	5 }

apAuthServerTimeout	OBJECT-TYPE
    		SYNTAX		Integer32 (1..60)
    		MAX-ACCESS	read-write
    		STATUS  	current
    		DESCRIPTION
    		"The number of seconds the access point waits for a reply from the RADIUS
    		 server before it resends the request"
  	  		::= { apAuthServerEntry 	6 }                                              
                                              
apKeyServerTable OBJECT-TYPE
	  	  	SYNTAX  SEQUENCE OF ApKeyServerEntry
    	    MAX-ACCESS  not-accessible
        	STATUS  current
          	DESCRIPTION
            "A table of information for Key Servers. Now support number of entries is 2."
  	        ::= { apSecurityMgmt 7 }
     
apKeyServerEntry OBJECT-TYPE
		  	SYNTAX  ApKeyServerEntry
   			MAX-ACCESS  not-accessible
    		STATUS  current
    		DESCRIPTION
            "An entry in the table of information for Key Servers for this Access Point."
    		INDEX { apKeyServerIndex }
        		::= { apKeyServerTable 1}
     
ApKeyServerEntry ::= SEQUENCE {
    		apKeyServerIndex	Integer32,
        	apKeyServerIPAddr	IpAddress,
    		apKeyServerPortNumber	Integer32
}
    
apKeyServerIndex	OBJECT-TYPE
	  	 	SYNTAX		Integer32 (1..2147483647)
    		MAX-ACCESS	not-accessible
    		STATUS  	current
    		DESCRIPTION
    			"A number uniquely identifying each Key server."
    			::= { apKeyServerEntry 	1 }
    
apKeyServerIPAddr	OBJECT-TYPE
	  	  	SYNTAX		IpAddress
    		MAX-ACCESS	read-write
    		STATUS  	current
    		DESCRIPTION
    			"The IP address of the Key server referred to in this table entry."
    			::= { apKeyServerEntry 	2 }
    
apKeyServerPortNumber	OBJECT-TYPE
    		SYNTAX		Integer32 (0..65535)
    		MAX-ACCESS	read-write
    		STATUS  	current
    		DESCRIPTION
    		"The UDP port the client is using to send requests to this server."
  	  		::= { apKeyServerEntry 	3 }       
    
apAccountServerTable OBJECT-TYPE
	   		SYNTAX  SEQUENCE OF ApAccountServerEntry
    	    MAX-ACCESS  not-accessible
        	STATUS  current
          	DESCRIPTION
            "A table of information for Account Servers. Now support number of entries is 1."
            ::= { apSecurityMgmt 	8 }
    	
apAccountServerEntry OBJECT-TYPE
    		SYNTAX  ApAccountServerEntry
    		MAX-ACCESS  not-accessible
    		STATUS  current
    		DESCRIPTION
            "An entry in the table of information for Account Servers for this Access Point."
    		INDEX { apAccountServerIndex }
        		::= { apAccountServerTable 1}
     
ApAccountServerEntry ::= SEQUENCE {
  	  	apAccountServerIndex		Integer32,
        apAccountServerIPAddr		IpAddress,
    	apAccountServerPortNumber	Integer32,
    	apAccountServerSharedSecret	OCTET STRING,
    	apAccountServerRetransmit	Integer32,
    	apAccountServerTimeout		Integer32
    }
    
apAccountServerIndex	OBJECT-TYPE
    		SYNTAX		Integer32 (1..2147483647)
    		MAX-ACCESS	not-accessible
    		STATUS  	current
    		DESCRIPTION
    			"A number uniquely identifying each Account server."
    		::= { apAccountServerEntry 	1 }
    
apAccountServerIPAddr	OBJECT-TYPE
    		SYNTAX		IpAddress
    		MAX-ACCESS	read-write
    		STATUS  	current
    		DESCRIPTION
    			"The IP address of the Account server referred to in this table entry."
    		::= { apAccountServerEntry 	2 }
     
apAccountServerPortNumber	OBJECT-TYPE
    		SYNTAX		Integer32 (0..65535)
    		MAX-ACCESS	read-write
    		STATUS  	current
    		DESCRIPTION
    			"The UDP port the client is using to send requests to this server."
    			::= { apAccountServerEntry 	3 }
    			
apAccountServerSharedSecret	OBJECT-TYPE
			SYNTAX	OCTET STRING (SIZE(0..20))
			ACCESS	read-write
			STATUS	mandatory
			DESCRIPTION
				"This values indicates the shared key used by the 
				accounting server."
			::= { apAccountServerEntry 4 }

apAccountServerRetransmit	OBJECT-TYPE
    		SYNTAX		Integer32 (1..30)
    		MAX-ACCESS	read-write
    		STATUS  	current
    		DESCRIPTION
    		"The number of times the access point tries to accounting logon access."
  	  		::= { apAccountServerEntry 	5 }

apAccountServerTimeout	OBJECT-TYPE
    		SYNTAX		Integer32 (1..60)
    		MAX-ACCESS	read-write
    		STATUS  	current
    		DESCRIPTION
    		"The number of seconds the access point waits for a reply from the RADIUS
    		  accounting server before it resends the request"
  	  		::= { apAccountServerEntry 	6 }

apFastReKeying OBJECT-TYPE
		SYNTAX  INTEGER {
     						enabled(1),
							disabled(2)
     						}
        MAX-ACCESS  read-write
        STATUS  current
        DESCRIPTION
            "The AP supprt the Fast-rekeying is enabled or disabled. 
   			 Default is disabled."
             ::= { apSecurityMgmt 9 }  
       
apTFTPServerPortNumber	OBJECT-TYPE
   		SYNTAX		Integer32 (0..65535)
   		MAX-ACCESS	read-write
   		STATUS  	current
   		DESCRIPTION
   		"The TFTP Server port."
  		::= { apSecurityMgmt 10 }       
       

apTFTPRetries OBJECT-TYPE
   		SYNTAX		Integer32 (0..65535)
		MAX-ACCESS	read-write
		STATUS		current
		DESCRIPTION
			"The maximum retries number of tftp client in SRAPEE"
		::= { apSecurityMgmt 11 }

apTFTPTimeOutInterval OBJECT-TYPE
   		SYNTAX		Integer32 (0..65535)
		MAX-ACCESS	read-write
		STATUS		current
		DESCRIPTION
			"The maximum time out interval of tftp client in SRAPEE"
		::= { apSecurityMgmt 12 }

apEncryptionTable OBJECT-TYPE
		SYNTAX SEQUENCE OF APEncryptionEntry
		MAX-ACCESS not-accessible
		STATUS current
		DESCRIPTION
			"Conceptual table for Encryption setting of device"
	::= { apSecurityMgmt 13}

apEncryptionEntry OBJECT-TYPE
		SYNTAX APEncryptionEntry
		MAX-ACCESS not-accessible
		STATUS current
		DESCRIPTION
			"An Entry (conceptual row) in the Encryption Table
						
			ifIndex - Each IEEE 802.11 interface is represented by an
			ifEntry. Interface tables in this MIB module are indexed
			by ifIndex."    
		INDEX { ifIndex }
	::= { apEncryptionTable 1 }

APEncryptionEntry ::=
		SEQUENCE { 	apEncryptionMode 		INTEGER,
					apWPAPSKPassPhrase 		OCTET STRING,
					apWEPDefaultKeyID		INTEGER,
					apWEPDefaultKey1		OCTET STRING,
					apWEPDefaultKey2		OCTET STRING,
					apWEPDefaultKey3		OCTET STRING,
					apWEPDefaultKey4		OCTET STRING }
					
apEncryptionMode OBJECT-TYPE
		SYNTAX		INTEGER	{
								none(1),
								wep64b(2),
								wep128b(3),	
								wep152b(4),	
								tkipWPAPSK(5),
								tkipWPAEnterprise(6),
								aesWPAPSK(7),
								aesWPAEnterprise(8)
							}
		MAX-ACCESS	read-write
		STATUS		current
		DESCRIPTION
			"The encryption mode that each IEEE 802.11 Interface(apEncryptionMode.ifIndex) is using.
			Value:  1 = No Encryption
					2 = 64 bit WEP
					3 = 128 bit WEP
					4 = 152 bit WEP
					5 = TKIP using WPA-PSK
					6 = TKIP using WPA-Enterprise
					7 = AES using WPA-PSK
					8 = AES using WPA-Enterprise"
		::=	{ apEncryptionEntry 1 }
		
apWPAPSKPassPhrase	OBJECT-TYPE
		SYNTAX OCTET STRING (SIZE (8..63))
		MAX-ACCESS read-write
		STATUS current
		DESCRIPTION
			"A WPA Pre-Share Key Pass Phrase."
	::= { apEncryptionEntry 2 }

apWEPDefaultKeyID	OBJECT-TYPE
		SYNTAX INTEGER (1..4)
		MAX-ACCESS read-write
		STATUS current
		DESCRIPTION
			"The WEPDefaultKey N currently being used to encrypt data"
	::= { apEncryptionEntry 3 }
	
apWEPDefaultKey1 OBJECT-TYPE
		SYNTAX OCTET STRING  (SIZE (5|13|16))
		MAX-ACCESS read-write
		STATUS current
		DESCRIPTION
			"A WEP default secret key 1 value."
	::= { apEncryptionEntry 4 }
	
apWEPDefaultKey2 OBJECT-TYPE
		SYNTAX OCTET STRING (SIZE (5|13|16))
		MAX-ACCESS read-write
		STATUS current
		DESCRIPTION
			"A WEP default secret key 2 value."
	::= { apEncryptionEntry 5 }

apWEPDefaultKey3 OBJECT-TYPE
		SYNTAX OCTET STRING (SIZE (5|13|16))
		MAX-ACCESS read-write
		STATUS current
		DESCRIPTION
			"A WEP default secret key 3 value."
	::= { apEncryptionEntry 6 }

apWEPDefaultKey4 OBJECT-TYPE
		SYNTAX OCTET STRING (SIZE (5|13|16))
		MAX-ACCESS read-write
		STATUS current
		DESCRIPTION
			"A WEP default secret key 4 value."
	::= { apEncryptionEntry 7 }
-- **********************************************************************
-- * End of Encryption TABLE
-- **********************************************************************

--
--  Notifications
--

radioTransmitStop NOTIFICATION-TYPE
	OBJECTS 	{ ifIndex, apMyMacAddr, apRadioChannel }
	STATUS		current
	DESCRIPTION 
		"The radio has stopped transmitting due to a fault. There may be a jammed channel.  
		The user should change the AP to the different channel or check if there is a RF hardware issue."
	::= { a3Com 0 95 }

radioReceiveStop NOTIFICATION-TYPE
	OBJECTS 	{ ifIndex, apMyMacAddr, apRadioChannel }
	STATUS		current
	DESCRIPTION 
		"The radio has stopped receiving due to a fault. There may be a jammed channel.
		The user should change the AP to the different channel or check if there is a RF hardware issue."
	::= { a3Com 0 96 }

exceedMaxAssociated NOTIFICATION-TYPE
	OBJECTS 	{ ifIndex, apMyMacAddr }
	STATUS		current
	DESCRIPTION 
		"Exceed max 256 Associated clients. No more association of wireless clients allowed.
		The user can disassociate the idle wirless clients."
	::= { a3Com 0 97 }

exceedtThresholdAssociated NOTIFICATION-TYPE
	OBJECTS 	{ ifIndex, apMyMacAddr }
	STATUS		current
	DESCRIPTION 
		"The number of Wireless Clients association reaches the threshold of the AP.
		Please check the MIB object, thresholdAssociated. The default is 200.
		The number of wireless client is more than the value of thresholdAssociated.
		This will affect the performace of the AP."
	::= { a3Com 0 98 }

dslSecurityViolation NOTIFICATION-TYPE
	OBJECTS 	{ ifIndex }
	STATUS		current
	DESCRIPTION 
		"For Wireless Client, User name or password is not correct in Dynamic Security Link database of AP.
		The user can check the AP admin if the account exists on the Dynamic Security Link database"
	::= { a3Com 0 99 }


--
-- managed groups
--
apManufactureInfoGroup 	OBJECT-GROUP
		OBJECTS {
				apModelnumber,
				apSerialnumber,
				apMyMacAddr,
				apFirmwareVer,
				apMfgDate,
				apWebUiVer,
				apProductName,
				apMfgName,
				apHardwareRev
				}
		STATUS		current
		DESCRIPTION "The apManufactureInfo group"
		::= { apConfigMgmtGroups 1 }


apSystemConfigGroup 	OBJECT-GROUP
		OBJECTS {
				apDeviceName,
				apDeviceLoc,
				apHelpFilePath,
				apMyIPAddr,
				apSubnetMask,
				apGatewayIPAddr,
				apAdditionalGatewaysTableLength,
				apAdditionalGatewaysIPAddr,
				apDHCPEnable,
				apStaticIPAddrEnable
				}
		STATUS		current
		DESCRIPTION "The apSystemConfig group"
		::= { apConfigMgmtGroups 2 }

apSNMPInfoGroup 	OBJECT-GROUP
		OBJECTS {
				apSNMPRequests, 
				apSNMPTraps,
				apAllTrapsEnable, 
				apColdBootTrapEnable, 
				apAuthenFailureTrapEnable, 
				apRFTrapEnable,   
				apWarmBootTrapEnable,
				apWCMaxAssocTrapEnable,
				apThresholdAssociatedEnable,
				dslSecurityViolationEnable
				}
		STATUS		current
		DESCRIPTION "The apSNMPInfo group"
		::= { apConfigMgmtGroups 3 }

apRFConfigGroup 	OBJECT-GROUP
		OBJECTS {
				apWlanServiceArea,
				apCountryName,
				apShortPreamble,
				apMaxWCTrigger,
				apWEPAlgorithm,
				apRadioAutoSense,
				apRadioChannel,
				apHighPerformance,
				apTransmitPower,
				apRadioAntenna,
				thresholdAssociated,
				apDataRateMgmt,
				apDataRate5,
				apDataRate11 
				}
		STATUS		current
		DESCRIPTION "The apRFConfig group"
		::= { apConfigMgmtGroups 4 }


apRFStatisticsGroup 	OBJECT-GROUP
		OBJECTS {
				rfTxUcastFrms,			
				rfRxUcastFrms, 
				rfTxBcastFrms, 
				rfRxBcastFrms, 
				rfTxMcastFrms, 
				rfRxMcastFrms, 
				rfTxEncryptFrms, 
				rfRxEncryptFrms, 
				rfTxFragFrms, 
				rfRxFragFrms, 
				rfTxBeacons,  
				rfRxBeacons, 
				rfTxACK,
				rfRxACK, 
				rfTxRTS, 
				rfRxRTS,
				rfCTSFailures,
				rfRxCTS,
				rfTxACKFailures,
				rfTxRetrys,
				rfFCSErrors, 
				rfRxDuplicateFrms,
				rfWEPUndecryptFrms,
				rfWEPICVErrors
				}
		STATUS		current
		DESCRIPTION "The apRFStatistics group"
		::= { apPerformMgmtGroups 1 }

apEtherItfStatGroup 	OBJECT-GROUP
		OBJECTS {			  
				apEtherPacketsIns, 
				apEtherPacketsOuts, 
				apEtherOctetsIns, 
				apEtherOctetsOuts,  
				apEtherPktsInPerSec, 
				apEtherPktsOutPerSec,  
				apEtherOctInPerSec,  
				apEtherOctOutPerSec 
				}
		STATUS		current
		DESCRIPTION "The apEtherInfStat group"
		::= { apPerformMgmtGroups 2 }

apRFItfStatGroup 	OBJECT-GROUP
		OBJECTS {
				apRFFrmsIns, 
				apRFFrmsOuts, 
				apRFOctetsIns, 
				apRFOctetsOuts,  
				apRFFrmsInPerSec, 
				apRFFrmsOutPerSec,  
				apRFOctInPerSec,  
				apRFOctOutPerSec    
				}
		STATUS		current
		DESCRIPTION "The apRFInfStat group"
		::= { apPerformMgmtGroups 3} 

apTrafficMatrixGroup 	OBJECT-GROUP
		OBJECTS {
				apEnetsNPktsToEnets, 			 
				apRFNPktsToEnets, 
				apEnetsNPktsToRF,            	
				apRFNPktsToRF    
				}
		STATUS		current
		DESCRIPTION "The apTrafficMatrix group"
		::= { apPerformMgmtGroups 4} 

apDSPerFreqStatTableGroup 	OBJECT-GROUP
		OBJECTS {
            	rfDSFrequency ,        
		       	rfDSPerFqPktsSents,      
		        rfDSPerFqPktsRcvds ,     
		        rfDSPerFqRetries       
		     	}
        STATUS		current
		DESCRIPTION "The apDSPerFreqStatTable group"
		::= { apPerformMgmtGroups 5} 



apFaultMgmtGroup 	OBJECT-GROUP
		OBJECTS {
				apUpdateTemplateStatus,
				apBackupFileName,  
				apTemplateOperation,
				apRestoreFileName,
				apSyslogDstIpAddressTableLength,
				apSyslogDstIpAddress,
				apSyslogEnable
				}
		STATUS		current
		DESCRIPTION "The apRFStatistics group"
		::= { apFaultMgmtGroups 1 }

apSecurityMgmtGroup 	OBJECT-GROUP
		OBJECTS {
				apACLViolations, 
				apEAPSupport,   
				apAuthServerSupportNumber,
				apKeyServerSupportNumber,
				apAccountServerSupportNumber,  
				apAuthServerIPAddr,
				apAuthServerPortNumber,
				apAuthSharedSecret,
				apAuthServerRetransmit,
    			apAuthServerTimeout,
				apKeyServerIPAddr,
				apKeyServerPortNumber,
				apAccountServerIPAddr,
				apAccountServerPortNumber,
				apAccountSharedSecret,
				apAccountServerRetransmit,
				apAccountServerTimeout,
				apFastReKeying,
				apTFTPServerPortNumber,
				apTFTPRetries,
				apTFTPTimeOutInterval,
				apEncryptionMode,
				apWPAPSKPassPhrase,
				apWEPDefaultKeyID,
				apWEPDefaultKey1,
				apWEPDefaultKey2,
				apWEPDefaultKey3,
				apWEPDefaultKey4
				}
		STATUS		current
		DESCRIPTION "The apSecurityMgmt group"
		::= { apSecurityMgmtGroups 1 }

wcmNotificationGroup NOTIFICATION-GROUP
	NOTIFICATIONS 	{
					radioTransmitStop,
					radioReceiveStop,
					exceedMaxAssociated,
					exceedtThresholdAssociated,
					dslSecurityViolation
					}
	STATUS  current
	DESCRIPTION "The wcm Notifications."
	::= {apEventGroups 1}

END
