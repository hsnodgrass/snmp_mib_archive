-- MIB generated by miftomib version 1.0a
-- Version 5-12-99.01

MYLEXRAID-MIB DEFINITIONS ::= BEGIN

-- Mylex Disk Array Controller

IMPORTS
    OBJECT-TYPE
    FROM RFC-1212
    Counter, enterprises
    FROM RFC1155-SMI
    DisplayString
    FROM RFC1213-MIB;

DmiCounter			::= Counter
DmiInteger			::= INTEGER
DmiDisplaystring	::= DisplayString
DmiDate				::= OCTET STRING (SIZE (28))
DmiComponentIndex	::= INTEGER

mylex               	OBJECT IDENTIFIER ::= {enterprises 1608}
dmtfStd             	OBJECT IDENTIFIER ::= {mylex 1}
dmtfComponents      	OBJECT IDENTIFIER ::= {dmtfStd 1}
dmtfGroups          	OBJECT IDENTIFIER ::= {dmtfComponents 1}

SControllerInformation ::= SEQUENCE {
	a2ControllerNumber                      	DmiInteger,
	a2OperationalState                      	DmiInteger,
	a2FirmwareRevision                      	DmiDisplaystring,
	a2ConfiguredChannels                    	DmiInteger,
	a2ActualChannels                        	DmiInteger,
	a2MaximumLogicalDrives                  	DmiInteger,
	a2MaximumTargetsPerChannel              	DmiInteger,
	a2MaximumTaggedRequests                 	DmiInteger,
	a2MaximumDataTransferSizePerIoRequestInK	DmiInteger,
	a2MaximumConcurrentCommands             	DmiInteger,
	a2RebuildRate                           	DmiInteger,
	a2LogicalSectorSizeInBytes              	DmiInteger,
	a2PhysicalSectorSizeInBytes             	DmiInteger,
	a2CacheLineSizeInBytes                  	DmiInteger,
	a2CacheSizeInMb                         	DmiInteger,
	a2CacheMemoryType                       	DmiInteger,
	a2EpromSizeInKb                         	DmiInteger,
	a2BusType                               	DmiInteger,
	a2ControllerClass                       	DmiInteger,
	a2ControllerModel                       	DmiInteger,
	a2SystemBusNumber                       	DmiInteger,
	a2SlotNumber                            	DmiInteger,
	a2InterruptVectorNumber                 	DmiInteger,
	a2InterruptMode                         	DmiInteger,
	a2NumberOfPhysicalDevices               	DmiInteger,
	a2NumberOfPhysicalDevicesOffLine        	DmiInteger,
	a2NumberOfLogicalDevices                	DmiInteger,
	a2NumberOfLogicalDevicesCritical        	DmiInteger,
	a2NumberOfLogicalDevicesOffLine         	DmiInteger,
	a2FaultManagementType                   	DmiInteger,
	a2ArrayInformation                      	DmiDisplaystring,
	a2LogicalDriveReadRequestsCount         	DmiCounter,
	a2DataReadFromLogicalDrivesInMb         	DmiCounter,
	a2LogicalDriveWriteRequestsCount        	DmiCounter,
	a2DataWrittenToLogicalDrivesInMb        	DmiCounter,
	a2LogicalDrivesReadCacheHitPercentage   	DmiCounter,
	a2PhysicalDriveReadRequestsCount        	DmiCounter,
	a2DataReadFromPhysicalDrivesInMb        	DmiCounter,
	a2PhysicalDriveWriteRequestsCount       	DmiCounter,
	a2DataWrittenToPhysicalDrivesInMb       	DmiCounter,
	a2StorageworksCabinetStatusOnChannel0   	DmiInteger,
	a2StorageworksCabinetStatusOnChannel1   	DmiInteger,
	a2StorageworksCabinetStatusOnChannel2   	DmiInteger,
	a2BatteryBackupUnitStatus               	DmiInteger,
	a2PartnerControllerNumber					DmiCounter,
	a2WWName									DmiDisplaystring
}

tControllerInformation OBJECT-TYPE
	SYNTAX		SEQUENCE OF SControllerInformation
	ACCESS		not-accessible
	STATUS		mandatory
	DESCRIPTION	"This group provides Controller Information."
	::= {dmtfGroups 2}

eControllerInformation OBJECT-TYPE
	SYNTAX		SControllerInformation
	ACCESS		not-accessible
	STATUS		mandatory
	DESCRIPTION	""
	INDEX		{a2ControllerNumber}
	::= {tControllerInformation 1}

a2ControllerNumber OBJECT-TYPE
	SYNTAX		DmiInteger
	ACCESS		read-only
	STATUS		mandatory
	DESCRIPTION	"Controller Number assigned to this controller by the device
driver."
	::= {eControllerInformation 1}

a2OperationalState OBJECT-TYPE
	SYNTAX		INTEGER {
		vFunctional                             	(1),
		vNon-functional                         	(2),
		vNotPresent                             	(128)
	}
	ACCESS		read-only
	STATUS		mandatory
	DESCRIPTION	"Operational state of this controller as seen by the device
driver."
	::= {eControllerInformation 2}

a2FirmwareRevision OBJECT-TYPE
	SYNTAX		DmiDisplaystring
	ACCESS		read-only
	STATUS		mandatory
	DESCRIPTION	"Controller Firmware Revision."
	::= {eControllerInformation 3}

a2ConfiguredChannels OBJECT-TYPE
	SYNTAX		DmiInteger
	ACCESS		read-only
	STATUS		mandatory
	DESCRIPTION	"Number of Channels (SCSI Bus) that are part of controller
configuration."
	::= {eControllerInformation 4}

a2ActualChannels OBJECT-TYPE
	SYNTAX		DmiInteger
	ACCESS		read-only
	STATUS		mandatory
	DESCRIPTION	"Number of Channels (SCSI Bus) that are physically present
on-board the controller."
	::= {eControllerInformation 5}

a2MaximumLogicalDrives OBJECT-TYPE
	SYNTAX		DmiInteger
	ACCESS		read-only
	STATUS		mandatory
	DESCRIPTION	"Maximum number of logical drives that can be configured on
this controller."
	::= {eControllerInformation 6}

a2MaximumTargetsPerChannel OBJECT-TYPE
	SYNTAX		DmiInteger
	ACCESS		read-only
	STATUS		mandatory
	DESCRIPTION	"Maximum Number of SCSI Target IDs supported per SCSI Bus."
	::= {eControllerInformation 7}

a2MaximumTaggedRequests OBJECT-TYPE
	SYNTAX		DmiInteger
	ACCESS		read-only
	STATUS		mandatory
	DESCRIPTION	"Maximum Number of Tagged requests that may be sent to a Hard
disk device by Controller Firmware."
	::= {eControllerInformation 8}

a2MaximumDataTransferSizePerIoRequestInK OBJECT-TYPE
	SYNTAX		DmiInteger
	ACCESS		read-only
	STATUS		mandatory
	DESCRIPTION	"Maximum amount of data that can be transferred per a single
IO request - in KB."
	::= {eControllerInformation 9}

a2MaximumConcurrentCommands OBJECT-TYPE
	SYNTAX		DmiInteger
	ACCESS		read-only
	STATUS		mandatory
	DESCRIPTION	"Maximum number of requests that can be sent to the controller
simultaneouly."
	::= {eControllerInformation 10}

a2RebuildRate OBJECT-TYPE
	SYNTAX		DmiInteger
	ACCESS		read-only
	STATUS		mandatory
	DESCRIPTION	"Value of Rebuild Rate."
	::= {eControllerInformation 11}

a2LogicalSectorSizeInBytes OBJECT-TYPE
	SYNTAX		DmiInteger
	ACCESS		read-only
	STATUS		mandatory
	DESCRIPTION	"Logical Sector Size in Bytes (Default: 512 bytes)."
	::= {eControllerInformation 12}

a2PhysicalSectorSizeInBytes OBJECT-TYPE
	SYNTAX		DmiInteger
	ACCESS		read-only
	STATUS		mandatory
	DESCRIPTION	"Physical Sector Size in Bytes (Default: 512 bytes)."
	::= {eControllerInformation 13}

a2CacheLineSizeInBytes OBJECT-TYPE
	SYNTAX		DmiInteger
	ACCESS		read-only
	STATUS		mandatory
	DESCRIPTION	"Cache Line Size in Bytes."
	::= {eControllerInformation 14}

a2CacheSizeInMb OBJECT-TYPE
	SYNTAX		DmiInteger
	ACCESS		read-only
	STATUS		mandatory
	DESCRIPTION	"Size of Controller Cache Module - in MB."
	::= {eControllerInformation 15}

a2CacheMemoryType OBJECT-TYPE
	SYNTAX		INTEGER {
		vDram                                   	(1),
		vEdram                                  	(2),
		vEdo                                    	(3),
		vDram-parity                            	(65),
		vEdram-parity                           	(66),
		vEdo-parity                             	(67),
		vDram-ecc                               	(129),
		vEdram-ecc                              	(130),
		vEdo-ecc                                	(131),
		vUnknown                                	(255)
	}
	ACCESS		read-only
	STATUS		mandatory
	DESCRIPTION	"Controller Cache Memory Type."
	::= {eControllerInformation 16}

a2EpromSizeInKb OBJECT-TYPE
	SYNTAX		DmiInteger
	ACCESS		read-only
	STATUS		mandatory
	DESCRIPTION	"Size of Controller EPROM Module - in KB."
	::= {eControllerInformation 17}

a2BusType OBJECT-TYPE
	SYNTAX		INTEGER {
		vEisa                                   	(1),
		vMca                                    	(2),
		vPci                                    	(3),
		vVesa                                   	(4),
		vIsa                                    	(5),
		vUnknown                                	(255)
	}
	ACCESS		read-only
	STATUS		mandatory
	DESCRIPTION	"Controller - System Bus Interface Type."
	::= {eControllerInformation 18}

a2ControllerClass OBJECT-TYPE
	SYNTAX		INTEGER {
		vRaid                                   	(1),
		vScsi-scsi                              	(96),
		vHba                                    	(128),
		vUnknown                                	(255)
	}
	ACCESS		read-only
	STATUS		mandatory
	DESCRIPTION	"Controller Class Type."
	::= {eControllerInformation 19}

a2ControllerModel OBJECT-TYPE
	SYNTAX		INTEGER {
		vDac960e                                	(1),
		vDac960m                                	(8),
		vDac960pd                               	(16),
		vDac960pl                               	(17),
		vDac960pdu                              	(18),
		vDac960pe                               	(19),
		vDac960pg                               	(20),
		vDac960pj                               	(21),
		vDac960ptl0                               	(22),
		vDac960pr                               	(23),
		vDac960prl                               	(24),
		vDac960pt                               	(25),
		vDac1164p	                              	(26),
		vDac960ptl1                              	(27),
		vDac960s                                	(96),
		vDac960su                               	(97),
		vDac960sx                               	(98),
		vDac960sf                               	(99),
		vDac960ss                               	(100),
		vDac960fl                               	(101),
		vDac960ll                               	(102),
		vDac960ff                               	(103),
		vFCArray	                               	(104),
		vBt-440                                 	(129),
		vBt-440c                                	(130),
		vBt-445                                 	(131),
		vBt-445c                                	(132),
		vBt-44xc                                	(133),
		vBt-445s                                	(134),
		vBt-640                                 	(136),
		vBt-640a                                	(137),
		vBt-646                                 	(138),
		vBt-646d                                	(139),
		vBt-646s                                	(140),
		vBt-742                                 	(144),
		vBt-742a                                	(145),
		vBt-747                                 	(146),
		vBt-747d                                	(147),
		vBt-747s                                	(148),
		vBt-74xc                                	(149),
		vBt-757                                 	(150),
		vBt-757d                                	(151),
		vBt-757s                                	(152),
		vBt-757cd                               	(153),
		vBt-75xc                                	(154),
		vBt-747c                                	(155),
		vBt-757c                                	(156),
		vBt-540                                 	(160),
		vBt-540c                                	(161),
		vBt-542                                 	(162),
		vBt-542b                                	(163),
		vBt-542c                                	(164),
		vBt-542d                                	(165),
		vBt-545                                 	(166),
		vBt-545c                                	(167),
		vBt-545s                                	(168),
		vBt-54xc                                	(169),
		vBt-946                                 	(176),
		vBt-946c                                	(177),
		vBt-948                                 	(178),
		vBt-948c                                	(179),
		vBt-956                                 	(180),
		vBt-956c                                	(181),
		vBt-958                                 	(182),
		vBt-958c                                	(183),
		vBt-958d                                	(184),
		vBt-956cd                               	(185),
		vBt-958cd                               	(186),
		vBt930                                  	(192),
		vBt932                                  	(193),
		vBt950                                  	(194),
		vBt952                                  	(195),
		vUnknown                                	(255)
	}
	ACCESS		read-only
	STATUS		mandatory
	DESCRIPTION	"Controller Model Type."
	::= {eControllerInformation 20}

a2SystemBusNumber OBJECT-TYPE
	SYNTAX		DmiInteger
	ACCESS		read-only
	STATUS		mandatory
	DESCRIPTION	"System Bus Number, for the bus the controller is interfacing
with. This value is supplied by the Operating system and may not be defined
for all operating systems."
	::= {eControllerInformation 21}

a2SlotNumber OBJECT-TYPE
	SYNTAX		DmiInteger
	ACCESS		read-only
	STATUS		mandatory
	DESCRIPTION	"Slot Number where the controller is physically present. Defined
for EISA and MCA controller only. "
	::= {eControllerInformation 22}

a2InterruptVectorNumber OBJECT-TYPE
	SYNTAX		DmiInteger
	ACCESS		read-only
	STATUS		mandatory
	DESCRIPTION	"Interrupt Vector Number being used by the controller. This
value is a mapped IRQ supplied by Operating System and may not be same as
the actual Interrupt Vector."
	::= {eControllerInformation 23}

a2InterruptMode OBJECT-TYPE
	SYNTAX		INTEGER {
		vEdge                                   	(0),
		vLevel                                  	(1),
		vUnknown                                	(255)
	}
	ACCESS		read-only
	STATUS		mandatory
	DESCRIPTION	"Interrupt Mode - Edge/Level."
	::= {eControllerInformation 24}

a2NumberOfPhysicalDevices OBJECT-TYPE
	SYNTAX		DmiInteger
	ACCESS		read-only
	STATUS		mandatory
	DESCRIPTION	"Number Of Physical Devices detected on this controller."
	::= {eControllerInformation 25}

a2NumberOfPhysicalDevicesOffLine OBJECT-TYPE
	SYNTAX		DmiInteger
	ACCESS		read-only
	STATUS		mandatory
	DESCRIPTION	"Number of Physical Devices, whose operational state is Off
Line."
	::= {eControllerInformation 26}

a2NumberOfLogicalDevices OBJECT-TYPE
	SYNTAX		DmiInteger
	ACCESS		read-only
	STATUS		mandatory
	DESCRIPTION	"Number of Logical Devices currently configured."
	::= {eControllerInformation 27}

a2NumberOfLogicalDevicesCritical OBJECT-TYPE
	SYNTAX		DmiInteger
	ACCESS		read-only
	STATUS		mandatory
	DESCRIPTION	"Number of Logical Devices, whose operational state is Critical."
	::= {eControllerInformation 28}

a2NumberOfLogicalDevicesOffLine OBJECT-TYPE
	SYNTAX		DmiInteger
	ACCESS		read-only
	STATUS		mandatory
	DESCRIPTION	"Number of Logical Devices, whose operational state is Off
Line."
	::= {eControllerInformation 29}

a2FaultManagementType OBJECT-TYPE
	SYNTAX		INTEGER {
		vAemi                                   	(1),
		vOem1                                   	(2),
		vOem2                                   	(4),
		vOem3                                   	(8),
		vConner                                 	(16),
		vSafte                                  	(32),
		vNotPresent                             	(0)
	}
	ACCESS		read-only
	STATUS		mandatory
	DESCRIPTION	"Controller Fault Management Type."
	::= {eControllerInformation 30}

a2ArrayInformation OBJECT-TYPE
	SYNTAX		DmiDisplaystring
	ACCESS		read-only
	STATUS		mandatory
	DESCRIPTION	"Information about Array(s) definition. The information is
provided in Channel-Target combination form."
	::= {eControllerInformation 31}

a2LogicalDriveReadRequestsCount OBJECT-TYPE
	SYNTAX		DmiCounter
	ACCESS		read-only
	STATUS		mandatory
	DESCRIPTION	"Number of Read Requests to Logical Drives."
	::= {eControllerInformation 32}

a2DataReadFromLogicalDrivesInMb OBJECT-TYPE
	SYNTAX		DmiCounter
	ACCESS		read-only
	STATUS		mandatory
	DESCRIPTION	"Amount of Data Read from all Logical Drives - in MB."
	::= {eControllerInformation 33}

a2LogicalDriveWriteRequestsCount OBJECT-TYPE
	SYNTAX		DmiCounter
	ACCESS		read-only
	STATUS		mandatory
	DESCRIPTION	"Number of Write Requests to Logical Drives."
	::= {eControllerInformation 34}

a2DataWrittenToLogicalDrivesInMb OBJECT-TYPE
	SYNTAX		DmiCounter
	ACCESS		read-only
	STATUS		mandatory
	DESCRIPTION	"Amount of data written to all Logical Drives - in MB."
	::= {eControllerInformation 35}

a2LogicalDrivesReadCacheHitPercentage OBJECT-TYPE
	SYNTAX		DmiCounter
	ACCESS		read-only
	STATUS		mandatory
	DESCRIPTION	"Logical Drives Read Data Cache Hit Rate."
	::= {eControllerInformation 36}

a2PhysicalDriveReadRequestsCount OBJECT-TYPE
	SYNTAX		DmiCounter
	ACCESS		read-only
	STATUS		mandatory
	DESCRIPTION	"Number of Read Requests to all physical drives."
	::= {eControllerInformation 37}

a2DataReadFromPhysicalDrivesInMb OBJECT-TYPE
	SYNTAX		DmiCounter
	ACCESS		read-only
	STATUS		mandatory
	DESCRIPTION	"Amount of Data Read from all physical drives - in MB."
	::= {eControllerInformation 38}

a2PhysicalDriveWriteRequestsCount OBJECT-TYPE
	SYNTAX		DmiCounter
	ACCESS		read-only
	STATUS		mandatory
	DESCRIPTION	"Number of Write Requests to all physical drives on this controll
r."
	::= {eControllerInformation 39}

a2DataWrittenToPhysicalDrivesInMb OBJECT-TYPE
	SYNTAX		DmiCounter
	ACCESS		read-only
	STATUS		mandatory
	DESCRIPTION	"Amount of data written all physical drives on this controller-
in MB."
	::= {eControllerInformation 40}

a2StorageworksCabinetStatusOnChannel0 OBJECT-TYPE
	SYNTAX		INTEGER {
		vOk                                     	(1),
		vNotOk                                  	(2),
		vNotPresent                             	(3)
	}
	ACCESS		read-only
	STATUS		mandatory
	DESCRIPTION	"StorageWorks Cabinet Status on Channel 0"
	::= {eControllerInformation 41}

a2StorageworksCabinetStatusOnChannel1 OBJECT-TYPE
	SYNTAX		INTEGER {
		vOk                                     	(1),
		vNotOk                                  	(2),
		vNotPresent                             	(3)
	}
	ACCESS		read-only
	STATUS		mandatory
	DESCRIPTION	"StorageWorks Cabinet Status on Channel 1"
	::= {eControllerInformation 42}

a2StorageworksCabinetStatusOnChannel2 OBJECT-TYPE
	SYNTAX		INTEGER {
		vOk                                     	(1),
		vNotOk                                  	(2),
		vNotPresent                             	(3)
	}
	ACCESS		read-only
	STATUS		mandatory
	DESCRIPTION	"StorageWorks Cabinet Status on Channel 2"
	::= {eControllerInformation 43}

a2BatteryBackupUnitStatus OBJECT-TYPE
	SYNTAX		INTEGER {
		vNotPresent                             	(0),
		vPresent                                	(1)
	}
	ACCESS		read-only
	STATUS		mandatory
	DESCRIPTION	"Battery Backup Unit Status."
	::= {eControllerInformation 44}

a2PartnerControllerNumber OBJECT-TYPE
	SYNTAX		DmiCounter
	ACCESS		read-only
	STATUS		mandatory
	DESCRIPTION	"Dual Active Partner Controller Number"
	::= {eControllerInformation 45}

a2WWName OBJECT-TYPE
	SYNTAX		DmiDisplaystring
	ACCESS		read-only
	STATUS		mandatory
	DESCRIPTION	"Controller World-Wide Name"
	::= {eControllerInformation 46}

SLogicalDriveInformation ::= SEQUENCE {
	a3ControllerNumber                      	DmiInteger,
	a3LogicalDriveNumber                    	DmiInteger,
	a3OperationalState                      	DmiInteger,
	a3RaidLevel		                          	DmiInteger,
	a3WritePolicy                           	DmiInteger,
	a3SizeInMb                              	DmiInteger,
	a3PhysicalSizeInMb                      	DmiInteger,
	a3StripeSizeInBytes                     	DmiInteger,
	a3PhysicalDriveMap                      	DmiDisplaystring,
	a3ArrayList                             	DmiDisplaystring,
	a3RaidLevelString                          	DmiDisplaystring
}

tLogicalDriveInformation OBJECT-TYPE
	SYNTAX		SEQUENCE OF SLogicalDriveInformation
	ACCESS		not-accessible
	STATUS		mandatory
	DESCRIPTION	"Provides information about Logical Drive Configuration."
	::= {dmtfGroups 3}

eLogicalDriveInformation OBJECT-TYPE
	SYNTAX		SLogicalDriveInformation
	ACCESS		not-accessible
	STATUS		mandatory
	DESCRIPTION	""
	INDEX		{a3ControllerNumber, a3LogicalDriveNumber}
	::= {tLogicalDriveInformation 1}

a3ControllerNumber OBJECT-TYPE
	SYNTAX		DmiInteger
	ACCESS		read-only
	STATUS		mandatory
	DESCRIPTION	"Controller Number - used as a key."
	::= {eLogicalDriveInformation 1}

a3LogicalDriveNumber OBJECT-TYPE
	SYNTAX		DmiInteger
	ACCESS		read-only
	STATUS		mandatory
	DESCRIPTION	"Logical Drive Number - used as a Key."
	::= {eLogicalDriveInformation 2}

a3OperationalState OBJECT-TYPE
	SYNTAX		INTEGER {
		vOnline                                 	(3),
		vCritical                               	(4),
		vOffline                                	(255),
		vNotPresent                             	(128)
	}
	ACCESS		read-only
	STATUS		mandatory
	DESCRIPTION	"Logical Drive Operational State."
	::= {eLogicalDriveInformation 3}

a3RaidLevel OBJECT-TYPE
	SYNTAX		INTEGER {
		vRaid0									(0),
		vRaid1									(1),
		vRaid3									(3),
		vRaid5									(5),
		vRaid0p1								(6),
		vJBOD									(7)
	}
	ACCESS		read-only
	STATUS		mandatory
	DESCRIPTION	"RAID Level associated with Logical Drive."
	::= {eLogicalDriveInformation 4}

a3WritePolicy OBJECT-TYPE
	SYNTAX		INTEGER {
		vWriteThru                              	(0),
		vWriteBack                              	(128)
	}
	ACCESS		read-only
	STATUS		mandatory
	DESCRIPTION	"Write Cache Policy associated with Logical Drive."
	::= {eLogicalDriveInformation 5}

a3SizeInMb OBJECT-TYPE
	SYNTAX		DmiInteger
	ACCESS		read-only
	STATUS		mandatory
	DESCRIPTION	"Logical Drive Size - in MB."
	::= {eLogicalDriveInformation 6}

a3PhysicalSizeInMb OBJECT-TYPE
	SYNTAX		DmiInteger
	ACCESS		read-only
	STATUS		mandatory
	DESCRIPTION	"Total physical capacity used by this Logical Drive - in MB."
	::= {eLogicalDriveInformation 7}

a3StripeSizeInBytes OBJECT-TYPE
	SYNTAX		DmiInteger
	ACCESS		read-only
	STATUS		mandatory
	DESCRIPTION	"Stripe size associated with Logical Drive. Valid for RAID
Levels 0, 5 and 6 only. Value is specifed in bytes."
	::= {eLogicalDriveInformation 8}

a3PhysicalDriveMap OBJECT-TYPE
	SYNTAX		DmiDisplaystring
	ACCESS		read-only
	STATUS		mandatory
	DESCRIPTION	"List of all physical drives that make up this Logical Drive.
The information is provided in Channel-Target combination form."
	::= {eLogicalDriveInformation 9}

a3ArrayList OBJECT-TYPE
	SYNTAX		DmiDisplaystring
	ACCESS		read-only
	STATUS		mandatory
	DESCRIPTION	"List of Arrays, this logical drive spans across. "
	::= {eLogicalDriveInformation 10}

a3RaidLevelString OBJECT-TYPE
	SYNTAX		DmiDisplaystring
	ACCESS		read-only
	STATUS		mandatory
	DESCRIPTION	"RAID Level associated with Logical Drive."
	::= {eLogicalDriveInformation 11}

SPhysicalDeviceInformation ::= SEQUENCE {
	a4ControllerNumber                      	DmiInteger,
	a4ScsiBusId                             	DmiInteger,
	a4ScsiTargetId                          	DmiInteger,
	a4ScsiLunId                             	DmiInteger,
	a4OperationalState                      	DmiInteger,
	a4VendorId                              	DmiDisplaystring,
	a4ProductId                             	DmiDisplaystring,
	a4ProductRevisionLevel                  	DmiDisplaystring,
	a4SizeInMb                              	DmiInteger,
	a4DeviceType                            	DmiInteger,
	a4SoftErrorsCount                       	DmiCounter,
	a4HardErrorsCount                       	DmiCounter,
	a4ParityErrorsCount                     	DmiCounter,
	a4MiscErrorsCount                       	DmiCounter,
	a4ArrayList                             	DmiDisplaystring,
	a4LogicalDriveList                      	DmiDisplaystring
}

tPhysicalDeviceInformation OBJECT-TYPE
	SYNTAX		SEQUENCE OF SPhysicalDeviceInformation
	ACCESS		not-accessible
	STATUS		mandatory
	DESCRIPTION	"SCSI Physical Device Information."
	::= {dmtfGroups 4}

ePhysicalDeviceInformation OBJECT-TYPE
	SYNTAX		SPhysicalDeviceInformation
	ACCESS		not-accessible
	STATUS		mandatory
	DESCRIPTION	""
	INDEX		{a4ControllerNumber, a4ScsiBusId, a4ScsiTargetId}
	::= {tPhysicalDeviceInformation 1}

a4ControllerNumber OBJECT-TYPE
	SYNTAX		DmiInteger
	ACCESS		read-only
	STATUS		mandatory
	DESCRIPTION	"Controller Number - used as a key"
	::= {ePhysicalDeviceInformation 1}

a4ScsiBusId OBJECT-TYPE
	SYNTAX		DmiInteger
	ACCESS		read-only
	STATUS		mandatory
	DESCRIPTION	"SCSI Channel Number - used as a key"
	::= {ePhysicalDeviceInformation 2}

a4ScsiTargetId OBJECT-TYPE
	SYNTAX		DmiInteger
	ACCESS		read-only
	STATUS		mandatory
	DESCRIPTION	"SCSI Physical Device Target Id - used as a key"
	::= {ePhysicalDeviceInformation 3}

a4ScsiLunId OBJECT-TYPE
	SYNTAX		DmiInteger
	ACCESS		read-only
	STATUS		mandatory
	DESCRIPTION	"SCSI LUN of Physical Device."
	::= {ePhysicalDeviceInformation 4}

a4OperationalState OBJECT-TYPE
	SYNTAX		INTEGER {
		vDead                                   	(0),
		vRebuilding                             	(2),
		vRebuildCancelled                       	(130),
		vOnline                                 	(3),
		vHotspare                               	(16),
		vPresent                                	(5),
		vNotPresent                             	(6)
	}
	ACCESS		read-only
	STATUS		mandatory
	DESCRIPTION	"SCSI Physical Device State."
	::= {ePhysicalDeviceInformation 5}

a4VendorId OBJECT-TYPE
	SYNTAX		DmiDisplaystring
	ACCESS		read-only
	STATUS		mandatory
	DESCRIPTION	"Physical Device Vendor Id - from SCSI Inquiry Info."
	::= {ePhysicalDeviceInformation 6}

a4ProductId OBJECT-TYPE
	SYNTAX		DmiDisplaystring
	ACCESS		read-only
	STATUS		mandatory
	DESCRIPTION	"Physical Device Product Id - from SCSI Inquiry Info."
	::= {ePhysicalDeviceInformation 7}

a4ProductRevisionLevel OBJECT-TYPE
	SYNTAX		DmiDisplaystring
	ACCESS		read-only
	STATUS		mandatory
	DESCRIPTION	"Physical Device Product Revision Level - from SCSI Inquiry
Info."
	::= {ePhysicalDeviceInformation 8}

a4SizeInMb OBJECT-TYPE
	SYNTAX		DmiInteger
	ACCESS		read-only
	STATUS		mandatory
	DESCRIPTION	"Size in MB - from SCSI Read Capacity Data."
	::= {ePhysicalDeviceInformation 9}

a4DeviceType OBJECT-TYPE
	SYNTAX		INTEGER {
		vFixedDrive                             	(0),
		vTape                                   	(1),
		vPrinter                                	(2),
		vProcessor                              	(3),
		vWorm                                   	(4),
		vCdrom                                  	(5),
		vScanner                                	(6),
		vMo                                     	(7),
		vChanger                                	(8),
		vCommunications                         	(9),
		vGraphics-0                             	(10),
		vGraphics-1                             	(11),
		vReserved-0                             	(12),
		vReserved-1                             	(13),
		vReserved-2                             	(14),
		vReserved-3                             	(15),
		vReserved-4                             	(16),
		vReserved-5                             	(17),
		vReserved-6                             	(18),
		vReserved-7                             	(19),
		vReserved-8                             	(20),
		vReserved-9                             	(21),
		vReserved-10                            	(22),
		vReserved-11                            	(23),
		vReserved-12                            	(24),
		vReserved-13                            	(25),
		vReserved-14                            	(26),
		vReserved-15                            	(27),
		vReserved-16                            	(28),
		vReserved-17                            	(29),
		vReserved-18                            	(30),
		vUnknown                                	(31),
		vScsiHostBusAdapter                     	(199)
	}
	ACCESS		read-only
	STATUS		mandatory
	DESCRIPTION	"SCSI Device Type - from SCSI Inquiry Information."
	::= {ePhysicalDeviceInformation 10}

a4SoftErrorsCount OBJECT-TYPE
	SYNTAX		DmiCounter
	ACCESS		read-only
	STATUS		mandatory
	DESCRIPTION	"Number of Soft Errors."
	::= {ePhysicalDeviceInformation 11}

a4HardErrorsCount OBJECT-TYPE
	SYNTAX		DmiCounter
	ACCESS		read-only
	STATUS		mandatory
	DESCRIPTION	"Number of Hard Errors."
	::= {ePhysicalDeviceInformation 12}

a4ParityErrorsCount OBJECT-TYPE
	SYNTAX		DmiCounter
	ACCESS		read-only
	STATUS		mandatory
	DESCRIPTION	"Number of Parity Errors."
	::= {ePhysicalDeviceInformation 13}

a4MiscErrorsCount OBJECT-TYPE
	SYNTAX		DmiCounter
	ACCESS		read-only
	STATUS		mandatory
	DESCRIPTION	"Number of Misc Errors."
	::= {ePhysicalDeviceInformation 14}

a4ArrayList OBJECT-TYPE
	SYNTAX		DmiDisplaystring
	ACCESS		read-only
	STATUS		mandatory
	DESCRIPTION	"List Of Arrays, this physical drive is part of."
	::= {ePhysicalDeviceInformation 15}

a4LogicalDriveList OBJECT-TYPE
	SYNTAX		DmiDisplaystring
	ACCESS		read-only
	STATUS		mandatory
	DESCRIPTION	"List of Logical Drives that depend on this physical drive."
	::= {ePhysicalDeviceInformation 16}

SMylexDacManagementSoftware ::= SEQUENCE {
	a5ManagementSoftwareRevision            	DmiDisplaystring,
	a5ManagementSoftwareBuildDate           	DmiDisplaystring,
	a5MylexDacDeviceDriverRevision          	DmiDisplaystring,
	a5MylexDacDeviceDriverBuildDate         	DmiDisplaystring,
	a5GamDriverRevision                     	DmiDisplaystring,
	a5GamDriverBuildDate                    	DmiDisplaystring
}

tMylexDacManagementSoftware OBJECT-TYPE
	SYNTAX		SEQUENCE OF SMylexDacManagementSoftware
	ACCESS		not-accessible
	STATUS		mandatory
	DESCRIPTION	"MDAC DAC Management Software Version Information."
	::= {dmtfGroups 5}

eMylexDacManagementSoftware OBJECT-TYPE
	SYNTAX		SMylexDacManagementSoftware
	ACCESS		not-accessible
	STATUS		mandatory
	DESCRIPTION	""
	::= {tMylexDacManagementSoftware 1}

a5ManagementSoftwareRevision OBJECT-TYPE
	SYNTAX		DmiDisplaystring
	ACCESS		read-only
	STATUS		mandatory
	DESCRIPTION	"Mylex DAC Management Software Revision Information."
	::= {eMylexDacManagementSoftware 1}

a5ManagementSoftwareBuildDate OBJECT-TYPE
	SYNTAX		DmiDisplaystring
	ACCESS		read-only
	STATUS		mandatory
	DESCRIPTION	"Mylex DAC Management Software Build Date Information - month/dat
/year format."
	::= {eMylexDacManagementSoftware 2}

a5MylexDacDeviceDriverRevision OBJECT-TYPE
	SYNTAX		DmiDisplaystring
	ACCESS		read-only
	STATUS		mandatory
	DESCRIPTION	"Mylex DAC Device driver Revision Information."
	::= {eMylexDacManagementSoftware 3}

a5MylexDacDeviceDriverBuildDate OBJECT-TYPE
	SYNTAX		DmiDisplaystring
	ACCESS		read-only
	STATUS		mandatory
	DESCRIPTION	"Mylex DAC Device Driver Build Date Information - month/date/year
format."
	::= {eMylexDacManagementSoftware 4}

a5GamDriverRevision OBJECT-TYPE
	SYNTAX		DmiDisplaystring
	ACCESS		read-only
	STATUS		mandatory
	DESCRIPTION	"Mylex DAC GAM Driver Revision Information."
	::= {eMylexDacManagementSoftware 5}

a5GamDriverBuildDate OBJECT-TYPE
	SYNTAX		DmiDisplaystring
	ACCESS		read-only
	STATUS		mandatory
	DESCRIPTION	"Mylex DAC GAM Driver Build Date Information - date/month/year
format."
	::= {eMylexDacManagementSoftware 6}

SLogicalDriveStatistics ::= SEQUENCE {
	a6ControllerNumber                      	DmiInteger,
	a6LogicalDriveNumber                    	DmiInteger,
	a6ReadRequestsCount                     	DmiCounter,
	a6DataReadInMb                          	DmiCounter,
	a6WriteRequestsCount                    	DmiCounter,
	a6DataWrittenInMb                       	DmiCounter,
	a6ReadCacheHitPercentage                	DmiCounter
}

tLogicalDriveStatistics OBJECT-TYPE
	SYNTAX		SEQUENCE OF SLogicalDriveStatistics
	ACCESS		not-accessible
	STATUS		mandatory
	DESCRIPTION	"Logical Drive Performance Statistics"
	::= {dmtfGroups 6}

eLogicalDriveStatistics OBJECT-TYPE
	SYNTAX		SLogicalDriveStatistics
	ACCESS		not-accessible
	STATUS		mandatory
	DESCRIPTION	""
	INDEX		{a6ControllerNumber, a6LogicalDriveNumber}
	::= {tLogicalDriveStatistics 1}

a6ControllerNumber OBJECT-TYPE
	SYNTAX		DmiInteger
	ACCESS		read-only
	STATUS		mandatory
	DESCRIPTION	"Controller Number - used as a key."
	::= {eLogicalDriveStatistics 1}

a6LogicalDriveNumber OBJECT-TYPE
	SYNTAX		DmiInteger
	ACCESS		read-only
	STATUS		mandatory
	DESCRIPTION	"Logical Drive Number - used as a key."
	::= {eLogicalDriveStatistics 2}

a6ReadRequestsCount OBJECT-TYPE
	SYNTAX		DmiCounter
	ACCESS		read-only
	STATUS		mandatory
	DESCRIPTION	"Number of Read Requests."
	::= {eLogicalDriveStatistics 3}

a6DataReadInMb OBJECT-TYPE
	SYNTAX		DmiCounter
	ACCESS		read-only
	STATUS		mandatory
	DESCRIPTION	"Amount of Data Read from this logical drive- in MB."
	::= {eLogicalDriveStatistics 4}

a6WriteRequestsCount OBJECT-TYPE
	SYNTAX		DmiCounter
	ACCESS		read-only
	STATUS		mandatory
	DESCRIPTION	"Number of Write Requests."
	::= {eLogicalDriveStatistics 5}

a6DataWrittenInMb OBJECT-TYPE
	SYNTAX		DmiCounter
	ACCESS		read-only
	STATUS		mandatory
	DESCRIPTION	"Amount of data written - in MB."
	::= {eLogicalDriveStatistics 6}

a6ReadCacheHitPercentage OBJECT-TYPE
	SYNTAX		DmiCounter
	ACCESS		read-only
	STATUS		mandatory
	DESCRIPTION	"Read Cache Hit Rate."
	::= {eLogicalDriveStatistics 7}

SPhysicalDriveStatistics ::= SEQUENCE {
	a7ControllerNumber                      	DmiInteger,
	a7ScsiBusId                             	DmiInteger,
	a7ScsiTargetId                          	DmiInteger,
	a7ScsiLun                               	DmiInteger,
	a7ReadRequestsCount                     	DmiCounter,
	a7DataReadInMb                          	DmiCounter,
	a7WriteRequestsCount                    	DmiCounter,
	a7DataWrittenInMb                       	DmiCounter
}

tPhysicalDriveStatistics OBJECT-TYPE
	SYNTAX		SEQUENCE OF SPhysicalDriveStatistics
	ACCESS		not-accessible
	STATUS		mandatory
	DESCRIPTION	"Physical Drive Performance Statistics"
	::= {dmtfGroups 7}

ePhysicalDriveStatistics OBJECT-TYPE
	SYNTAX		SPhysicalDriveStatistics
	ACCESS		not-accessible
	STATUS		mandatory
	DESCRIPTION	""
	INDEX		{a7ControllerNumber, a7ScsiBusId, a7ScsiTargetId}
	::= {tPhysicalDriveStatistics 1}

a7ControllerNumber OBJECT-TYPE
	SYNTAX		DmiInteger
	ACCESS		read-only
	STATUS		mandatory
	DESCRIPTION	"Controller Number - used as a key."
	::= {ePhysicalDriveStatistics 1}

a7ScsiBusId OBJECT-TYPE
	SYNTAX		DmiInteger
	ACCESS		read-only
	STATUS		mandatory
	DESCRIPTION	"SCSI Channel Number - used as a key."
	::= {ePhysicalDriveStatistics 2}

a7ScsiTargetId OBJECT-TYPE
	SYNTAX		DmiInteger
	ACCESS		read-only
	STATUS		mandatory
	DESCRIPTION	"SCSI Target Device Id - used as a key."
	::= {ePhysicalDriveStatistics 3}

a7ScsiLun OBJECT-TYPE
	SYNTAX		DmiInteger
	ACCESS		read-only
	STATUS		mandatory
	DESCRIPTION	"SCSI Lun of Physical Device."
	::= {ePhysicalDriveStatistics 4}

a7ReadRequestsCount OBJECT-TYPE
	SYNTAX		DmiCounter
	ACCESS		read-only
	STATUS		mandatory
	DESCRIPTION	"Number of Read Requests."
	::= {ePhysicalDriveStatistics 5}

a7DataReadInMb OBJECT-TYPE
	SYNTAX		DmiCounter
	ACCESS		read-only
	STATUS		mandatory
	DESCRIPTION	"Amount of Data Read - in MB."
	::= {ePhysicalDriveStatistics 6}

a7WriteRequestsCount OBJECT-TYPE
	SYNTAX		DmiCounter
	ACCESS		read-only
	STATUS		mandatory
	DESCRIPTION	"Number of Write Requests."
	::= {ePhysicalDriveStatistics 7}

a7DataWrittenInMb OBJECT-TYPE
	SYNTAX		DmiCounter
	ACCESS		read-only
	STATUS		mandatory
	DESCRIPTION	"Amount of data written - in MB."
	::= {ePhysicalDriveStatistics 8}

SFaultManagementCabinetInformation ::= SEQUENCE {
	a8ControllerNumber                      	DmiInteger,
	a8ScsiBusId                             	DmiInteger,
	a8CabinetNumber                         	DmiInteger,
	a8ScsiTargetId                          	DmiInteger,
	a8ScsiLun                               	DmiInteger,
	a8CabinetType                           	DmiInteger,
	a8NumberOfFans                          	DmiInteger,
	a8NumberOfPowerSupplyUnits              	DmiInteger,
	a8NumberOfHeatSensors                   	DmiInteger,
	a8NumberOfDriveSlots                    	DmiInteger,
	a8NumberOfDoorLocks                     	DmiInteger,
	a8NumberOfSpeakers                      	DmiInteger,
	a8NumberOfFansCritical                  	DmiInteger,
	a8NumberOfPowerSupplyUnitsCritical      	DmiInteger,
	a8NumberOfHeatSensorsCritical           	DmiInteger,
	a8NumberOfFansFailed                    	DmiInteger,
	a8NumberOfPowerSupplyUnitsFailed        	DmiInteger,
	a8NumberOfHeatSensorsFailed             	DmiInteger
}

tFaultManagementCabinetInformation OBJECT-TYPE
	SYNTAX		SEQUENCE OF SFaultManagementCabinetInformation
	ACCESS		not-accessible
	STATUS		mandatory
	DESCRIPTION	"Fault Management Cabinet Information."
	::= {dmtfGroups 8}

eFaultManagementCabinetInformation OBJECT-TYPE
	SYNTAX		SFaultManagementCabinetInformation
	ACCESS		not-accessible
	STATUS		mandatory
	DESCRIPTION	""
	INDEX		{a8ControllerNumber, a8ScsiBusId, a8CabinetNumber}
	::= {tFaultManagementCabinetInformation 1}

a8ControllerNumber OBJECT-TYPE
	SYNTAX		DmiInteger
	ACCESS		read-only
	STATUS		mandatory
	DESCRIPTION	"Controller Number - used as a key."
	::= {eFaultManagementCabinetInformation 1}

a8ScsiBusId OBJECT-TYPE
	SYNTAX		DmiInteger
	ACCESS		read-only
	STATUS		mandatory
	DESCRIPTION	"SCSI Channel Number - used as a key."
	::= {eFaultManagementCabinetInformation 2}

a8CabinetNumber OBJECT-TYPE
	SYNTAX		DmiInteger
	ACCESS		read-only
	STATUS		mandatory
	DESCRIPTION	"Cabinet Number - used as a key."
	::= {eFaultManagementCabinetInformation 3}

a8ScsiTargetId OBJECT-TYPE
	SYNTAX		DmiInteger
	ACCESS		read-only
	STATUS		mandatory
	DESCRIPTION	"SCSI Target Device Id."
	::= {eFaultManagementCabinetInformation 4}

a8ScsiLun OBJECT-TYPE
	SYNTAX		DmiInteger
	ACCESS		read-only
	STATUS		mandatory
	DESCRIPTION	"SCSI Lun of Physical Device."
	::= {eFaultManagementCabinetInformation 5}

a8CabinetType OBJECT-TYPE
	SYNTAX		INTEGER {
		vConnerCr-6                             	(1),
		vConnerSmartCabinet                     	(2),
		vSafte                                  	(3),
		vUnknown                                	(255)
	}
	ACCESS		read-only
	STATUS		mandatory
	DESCRIPTION	"Fault Management Cabinet Type - Conner CR6/Conner Smart/SAFTE."
	::= {eFaultManagementCabinetInformation 6}

a8NumberOfFans OBJECT-TYPE
	SYNTAX		DmiInteger
	ACCESS		read-only
	STATUS		mandatory
	DESCRIPTION	"Number of Fans housed inside the cabinet."
	::= {eFaultManagementCabinetInformation 7}

a8NumberOfPowerSupplyUnits OBJECT-TYPE
	SYNTAX		DmiInteger
	ACCESS		read-only
	STATUS		mandatory
	DESCRIPTION	"Number of Power Supply Units."
	::= {eFaultManagementCabinetInformation 8}

a8NumberOfHeatSensors OBJECT-TYPE
	SYNTAX		DmiInteger
	ACCESS		read-only
	STATUS		mandatory
	DESCRIPTION	"Number of Heat Sensors."
	::= {eFaultManagementCabinetInformation 9}

a8NumberOfDriveSlots OBJECT-TYPE
	SYNTAX		DmiInteger
	ACCESS		read-only
	STATUS		mandatory
	DESCRIPTION	"Number of Drive Slots."
	::= {eFaultManagementCabinetInformation 10}

a8NumberOfDoorLocks OBJECT-TYPE
	SYNTAX		DmiInteger
	ACCESS		read-only
	STATUS		mandatory
	DESCRIPTION	"Number of Door Locks."
	::= {eFaultManagementCabinetInformation 11}

a8NumberOfSpeakers OBJECT-TYPE
	SYNTAX		DmiInteger
	ACCESS		read-only
	STATUS		mandatory
	DESCRIPTION	"Number of Speakers."
	::= {eFaultManagementCabinetInformation 12}

a8NumberOfFansCritical OBJECT-TYPE
	SYNTAX		DmiInteger
	ACCESS		read-only
	STATUS		mandatory
	DESCRIPTION	"Number of Fans in Critical State."
	::= {eFaultManagementCabinetInformation 13}

a8NumberOfPowerSupplyUnitsCritical OBJECT-TYPE
	SYNTAX		DmiInteger
	ACCESS		read-only
	STATUS		mandatory
	DESCRIPTION	"Number of Power Supply units in critical state."
	::= {eFaultManagementCabinetInformation 14}

a8NumberOfHeatSensorsCritical OBJECT-TYPE
	SYNTAX		DmiInteger
	ACCESS		read-only
	STATUS		mandatory
	DESCRIPTION	"Number of Heat Sensors in critical state."
	::= {eFaultManagementCabinetInformation 15}

a8NumberOfFansFailed OBJECT-TYPE
	SYNTAX		DmiInteger
	ACCESS		read-only
	STATUS		mandatory
	DESCRIPTION	"Number of Fans in Failed State."
	::= {eFaultManagementCabinetInformation 16}

a8NumberOfPowerSupplyUnitsFailed OBJECT-TYPE
	SYNTAX		DmiInteger
	ACCESS		read-only
	STATUS		mandatory
	DESCRIPTION	"Number of Power Supply units in Failed state."
	::= {eFaultManagementCabinetInformation 17}

a8NumberOfHeatSensorsFailed OBJECT-TYPE
	SYNTAX		DmiInteger
	ACCESS		read-only
	STATUS		mandatory
	DESCRIPTION	"Number of Heat Sensors in Failed state."
	::= {eFaultManagementCabinetInformation 18}

SMylexRaidEventInformation ::= SEQUENCE {
	a9EventTableIndex                       	DmiInteger,
	a9EventCode                             	DmiInteger,
	a9EventTimeStamp                        	DmiInteger,
	a9ControllerNumber                      	DmiInteger,
	a9ChannelNumber                         	DmiInteger,
	a9TargetNumber                          	DmiInteger,
	a9LunNumber                             	DmiInteger,
	a9LogicalDriveNumber                    	DmiInteger,
	a9FmtCabinetNumber                      	DmiInteger,
	a9FanUnitNumber                         	DmiInteger,
	a9PowerSupplyUnitNumber                 	DmiInteger,
	a9HeatSensorUnitNumber                  	DmiInteger
}

tMylexRaidEventInformation OBJECT-TYPE
	SYNTAX		SEQUENCE OF SMylexRaidEventInformation
	ACCESS		not-accessible
	STATUS		mandatory
	DESCRIPTION	"Event Information for Mylex RAID events."
	::= {dmtfGroups 9}

eMylexRaidEventInformation OBJECT-TYPE
	SYNTAX		SMylexRaidEventInformation
	ACCESS		not-accessible
	STATUS		mandatory
	DESCRIPTION	""
	INDEX		{a9EventTableIndex}
	::= {tMylexRaidEventInformation 1}

a9EventTableIndex OBJECT-TYPE
	SYNTAX		DmiInteger
	ACCESS		read-only
	STATUS		mandatory
	DESCRIPTION	"Index to the event table. A maximum of 256 events can be
stored in the event table."
	::= {eMylexRaidEventInformation 1}

a9EventCode OBJECT-TYPE
	SYNTAX		INTEGER {
		vOperationalStateOfPhysicalDeviceHasChan	(1),
		vOperationalStateOfPhysicalDeviceHasCha1	(2),
		vThePhysicalDeviceHasSomeErrors         	(3),
		vThePhysicalDeviceIsGoingToFail         	(4),
		vAnAutoRebuildOperationStartedOnThisPhys	(5),
		vAManualRebuildOperationStartedOnThisPhy	(6),
		vAManualOrAutoRebuildOperationHasComplet	(7),
		vAManualOrAutoRebuildOperationHasBeenCan	(8),
		vAManualOrAutoRebuildOperationHasResulte	(9),
		vAManualOrAutoRebuildOperationHasResult1	(10),
		vAManualOrAutoRebuildOperationHasResult2	(11),
		vTheOperationalStateOfPhysicalDeviceHasC	(12),
		vForTheFirstTimeGamMonitorFindsThisPhysi	(13),
		vAPreviouslyFoundPhysicalDeviceDidNotRes	(14),
		vAPhysicalDeviceThatIsNotPartOfCurrentDa	(15),
		vExpandCapacityOperationStartedOnThisPhy	(16),
		vExpandCapacityOperationDoneOnThisPhysic	(17),
		vExpandCapacityOperationResultedInErrorO	(18),
		vCommandTimed-outOnThisPhysicalDrive    	(19),
		vACommandSentToThisPhysicalDeviceHasBeen	(20),
		vACommandIsBeingRetriedOnThisPhysicalDri	(21),
		vParityErrorReportedOnThisPhysicalDrive 	(22),
		vSoftErrorReportedOnThisPhysicalDrive   	(23),
		vMiscellaneousErrorReportedOnThisPhysica	(24),
		vPhysicalDeviceIsReset                  	(25),
		vPhysicalDeviceIsConfiguredAsActiveSpare	(26),
		vPhysicalDeviceIsConfiguredAsWarmSpare  	(27),
		vRequestSenseDataAvailableForThisPhysica	(28),
		vConsistencyCheckOperationStartedSuccess	(128),
		vTheConsistencyCheckOperationThatWasInPr	(129),
		vAnOn-goingConsistencyCheckOperationOnTh	(130),
		vAnOn-goingConsistencyCheckOperationResu	(131),
		vAnOn-goingConsistencyCheckOperationRes1	(132),
		vAnOn-goingConsistencyCheckOperationRes2	(133),
		vOperationalStateOfLogicalDriveChangedFr	(134),
		vOperationalStateOfLogicalDriveChangedF1	(135),
		vOperationalStateOfLogicalDriveChangedF2	(136),
		vAnAutomaticRebuildOperationHasStarted  	(137),
		vAManualRebuildOperationHasStarted      	(138),
		vAnOn-goingAutoOrManualRebuildOperationH	(139),
		vAnOn-goingAutoOrManualRebuildOperation1	(140),
		vAnOn-goingAutoOrManualRebuildOperation2	(141),
		vAnOn-goingAutoOrManualRebuildOperationR	(142),
		vAnOn-goingAutoOrManualRebuildOperation3	(143),
		vInitializationOperationStartedSuccessfu	(144),
		vInitializationOperationCompletedSuccess	(145),
		vInitializationOperationCanceled        	(146),
		vInitializationOperationFailedBecauseThe	(147),
		vForTheFirstTimeGamEventMonitorFindsThis	(148),
		vAPreviouslyConfiguredLogicalDriveIsNoLo	(149),
		vExpandCapacityOperationStartedForThisLo	(150),
		vExpandCapacityOperationDoneForThisLogic	(151),
		vExpandCapacityOperationOnThisLogicalDri	(152),
		vBadBlocksFoundOnThisLogicalDrive       	(153),
		vLogicalDriveSizeHasChanged             	(154),
		vLogicalDriveRaidLevelHasChanged        	(155),
		vBadDataBlocksFoundOnThisLogicalDrive   	(156),
		vFanUnitFailed                          	(256),
		vFanUnitIsOk                            	(257),
		vAemiFaultManagementIndicatesThatThereIs	(258),
		vSafteCabinetIndicateThatTheFanUnitIsNot	(259),
		vConnerCr-6Raidsaftescr1xCabinetIndicate	(272),
		vConnerCr-6Raidsaftescr1xCabinetIndiates	(273),
		vAemiFaultManagementIndicatesThatAPowerS	(274),
		vSafteCabinetIndicatesThatThePowerSupply	(275),
		vSaftescr1xCabinetTemperatureRisedAbove7	(288),
		vSaftescr1xCabinetTemperatureRisedAbove5	(289),
		vSaftescr1xCabinetTemperatureIsOkbelow50	(290),
		vAemiFaultManagementIndicatesOver-temper	(291),
		vSaftescr1xCabinetIndicatesThatTheHeatSe	(292),
		vStorageWorksCabinetFailed              	(304),
		vStorageWorksCabinetInCriticalState     	(305),
		vStorageWorksCabinetFunctioningOk       	(306),
		vGamServerSoftwareInitializationSuccessf	(384),
		vTheDacControllerCouldNotFlushCachedData	(385),
		vTheDeviceStateChangeTableIsFull        	(386),
		vControllerIsDead                       	(388),
		vControllerHasBeenReset                 	(389),
		vANewControllerFoundByGamServerSoftware 	(390),
		vControllerIsGone                       	(391),
		vBatteryBackupUnitFoundOnThisController 	(392),
		vBatteryBackupUnitPowerIsLow            	(393),
		vBatteryBackupUnitPowerOk               	(394),
		vControllerPoweredOff				       	(395),
		vControllerPoweredOn						(396),
		vControllerOnline							(397),
		vControllerOffline							(398),
		vControllerCritical							(399),
		vControllerBatteryBackupReconditionStart	(400),
		vControllerBatteryBackupReconditionEnd		(401),
		vGamServerStarted                       	(512),
		vSystemSizeTableFull                    	(513),
		vAUserLoggedOntoGamServer               	(514),
		vAUserLoggedOutOfGamServer              	(515),
		vUnknown                                	(255)
	}
	ACCESS		read-only
	STATUS		mandatory
	DESCRIPTION	"Mylex RAID event code."
	::= {eMylexRaidEventInformation 2}

a9EventTimeStamp OBJECT-TYPE
	SYNTAX		DmiInteger
	ACCESS		read-only
	STATUS		mandatory
	DESCRIPTION	"Time Stamp associated with this event. It's the number of
seconds since midnight(00:00:00) January 1, 1970 GMT."
	::= {eMylexRaidEventInformation 3}

a9ControllerNumber OBJECT-TYPE
	SYNTAX		DmiInteger
	ACCESS		read-only
	STATUS		mandatory
	DESCRIPTION	"Identifies the Disk Array Controller."
	::= {eMylexRaidEventInformation 4}

a9ChannelNumber OBJECT-TYPE
	SYNTAX		DmiInteger
	ACCESS		read-only
	STATUS		mandatory
	DESCRIPTION	"Identifies the SCSI Bus."
	::= {eMylexRaidEventInformation 5}

a9TargetNumber OBJECT-TYPE
	SYNTAX		DmiInteger
	ACCESS		read-only
	STATUS		mandatory
	DESCRIPTION	"Identifies the SCSI Target ID of physical device."
	::= {eMylexRaidEventInformation 6}

a9LunNumber OBJECT-TYPE
	SYNTAX		DmiInteger
	ACCESS		read-only
	STATUS		mandatory
	DESCRIPTION	"Identifies the SCSI LUN of physical device."
	::= {eMylexRaidEventInformation 7}

a9LogicalDriveNumber OBJECT-TYPE
	SYNTAX		DmiInteger
	ACCESS		read-only
	STATUS		mandatory
	DESCRIPTION	"Identifies the Logical Drive."
	::= {eMylexRaidEventInformation 8}

a9FmtCabinetNumber OBJECT-TYPE
	SYNTAX		DmiInteger
	ACCESS		read-only
	STATUS		mandatory
	DESCRIPTION	"Identifies the Fault Management Cabinet Number."
	::= {eMylexRaidEventInformation 9}

a9FanUnitNumber OBJECT-TYPE
	SYNTAX		DmiInteger
	ACCESS		read-only
	STATUS		mandatory
	DESCRIPTION	"Identifies the FAN Unit."
	::= {eMylexRaidEventInformation 10}

a9PowerSupplyUnitNumber OBJECT-TYPE
	SYNTAX		DmiInteger
	ACCESS		read-only
	STATUS		mandatory
	DESCRIPTION	"Identifies the Power Supply Unit Number."
	::= {eMylexRaidEventInformation 11}

a9HeatSensorUnitNumber OBJECT-TYPE
	SYNTAX		DmiInteger
	ACCESS		read-only
	STATUS		mandatory
	DESCRIPTION	"Identifies the Heat Sensor Unit Number."
	::= {eMylexRaidEventInformation 12}

SBatteryBackupUnitInformation ::= SEQUENCE {
	a10ControllerNumber                     	DmiInteger,
	a10OperationalState                     	DmiInteger,
	a10BatteryType                          	DmiInteger,
	a10CurrentPowerInHours                  	DmiInteger,
	a10MaximumPowerInHours                  	DmiInteger,
	a10ThresholdValueInHours                	DmiInteger,
	a10ChargeLevelInPercentage              	DmiInteger,
	a10Version                              	DmiInteger,
	a10OperationalStateString                  	DmiDisplaystring
}

tBatteryBackupUnitInformation OBJECT-TYPE
	SYNTAX		SEQUENCE OF SBatteryBackupUnitInformation
	ACCESS		not-accessible
	STATUS		mandatory
	DESCRIPTION	"This group provides Battery Backup Unit Information."
	::= {dmtfGroups 10}

eBatteryBackupUnitInformation OBJECT-TYPE
	SYNTAX		SBatteryBackupUnitInformation
	ACCESS		not-accessible
	STATUS		mandatory
	DESCRIPTION	""
	INDEX		{a10ControllerNumber}
	::= {tBatteryBackupUnitInformation 1}

a10ControllerNumber OBJECT-TYPE
	SYNTAX		DmiInteger
	ACCESS		read-only
	STATUS		mandatory
	DESCRIPTION	"Controller Number assigned to this controller by the device
driver."
	::= {eBatteryBackupUnitInformation 1}

a10OperationalState OBJECT-TYPE
	SYNTAX		INTEGER {
		vNoBatterBackupPresent						(-1),
		vNoReconditionSincePowerOn              	(1),
		vReconditionNeeded                      	(2),
		vFirstWarningOnLowBatteryCharge         	(4),
		vLastWarningOnLowBatteryCharge          	(8)
	}
	ACCESS		read-only
	STATUS		mandatory
	DESCRIPTION	"Operational state of Battery Backup Unit."
	::= {eBatteryBackupUnitInformation 2}

a10BatteryType OBJECT-TYPE
	SYNTAX		INTEGER {
		vNickelCadmium                          	(1)
	}
	ACCESS		read-only
	STATUS		mandatory
	DESCRIPTION	"Battery Type."
	::= {eBatteryBackupUnitInformation 3}

a10CurrentPowerInHours OBJECT-TYPE
	SYNTAX		DmiInteger
	ACCESS		read-only
	STATUS		mandatory
	DESCRIPTION	"Current Power in Hours."
	::= {eBatteryBackupUnitInformation 4}

a10MaximumPowerInHours OBJECT-TYPE
	SYNTAX		DmiInteger
	ACCESS		read-only
	STATUS		mandatory
	DESCRIPTION	"Maximum Power in Hours."
	::= {eBatteryBackupUnitInformation 5}

a10ThresholdValueInHours OBJECT-TYPE
	SYNTAX		DmiInteger
	ACCESS		read-only
	STATUS		mandatory
	DESCRIPTION	"Threshold Value in Hours."
	::= {eBatteryBackupUnitInformation 6}

a10ChargeLevelInPercentage OBJECT-TYPE
	SYNTAX		DmiInteger
	ACCESS		read-only
	STATUS		mandatory
	DESCRIPTION	"Battery Charge Level (in percentage)."
	::= {eBatteryBackupUnitInformation 7}

a10Version OBJECT-TYPE
	SYNTAX		DmiInteger
	ACCESS		read-only
	STATUS		mandatory
	DESCRIPTION	"BBU Hardware Version Number."
	::= {eBatteryBackupUnitInformation 8}

a10OperationalStateString OBJECT-TYPE
	SYNTAX		DmiDisplaystring
	ACCESS		read-only
	STATUS		mandatory
	DESCRIPTION	"Operational state of Battery Backup Unit."
	::= {eBatteryBackupUnitInformation 9}

--
--    TRAPS
--    Note that Trap annotations are also used. The trap
--    annotations ( NMS Trap Annotations ) are in comments so the 
--    MIB compilers which donot understand annotations will have no problems.

---
---	 trap 1 to trap 127 are physical device trap. 
---

fCArrayAssistant1	TRAP-TYPE
		ENTERPRISE  eMylexRaidEventInformation
		VARIABLES   {
			a9EventCode,
			a9ControllerNumber,
			a9ChannelNumber,
			a9TargetNumber,
			a9LunNumber,
			a9EventTimeStamp
		}
                DESCRIPTION
                   "device became online."
		   
                 --#SUMMARY  "[Event %d ctl %d chn %d tgt %d lun %d Time %d :] device became online."
                 --#ARGUMENTS {0,1,2,3,4,5}
                 --#SEVERITY INFORMATIONAL
		 --#TIMEINDEX 5
                 --#STATE OPERATIONAL
                 ::= 1

fCArrayAssistant2	TRAP-TYPE
		ENTERPRISE  eMylexRaidEventInformation
		VARIABLES   {
			a9EventCode,
			a9ControllerNumber,
			a9ChannelNumber,
			a9TargetNumber,
			a9LunNumber,
			a9EventTimeStamp
		}
                DESCRIPTION
                   "A hard disk has been added as hot spare."
		   
                --#SUMMARY "[Event %d ctl %d chn %d tgt %d lun %d Time %d :] A hard disk has been added as hot spare."
                --#ARGUMENTS {0,1,2,3,4,5}
                --#SEVERITY INFORMATIONAL
		--#TIMEINDEX 5
                --#STATE OPERATIONAL
                ::= 2

fCArrayAssistant3	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Hard drive error found."
		   
                  --#SUMMARY "[Event %d ctl %d chn %d tgt %d lun %d Time %d :] Hard drive error found."
                  --#ARGUMENTS {0,1,2,3,4,5}
                  --#SEVERITY MAJOR
	   	  --#TIMEINDEX 5
                  --#STATE OPERATIONAL
                 ::= 3

fCArrayAssistant4	TRAP-TYPE
		ENTERPRISE  eMylexRaidEventInformation
		VARIABLES   {
			a9EventCode,
			a9ControllerNumber,
			a9ChannelNumber,
			a9TargetNumber,
			a9LunNumber,
			a9EventTimeStamp
		}
                  DESCRIPTION
                   "Hard drive PFA condition found,this drive may fail soon"
		   
                  --#SUMMARY "[Event %d ctl %d chn %d tgt %d lun %d Time %d :] Hard drive PFA condition found,this drive may fail soon"
                  --#ARGUMENTS {0,1,2,3,4,5}
                  --#SEVERITY MAJOR
	   	  --#TIMEINDEX 5
                  --#STATE OPERATIONAL
                  ::= 4

fCArrayAssistant5	TRAP-TYPE
		ENTERPRISE  eMylexRaidEventInformation
		VARIABLES   {
			a9EventCode,
			a9ControllerNumber,
			a9ChannelNumber,
			a9TargetNumber,
			a9LunNumber,
			a9EventTimeStamp
		}
                  DESCRIPTION
                   "An automatic rebuild has started."
		   
                  --#SUMMARY "[Event %d ctl %d chn %d tgt %d lun %d Time %d :] An automatic rebuild has started."
                  --#ARGUMENTS {0,1,2,3,4,5}
                  --#SEVERITY INFORMATIONAL
	   	  --#TIMEINDEX 5
                  --#STATE OPERATIONAL
                     ::= 5

fCArrayAssistant6	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "A manual rebuild has started."
		   
                --#SUMMARY "[Event %d ctl %d chn %d tgt %d lun %d Time %d :] A manual rebuild has started."
	        --#ARGUMENTS {0,1,2,3,4,5}
		--#SEVERITY INFORMATIONAL
	   	--#TIMEINDEX 5
		--#STATE OPERATIONAL
		::= 6


fCArrayAssistant7	TRAP-TYPE
		ENTERPRISE  eMylexRaidEventInformation
		VARIABLES   {
			a9EventCode,
			a9ControllerNumber,
			a9ChannelNumber,
			a9TargetNumber,
			a9LunNumber,
			a9EventTimeStamp
		}
                  DESCRIPTION
                   "Rebuild is over."
		   
                  --#SUMMARY "[Event %d ctl %d chn %d tgt %d lun %d Time %d :] Rebuild is over."
                  --#ARGUMENTS {0,1,2,3,4,5}
                  --#SEVERITY INFORMATIONAL
		  --#TIMEINDEX 5
                  --#STATE OPERATIONAL
                  ::= 7

fCArrayAssistant8	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Rebuild is cancelled."
		   
                 --#SUMMARY "[Event %d ctl %d chn %d tgt %d lun %d Time %d :] Rebuild is cancelled."
                 --#ARGUMENTS {0,1,2,3,4,5}
                 --#SEVERITY MINOR
	         --#TIMEINDEX 5
                 --#STATE OPERATIONAL
                 ::= 8

fCArrayAssistant9	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                  "Rebuild stopped with error."
		  
                 --#SUMMARY  "[Event %d ctl %d chn %d tgt %d lun %d Time %d :] Rebuild stopped with error."
                 --#ARGUMENTS {0,1,2,3,4,5}
                 --#SEVERITY MAJOR
	         --#TIMEINDEX 5
                 --#STATE OPERATIONAL
                 ::= 9

fCArrayAssistant10	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                  "Rebuild stopped with error.New device failed."
		  
                 --#SUMMARY  "[Event %d ctl %d chn %d tgt %d lun %d Time %d :] Rebuild stopped with error.New device failed."
                 --#ARGUMENTS {0,1,2,3,4,5}
                 --#SEVERITY MAJOR
	         --#TIMEINDEX 5
                 --#STATE OPERATIONAL
                 ::= 10

fCArrayAssistant11	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                 "Rebuild stopped with error.logical drive failed."
		 
                 --#SUMMARY  "[Event %d ctl %d chn %d tgt %d lun %d Time %d :] Rebuild stopped with error.logical drive failed."
                 --#ARGUMENTS {0,1,2,3,4,5}
                 --#SEVERITY MAJOR
	         --#TIMEINDEX 5
                 --#STATE OPERATIONAL
                 ::= 11

fCArrayAssistant12	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "A Hard disk has failed."
		   
                 --#SUMMARY "[Event %d ctl %d chn %d tgt %d lun %d Time %d :] A Hard disk has failed."
                 --#ARGUMENTS {0,1,2,3,4,5}
                 --#SEVERITY CRITICAL
	         --#TIMEINDEX 5
                 --#STATE NONOPERATIONAL
                 ::= 12

fCArrayAssistant13	TRAP-TYPE
		ENTERPRISE  eMylexRaidEventInformation
		VARIABLES   {
			a9EventCode,
			a9ControllerNumber,
			a9ChannelNumber,
			a9TargetNumber,
			a9LunNumber,
			a9EventTimeStamp
		}
                 DESCRIPTION
		  "A new physical device has been found."
		  
                 --#SUMMARY "[Event %d ctl %d chn %d tgt %d lun %d Time %d :] A new physical device has been found."
                 --#ARGUMENTS {0,1,2,3,4,5}
                 --#SEVERITY INFORMATIONAL
	         --#TIMEINDEX 5
                 --#STATE OPERATIONAL
                 ::= 13

fCArrayAssistant14	TRAP-TYPE
		ENTERPRISE  eMylexRaidEventInformation
		VARIABLES   {
			a9EventCode,
			a9ControllerNumber,
			a9ChannelNumber,
			a9TargetNumber,
			a9LunNumber,
			a9EventTimeStamp
		}
                 DESCRIPTION
		  "physical device has been removed."
		  
                 --#SUMMARY "[Event %d ctl %d chn %d tgt %d lun %d Time %d :] A physical device has been removed."
                 --#ARGUMENTS {0,1,2,3,4,5}
                 --#SEVERITY INFORMATIONAL
	         --#TIMEINDEX 5
                 --#STATE NONOPERATIONAL
                 ::= 14

fCArrayAssistant15	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "A previously configured device is now available for configuration."
		   
                 --#SUMMARY "[Event %d ctl %d chn %d tgt %d lun %d Time %d :] A previously configured device is now available for configuration"
                 --#ARGUMENTS {0,1,2,3,4,5}
                 --#SEVERITY INFORMATIONAL
	         --#TIMEINDEX 5
                 --#STATE OPERATIONAL
                 ::= 15

fCArrayAssistant16	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Expand capacity started."
		   
                 --#SUMMARY "[Event %d ctl %d chn %d tgt %d lun %d Time %d :] Expand capacity started."
                 --#ARGUMENTS {0,1,2,3,4,5}
                 --#SEVERITY INFORMATIONAL
	         --#TIMEINDEX 5
                 --#STATE OPERATIONAL
                 ::= 16
		 
fCArrayAssistant17	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Expand capacity completed."
		 
                 --#SUMMARY "[Event %d ctl %d chn %d tgt %d lun %d Time %d :] Expand capacity completed."
                 --#ARGUMENTS {0,1,2,3,4,5}
                 --#SEVERITY INFORMATIONAL
	         --#TIMEINDEX 5
                 --#STATE OPERATIONAL
                 ::= 17

fCArrayAssistant18	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Expand capacity stopped with error."
		   
                 --#SUMMARY "[Event %d ctl %d chn %d tgt %d lun %d Time %d :] Expand capacity stopped with error."
                 --#ARGUMENTS {0,1,2,3,4,5}
                 --#SEVERITY MAJOR
	         --#TIMEINDEX 5
                 --#STATE OPERATIONAL
                 ::= 18

fCArrayAssistant19	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Command timed out."
		 
                 --#SUMMARY "[Event %d ctl %d chn %d tgt %d lun %d Time %d :] Command timed out."
                 --#ARGUMENTS {0,1,2,3,4,5}
                 --#SEVERITY MAJOR
	         --#TIMEINDEX 5
                 --#STATE OPERATIONAL
		 ::= 19
		 
fCArrayAssistant20	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Command aborted."
		   
                 --#SUMMARY "[Event %d ctl %d chn %d tgt %d lun %d Time %d :] Command aborted."
                 --#ARGUMENTS {0,1,2,3,4,5}
                 --#SEVERITY MINOR
	         --#TIMEINDEX 5
                 --#STATE OPERATIONAL
		 ::= 20
		 
fCArrayAssistant21	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Command retried."
		 
                 --#SUMMARY "[Event %d ctl %d chn %d tgt %d lun %d Time %d :] Command retried."
                 --#ARGUMENTS {0,1,2,3,4,5}
                 --#SEVERITY INFORMATIONAL
	         --#TIMEINDEX 5
                 --#STATE OPERATIONAL
		 ::= 21
		 
fCArrayAssistant22	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Parity errors found."
		   
                 --#SUMMARY "[Event %d ctl %d chn %d tgt %d lun %d Time %d :] Parity errors found."
                 --#ARGUMENTS {0,1,2,3,4,5}
                 --#SEVERITY INFORMATIONAL
	         --#TIMEINDEX 5
                 --#STATE OPERATIONAL
                 ::= 22


fCArrayAssistant23	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Soft errors found."
		   
                 --#SUMMARY "[Event %d ctl %d chn %d tgt %d lun %d Time %d :] Soft errors found."
                 --#ARGUMENTS {0,1,2,3,4,5}
                 --#SEVERITY INFORMATIONAL
	         --#TIMEINDEX 5
                 --#STATE OPERATIONAL
                 ::= 23

fCArrayAssistant24	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Miscellaneous errors found."
		   
                 --#SUMMARY "[Event %d ctl %d chn %d tgt %d lun %d Time %d :] Miscellaneous errors found."
                 --#ARGUMENTS {0,1,2,3,4,5}
                 --#SEVERITY INFORMATIONAL
	         --#TIMEINDEX 5
                 --#STATE OPERATIONAL
                 ::= 24

fCArrayAssistant25	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Physical device is reset."
		   
                 --#SUMMARY "[Event %d ctl %d chn %d tgt %d lun %d Time %d :] Physical device is reset."
                 --#ARGUMENTS {0,1,2,3,4,5}
                 --#SEVERITY INFORMATIONAL
	         --#TIMEINDEX 5
                 --#STATE OPERATIONAL
                 ::= 25

fCArrayAssistant26	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "A hard disk has been added as an active spare."
		   
                 --#SUMMARY "[Event %d ctl %d chn %d tgt %d lun %d Time %d :] A hard disk has been added as an active spare."
                 --#ARGUMENTS {0,1,2,3,4,5}
                 --#SEVERITY INFORMATIONAL
	         --#TIMEINDEX 5
                 --#STATE OPERATIONAL
                 ::= 26

fCArrayAssistant27	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "A hard disk has been added as an warm spare."
		 
                 --#SUMMARY "[Event %d ctl %d chn %d tgt %d lun %d Time %d :] A hard disk has been added as an warm spare."
                 --#ARGUMENTS {0,1,2,3,4,5}
                 --#SEVERITY INFORMATIONAL
	         --#TIMEINDEX 5
                 --#STATE OPERATIONAL
                 ::= 27

fCArrayAssistant28	TRAP-TYPE
		ENTERPRISE  eMylexRaidEventInformation
		VARIABLES   {
			a9EventCode,
			a9ControllerNumber,
			a9ChannelNumber,
			a9TargetNumber,
			a9LunNumber,
			a9EventTimeStamp
		}
                 DESCRIPTION
                   "Request Sense Data Available."
		 
                 --#SUMMARY "[Event %d ctl %d chn %d tgt %d lun %d Time %d :] Request Sense Data Available."
                 --#ARGUMENTS {0,1,2,3,4,5}
                 --#SEVERITY INFORMATIONAL
	         --#TIMEINDEX 5
                 --#STATE OPERATIONAL
                 ::= 28


---
--- trap 128 to trap 255 are logical drive trap
---

fCArrayAssistant29	TRAP-TYPE
		ENTERPRISE  eMylexRaidEventInformation
		VARIABLES   {
			a9EventCode,
			a9ControllerNumber,
			a9LogicalDriveNumber,
			a9EventTimeStamp
		}
                DESCRIPTION
                   "A consistency check is started."
		   
                --#SUMMARY "[Event %d ctl %d logdrv %d Time %d :] A consistency check is started."
                --#ARGUMENTS {0,1,2,3}
                --#SEVERITY INFORMATIONAL
	        --#TIMEINDEX 3
                --#STATE OPERATIONAL
                ::= 128

fCArrayAssistant30	TRAP-TYPE
		ENTERPRISE  eMylexRaidEventInformation
		VARIABLES   {
			a9EventCode,
			a9ControllerNumber,
			a9LogicalDriveNumber,
			a9EventTimeStamp
		}
                 DESCRIPTION
                   "Consistency check is finished."
		   
                 --#SUMMARY "[Event %d ctl %d logdrv %d Time %d :] Consistency check is finished."
                 --#ARGUMENTS {0,1,2,3}
                 --#SEVERITY INFORMATIONAL
	         --#TIMEINDEX 3
		 --#STATE OPERATIONAL
                 ::= 129

fCArrayAssistant31	TRAP-TYPE
		ENTERPRISE  eMylexRaidEventInformation
		VARIABLES   {
			a9EventCode,
			a9ControllerNumber,
			a9LogicalDriveNumber,
			a9EventTimeStamp
		}
                 DESCRIPTION
                   "Consistency check is cancelled."
		   
                 --#SUMMARY "[Event %d ctl %d logdrv %d Time %d :] Consistency check is cancelled."
                 --#ARGUMENTS {0,1,2,3}
                 --#SEVERITY INFORMATIONAL
	         --#TIMEINDEX 3
                 --#STATE OPERATIONAL
                 ::= 130

fCArrayAssistant32	TRAP-TYPE
		ENTERPRISE  eMylexRaidEventInformation
		VARIABLES   {
			a9EventCode,
			a9ControllerNumber,
			a9LogicalDriveNumber,
			a9EventTimeStamp
		}
                 DESCRIPTION
                   "Consistency check on logical drive error."
		   
                 --#SUMMARY "[Event %d ctl %d logdrv %d Time %d :] Consistency check on logical drive error."
                 --#ARGUMENTS {0,1,2,3}
                 --#SEVERITY MAJOR
	         --#TIMEINDEX 3
                 --#STATE OPERATIONAL
                 ::= 131

fCArrayAssistant33	TRAP-TYPE
		ENTERPRISE  eMylexRaidEventInformation
		VARIABLES   {
			a9EventCode,
			a9ControllerNumber,
			a9LogicalDriveNumber,
			a9EventTimeStamp
		}
                 DESCRIPTION
                   "Consistency check on logical drive failed."
		   
                 --#SUMMARY "[Event %d ctl %d logdrv %d Time %d :] Consistency check on logical drive failed."
                 --#ARGUMENTS {0,1,2,3}
                 --#SEVERITY MAJOR
	         --#TIMEINDEX 3
                 --#STATE OPERATIONAL
                 ::= 132

fCArrayAssistant34	TRAP-TYPE
		ENTERPRISE  eMylexRaidEventInformation
		VARIABLES   {
			a9EventCode,
			a9ControllerNumber,
			a9LogicalDriveNumber,
			a9EventTimeStamp
		}
                 DESCRIPTION
                   "Consistency check on logical drive failed due to physical device failure."
		   
                 --#SUMMARY "[Event %d ctl %d logdrv %d Time %d :] Consistency check on logical drive failed due to physical device failure."
                 --#ARGUMENTS {0,1,2,3}
                 --#SEVERITY MAJOR
	         --#TIMEINDEX 3
                 --#STATE DEGRADED
                 ::= 133

fCArrayAssistant35	TRAP-TYPE
		ENTERPRISE  eMylexRaidEventInformation
		VARIABLES   {
			a9EventCode,
			a9ControllerNumber,
			a9LogicalDriveNumber,
			a9EventTimeStamp
		}
                 DESCRIPTION
                   "A logical drive has been made offline."
		   
                 --#SUMMARY "[Event %d ctl %d logdrv %d Time %d :] A logical drive has been made offline."
                 --#ARGUMENTS {0,1,2,3}
                 --#SEVERITY CRITICAL
	         --#TIMEINDEX 3
                 --#STATE NONOPERATIONAL
                 ::= 134

fCArrayAssistant36	TRAP-TYPE
		ENTERPRISE  eMylexRaidEventInformation
		VARIABLES   {
			a9EventCode,
			a9ControllerNumber,
			a9LogicalDriveNumber,
			a9EventTimeStamp
		}
                 DESCRIPTION
                   "A logical drive is critical."
		   
                 --#SUMMARY "[Event %d ctl %d logdrv %d Time %d :] A logical drive is critical."
                 --#ARGUMENTS {0,1,2,3}
                 --#SEVERITY MAJOR
	         --#TIMEINDEX 3
                 --#STATE DEGRADED
                 ::= 135

fCArrayAssistant37	TRAP-TYPE
		ENTERPRISE  eMylexRaidEventInformation
		VARIABLES   {
			a9EventCode,
			a9ControllerNumber,
			a9LogicalDriveNumber,
			a9EventTimeStamp
		}
                 DESCRIPTION
                   "A logical drive has been placed online."
		   
                 --#SUMMARY "[Event %d ctl %d logdrv %d Time %d :] A logical drive has been placed online."
                 --#ARGUMENTS {0,1,2,3}
                 --#SEVERITY INFORMATIONAL
	         --#TIMEINDEX 3
                 --#STATE OPERATIONAL
                 ::= 136

fCArrayAssistant38	TRAP-TYPE
		ENTERPRISE  eMylexRaidEventInformation
		VARIABLES   {
			a9EventCode,
			a9ControllerNumber,
			a9LogicalDriveNumber,
			a9EventTimeStamp
		}
                DESCRIPTION
                   "An automatic rebuild has started on logical drive."
                --#SUMMARY "[Event %d ctl %d logdrv %d Time %d :] An automatic rebuild has started on logical drive."
                --#ARGUMENTS {0,1,2,3}
                --#SEVERITY INFORMATIONAL
                --#TIMEINDEX 3
                --#STATE OPERATIONAL
                ::= 137

fCArrayAssistant39	TRAP-TYPE
		ENTERPRISE  eMylexRaidEventInformation
		VARIABLES   {
			a9EventCode,
			a9ControllerNumber,
			a9LogicalDriveNumber,
			a9EventTimeStamp
		}
                 DESCRIPTION
                  "A manual rebuild has started on logical drive."
                 --#SUMMARY "[Event %d ctl %d logdrv %d Time %d :] A manual rebuild has started on logical drive."
                 --#ARGUMENTS {0,1,2,3}
                 --#SEVERITY INFORMATIONAL
                 --#TIMEINDEX 3
                 --#STATE OPERATIONAL
                 ::= 138


fCArrayAssistant40	TRAP-TYPE
		ENTERPRISE  eMylexRaidEventInformation
		VARIABLES   {
			a9EventCode,
			a9ControllerNumber,
			a9LogicalDriveNumber,
			a9EventTimeStamp
		}
                 DESCRIPTION
                   "Rebuild on logical drive is over."
                 --#SUMMARY "[Event %d ctl %d logdrv %d Time %d :] Rebuild on logical drive is over."
                 --#ARGUMENTS {0,1,2,3}
                 --#SEVERITY INFORMATIONAL
                 --#TIMEINDEX 3
                 --#STATE OPERATIONAL
                 ::= 139

fCArrayAssistant41	TRAP-TYPE
		ENTERPRISE  eMylexRaidEventInformation
		VARIABLES   {
			a9EventCode,
			a9ControllerNumber,
			a9LogicalDriveNumber,
			a9EventTimeStamp
		}
                 DESCRIPTION
                   "Rebuild on logical drive is cancelled."
		   
                 --#SUMMARY "[Event %d ctl %d logdrv %d Time %d :] Rebuild on logical drive is cancelled."
                 --#ARGUMENTS {0,1,2,3}
                 --#SEVERITY INFORMATIONAL
                 --#TIMEINDEX 3
                 --#STATE DEGRADED
                 ::= 140

fCArrayAssistant42	TRAP-TYPE
		ENTERPRISE  eMylexRaidEventInformation
		VARIABLES   {
			a9EventCode,
			a9ControllerNumber,
			a9LogicalDriveNumber,
			a9EventTimeStamp
		}
                 DESCRIPTION
                   "Rebuild stopped with error."
                --#SUMMARY "[Event %d ctl %d logdrv %d Time %d :] Rebuild stopped with error."
                --#ARGUMENTS {0,1,2,3}
                --#SEVERITY MAJOR
                --#TIMEINDEX 3
                --#STATE DEGRADED
                ::= 141
		
fCArrayAssistant43	TRAP-TYPE
		ENTERPRISE  eMylexRaidEventInformation
		VARIABLES   {
			a9EventCode,
			a9ControllerNumber,
			a9LogicalDriveNumber,
			a9EventTimeStamp
		}
                 DESCRIPTION
                  "Rebuild stopped with error.New device failed."
                 --#SUMMARY "[Event %d ctl %d logdrv %d Time %d :] Rebuild stopped with error.New device failed."
                 --#ARGUMENTS {0,1,2,3}
                 --#SEVERITY MAJOR
                 --#TIMEINDEX 3
                 --#STATE DEGRADED
                 ::= 142

fCArrayAssistant44	TRAP-TYPE
		ENTERPRISE  eMylexRaidEventInformation
		VARIABLES   {
			a9EventCode,
			a9ControllerNumber,
			a9LogicalDriveNumber,
			a9EventTimeStamp
		}
                 DESCRIPTION
                   "Rebuild stopped because logical drive failed."
                 --#SUMMARY "[Event %d ctl %d logdrv %d Time %d :] Rebuild stopped because logical drive failed."
                 --#ARGUMENTS {0,1,2,3}
                 --#SEVERITY CRITICAL
                 --#TIMEINDEX 3
                 --#STATE NONOPERATIONAL
                 ::= 143

fCArrayAssistant45	TRAP-TYPE
		ENTERPRISE  eMylexRaidEventInformation
		VARIABLES   {
			a9EventCode,
			a9ControllerNumber,
			a9LogicalDriveNumber,
			a9EventTimeStamp
		}
                 DESCRIPTION
                   "Logical drive initialization started."
                 --#SUMMARY "[Event %d ctl %d logdrv %d Time %d :] Logical drive initialization started."
                 --#ARGUMENTS {0,1,2,3}
                 --#SEVERITY INFORMATIONAL
                 --#TIMEINDEX 3
                 --#STATE OPERATIONAL
                 ::= 144
         

fCArrayAssistant46	TRAP-TYPE
		ENTERPRISE  eMylexRaidEventInformation
		VARIABLES   {
			a9EventCode,
			a9ControllerNumber,
			a9LogicalDriveNumber,
			a9EventTimeStamp
		}
                 DESCRIPTION
                  "Logical drive initialization done."
                 --#SUMMARY "[Event %d ctl %d logdrv %d Time %d :] Logical drive initialization done."
                 --#ARGUMENTS {0,1,2,3}
                 --#SEVERITY INFORMATIONAL
                 --#TIMEINDEX 3
                 --#STATE OPERATIONAL
                ::= 145


fCArrayAssistant47	TRAP-TYPE
		ENTERPRISE  eMylexRaidEventInformation
		VARIABLES   {
			a9EventCode,
			a9ControllerNumber,
			a9LogicalDriveNumber,
			a9EventTimeStamp
		}
                 DESCRIPTION
                  "Logical drive initialization cancelled."
                --#SUMMARY "[Event %d ctl %d logdrv %d Time %d :] Logical drive initialization cancelled."
                --#ARGUMENTS {0,1,2,3}
                --#SEVERITY INFORMATIONAL
                --#TIMEINDEX 3
                --#STATE OPERATIONAL
                ::= 146

fCArrayAssistant48	TRAP-TYPE
		ENTERPRISE  eMylexRaidEventInformation
		VARIABLES   {
			a9EventCode,
			a9ControllerNumber,
			a9LogicalDriveNumber,
			a9EventTimeStamp
		}
                 DESCRIPTION
                  "Logical drive initialization failed."
                 --#SUMMARY "[Event %d ctl %d logdrv %d Time %d :] Logical drive initialization failed."
                 --#ARGUMENTS {0,1,2,3}
                 --#SEVERITY MINOR
                 --#TIMEINDEX 3
                 --#STATE NONOPERATIONAL
                 ::= 147

fCArrayAssistant49	TRAP-TYPE
		ENTERPRISE  eMylexRaidEventInformation
		VARIABLES   {
			a9EventCode,
			a9ControllerNumber,
			a9LogicalDriveNumber,
			a9EventTimeStamp
		}
                 DESCRIPTION
                  "A new logical drive has been created."
                 --#SUMMARY "[Event %d ctl %d logdrv %d Time %d :] A new logical drive has been created."
                 --#ARGUMENTS {0,1,2,3}
                 --#SEVERITY INFORMATIONAL
                 --#TIMEINDEX 3
                 --#STATE OPERATIONAL
                 ::= 148

fCArrayAssistant50	TRAP-TYPE
		ENTERPRISE  eMylexRaidEventInformation
		VARIABLES   {
			a9EventCode,
			a9ControllerNumber,
			a9LogicalDriveNumber,
			a9EventTimeStamp
		}
                 DESCRIPTION
                  "A new logical drive has been deleted."
                 --#SUMMARY "[Event %d ctl %d logdrv %d Time %d :] A new logical drive has been deleted."
                 --#ARGUMENTS {0,1,2,3}
                 --#SEVERITY INFORMATIONAL
                 --#TIMEINDEX 3
                 --#STATE NONOPERATIONAL
                 ::= 149

fCArrayAssistant51	TRAP-TYPE
		ENTERPRISE  eMylexRaidEventInformation
		VARIABLES   {
			a9EventCode,
			a9ControllerNumber,
			a9LogicalDriveNumber,
			a9EventTimeStamp
		}
                 DESCRIPTION
                  "Expand capacity started."
                 --#SUMMARY "[Event %d ctl %d logdrv %d Time %d :] Expand capacity started."
                 --#ARGUMENTS {0,1,2,3}
                 --#SEVERITY INFORMATIONAL
                 --#TIMEINDEX 3
                 --#STATE OPERATIONAL
                 ::= 150
		 
fCArrayAssistant52	TRAP-TYPE
		ENTERPRISE  eMylexRaidEventInformation
		VARIABLES   {
			a9EventCode,
			a9ControllerNumber,
			a9LogicalDriveNumber,
			a9EventTimeStamp
		}
                 DESCRIPTION
                  "Expand capacity completed."
                 --#SUMMARY "[Event %d ctl %d logdrv %d Time %d :] Expand capacity completed."
                 --#ARGUMENTS {0,1,2,3}
                 --#SEVERITY INFORMATIONAL
                 --#TIMEINDEX 3
                 --#STATE OPERATIONAL
                 ::= 151
		 
fCArrayAssistant53	TRAP-TYPE
		ENTERPRISE  eMylexRaidEventInformation
		VARIABLES   {
			a9EventCode,
			a9ControllerNumber,
			a9LogicalDriveNumber,
			a9EventTimeStamp
		}
                 DESCRIPTION
                  "Expand capacity stopped with error."
                 --#SUMMARY "[Event %d ctl %d logdrv %d Time %d :] Expand capacity stopped with error."
                 --#ARGUMENTS {0,1,2,3}
                 --#SEVERITY MAJOR
                 --#TIMEINDEX 3
                 --#STATE NONOPERATIONAL
                 ::= 152
		 
fCArrayAssistant54	TRAP-TYPE
		ENTERPRISE  eMylexRaidEventInformation
		VARIABLES   {
			a9EventCode,
			a9ControllerNumber,
			a9LogicalDriveNumber,
			a9EventTimeStamp
		}
                 DESCRIPTION
                  "Bad Blocks found."
                 --#SUMMARY "[Event %d ctl %d logdrv %d Time %d :] Bad Blocks found."
                 --#ARGUMENTS {0,1,2,3}
                 --#SEVERITY MINOR
                 --#TIMEINDEX 3
                 --#STATE OPERATIONAL
                 ::= 153
		 
fCArrayAssistant55	TRAP-TYPE
		ENTERPRISE  eMylexRaidEventInformation
		VARIABLES   {
			a9EventCode,
			a9ControllerNumber,
			a9LogicalDriveNumber,
			a9EventTimeStamp
		}
                 DESCRIPTION
                  "System drive size changed."
                 --#SUMMARY "[Event %d ctl %d logdrv %d Time %d :] System drive size changed."
                 --#ARGUMENTS {0,1,2,3}
                 --#SEVERITY INFORMATIONAL
                 --#TIMEINDEX 3
                 --#STATE OPERATIONAL
                 ::= 154
		 
fCArrayAssistant56	TRAP-TYPE
		ENTERPRISE  eMylexRaidEventInformation
		VARIABLES   {
			a9EventCode,
			a9ControllerNumber,
			a9LogicalDriveNumber,
			a9EventTimeStamp
		}
                 DESCRIPTION
                  "System device type changed."
                 --#SUMMARY "[Event %d ctl %d logdrv %d Time %d :] System device type changed."
                 --#ARGUMENTS {0,1,2,3}
                 --#SEVERITY INFORMATIONAL
                 --#TIMEINDEX 3
                 --#STATE OPERATIONAL
                 ::= 155

fCArrayAssistant57	TRAP-TYPE
		ENTERPRISE  eMylexRaidEventInformation
		VARIABLES   {
			a9EventCode,
			a9ControllerNumber,
			a9LogicalDriveNumber,
			a9EventTimeStamp
		}
                 DESCRIPTION
                  "Bad Data Blocks found."
                 --#SUMMARY "[Event %d ctl %d logdrv %d Time %d :] Bad Data Blocks found."
                 --#ARGUMENTS {0,1,2,3}
                 --#SEVERITY INFORMATIONAL
                 --#TIMEINDEX 3
                 --#STATE OPERATIONAL
                 ::= 156
		 
---
--- trap 256 to trap 271 are FMT fan traps
---

fCArrayAssistant77	TRAP-TYPE
		ENTERPRISE  eMylexRaidEventInformation
		VARIABLES   {
			a9EventCode,
			a9ControllerNumber,
			a9ChannelNumber,
			a9FmtCabinetNumber,
			a9FanUnitNumber,
			a9EventTimeStamp
		}
		DESCRIPTION
                   "Fan failure."
                 --#SUMMARY "[Event %d ctl %d chn %d Cabinet %d Fan %d Time %d :] Fan failure."
                 --#ARGUMENTS {0,1,2,3,4,5}
                 --#SEVERITY CRITICAL
                 --#TIMEINDEX 5
                 --#STATE NONOPERATIONAL
                 ::= 256

fCArrayAssistant78	TRAP-TYPE
		ENTERPRISE  eMylexRaidEventInformation
		VARIABLES   {
			a9EventCode,
			a9ControllerNumber,
			a9ChannelNumber,
			a9FmtCabinetNumber,
			a9FanUnitNumber,
			a9EventTimeStamp
		}
		DESCRIPTION
                 "Fan has been restored."
                --#SUMMARY "[Event %d ctl %d chn %d Cabinet %d Fan %d Time %d :] Fan has been restored."
                --#ARGUMENTS {0,1,2,3,4,5}
                --#SEVERITY INFORMATIONAL
                --#TIMEINDEX 5
                --#STATE OPERATIONAL
                ::= 257

fCArrayAssistant79	TRAP-TYPE
		ENTERPRISE  eMylexRaidEventInformation
		VARIABLES   {
			a9EventCode,
			a9ControllerNumber,
			a9ChannelNumber,
			a9FmtCabinetNumber,
			a9FanUnitNumber,
			a9EventTimeStamp
		}
                 DESCRIPTION
                   "Aemi Fan failure."
                 --#SUMMARY "[Event %d ctl %d chn %d Cabinet %d Fan %d Time %d :] Aemi Fan failure."
                 --#ARGUMENTS {0,1,2,3,4,5}
                 --#SEVERITY CRITICAL
                 --#TIMEINDEX 5
                 --#STATE NONOPERATIONAL
                 ::= 258

fCArrayAssistant80	TRAP-TYPE
		ENTERPRISE  eMylexRaidEventInformation
		VARIABLES   {
			a9EventCode,
			a9ControllerNumber,
			a9ChannelNumber,
			a9FmtCabinetNumber,
			a9FanUnitNumber,
			a9EventTimeStamp
		}
                 DESCRIPTION
                   "Fan was prsent earlier;Not available now." 
                 --#SUMMARY "[Event %d ctl %d chn %d Cabinet %d Fan %d Time %d :] Fan was present earlier;Not available now." 
                 --#ARGUMENTS {0,1,2,3,4,5}
                 --#SEVERITY INFORMATIONAL
                 --#TIMEINDEX 5
                 --#STATE NONOPERATIONAL
                 ::= 259

---
--- trap 272 to 287	 are FMT power trap
---

fCArrayAssistant81	TRAP-TYPE
		ENTERPRISE  eMylexRaidEventInformation
		VARIABLES   {
			a9EventCode,
			a9ControllerNumber,
			a9ChannelNumber,
			a9FmtCabinetNumber,
			a9PowerSupplyUnitNumber,
			a9EventTimeStamp
		}
                 DESCRIPTION
                   "Power supply failure."
                 --#SUMMARY "[Event %d ctl %d chn %d Cabinet %d PowerSupplyUnit %d Time %d :] Power supply failure."
                 --#ARGUMENTS {0,1,2,3,4,5}
                 --#SEVERITY CRITICAL
                 --#TIMEINDEX 5
                 --#STATE NONOPERATIONAL
                ::= 272

fCArrayAssistant82	TRAP-TYPE
		ENTERPRISE  eMylexRaidEventInformation
		VARIABLES   {
			a9EventCode,
			a9ControllerNumber,
			a9ChannelNumber,
			a9FmtCabinetNumber,
			a9PowerSupplyUnitNumber,
			a9EventTimeStamp
		}
                 DESCRIPTION
                  "Power supply has been restored."
                 --#SUMMARY "[Event %d ctl %d chn %d Cabinet %d PowerSupplyUnit %d Time %d :] Power supply has been restored."
                 --#ARGUMENTS {0,1,2,3,4,5}
                 --#SEVERITY INFORMATIONAL
                 --#TIMEINDEX 5
                 --#STATE OPERATIONAL
                 ::= 273

aemiPowerSupplyFailed   TRAP-TYPE
		ENTERPRISE  eMylexRaidEventInformation
		VARIABLES   {
			a9EventCode,
			a9ControllerNumber,
			a9ChannelNumber,
			a9FmtCabinetNumber,
			a9PowerSupplyUnitNumber,
			a9EventTimeStamp
		}
                 DESCRIPTION
                   "AEMI Power supply failure."
                 --#SUMMARY "[Event %d ctl %d chn %d Cabinet %d PowerSupplyUnit %d Time %d :] Aemi Power supply failure."
                 --#ARGUMENTS {0,1,2,3,4,5}
                 --#SEVERITY CRITICAL
                 --#TIMEINDEX 5
                 --#STATE NONOPERATIONAL
                 ::= 274

fCArrayAssistant83	TRAP-TYPE
		ENTERPRISE  eMylexRaidEventInformation
		VARIABLES   {
			a9EventCode,
			a9ControllerNumber,
			a9ChannelNumber,
			a9PowerSupplyUnitNumber,
			a9FanUnitNumber,
			a9EventTimeStamp
		}
                 DESCRIPTION
                   "Power supply was present earlier;Not available now."
                 --#SUMMARY "[Event %d ctl %d chn %d PowerSupplyUnit %d Fan %d Time %d :] Power supply was present earlier;Not available now."
                 --#ARGUMENTS {0,1,2,3,4,5}
                 --#SEVERITY INFORMATIONAL
                 --#TIMEINDEX 5
                 --#STATE NONOPERATIONAL
                 ::= 275

---
---	trap 288 to trqap 303 are FMT temperature trap
---

fCArrayAssistant84	TRAP-TYPE
		ENTERPRISE  eMylexRaidEventInformation
		VARIABLES   {
			a9EventCode,
			a9ControllerNumber,
			a9ChannelNumber,
			a9FmtCabinetNumber,
			a9HeatSensorUnitNumber,
			a9EventTimeStamp
		}
                  DESCRIPTION
                   "Over temperature.Temperature is above 70 degrees celsius."
                 --#SUMMARY "[Event %d ctl %d chn %d Cabinet %d HeatSensor %d Time %d :] Over Temperature.Temperature is above 70 degrees celsius."
                 --#ARGUMENTS {0,1,2,3,4,5}
                 --#SEVERITY CRITICAL
                 --#TIMEINDEX 5
                 --#STATE DEGRADED
                 ::= 288

fCArrayAssistant85	TRAP-TYPE
		ENTERPRISE  eMylexRaidEventInformation
		VARIABLES   {
			a9EventCode,
			a9ControllerNumber,
			a9ChannelNumber,
			a9FmtCabinetNumber,
			a9HeatSensorUnitNumber,
			a9EventTimeStamp
		}
                  DESCRIPTION
                   "Temperature is above 50 degrees celsius."
                 --#SUMMARY "[Event %d ctl %d chn %d Cabinet %d HeatSensor %d Time %d :] Temperature is above 50 degrees celsius."
                 --#ARGUMENTS {0,1,2,3,4,5}
                 --#SEVERITY MAJOR
                 --#TIMEINDEX 5
                 --#STATE DEGRADED
                 ::= 289
		 
fCArrayAssistant86	TRAP-TYPE
		ENTERPRISE  eMylexRaidEventInformation
		VARIABLES   {
			a9EventCode,
			a9ControllerNumber,
			a9ChannelNumber,
			a9FmtCabinetNumber,
			a9HeatSensorUnitNumber,
			a9EventTimeStamp
		}
                  DESCRIPTION
                   "Normal temperature has been restored."
                 --#SUMMARY "[Event %d ctl %d chn %d Cabinet %d HeatSensor %d Time %d :] Normal temperature has been restored."
                 --#ARGUMENTS {0,1,2,3,4,5}
                 --#SEVERITY INFORMATIONAL
                 --#TIMEINDEX 5
                 --#STATE OPERATIONAL
                 ::= 290
		 
aemiOverTemperature  TRAP-TYPE
		ENTERPRISE  eMylexRaidEventInformation
		VARIABLES   {
			a9EventCode,
			a9ControllerNumber,
			a9ChannelNumber,
			a9FmtCabinetNumber,
			a9HeatSensorUnitNumber,
			a9EventTimeStamp
		}
                 DESCRIPTION
                  "Over temperature."
                 --#SUMMARY "[Event %d ctl %d chn %d Cabinet %d HeatSensor %d Time %d :] AEMI over temperature."
                 --#ARGUMENTS {0,1,2,3,4,5}
                 --#SEVERITY CRITICAL
                 --#TIMEINDEX 5
                 --#STATE DEGRADED
                 ::= 291

fCArrayAssistant87	TRAP-TYPE
		ENTERPRISE  eMylexRaidEventInformation
		VARIABLES   {
			a9EventCode,
			a9ControllerNumber,
			a9ChannelNumber,
			a9FmtCabinetNumber,
			a9HeatSensorUnitNumber,
			a9EventTimeStamp
		}
                  DESCRIPTION
                   "Heat sensor was present earlier;Not available now."
                 --#SUMMARY "[Event %d ctl %d chn %d tgt %d HeatSensor %d Time %d :] Heat sensor was present earlier;Not available now."
                 --#ARGUMENTS {0,1,2,3,4,5}
                 --#SEVERITY INFORMATIONAL
                 --#TIMEINDEX 5
                 --#STATE OPERATIONAL
                 ::= 292
		 
fmtStorageworksFailed    TRAP-TYPE
		ENTERPRISE  eMylexRaidEventInformation
		VARIABLES   {
			a9EventCode,
			a9ControllerNumber,
			a9ChannelNumber,
			a9EventTimeStamp
		}
                  DESCRIPTION
                   "Storage-Works Enclosure failed."
                 --#SUMMARY "[Event %d ctl %d chn %d Time %d :] Storage-Works Enclosure failed."
                 --#ARGUMENTS {0,1,2,3}
                 --#SEVERITY CRITICAL
                 --#TIMEINDEX 3
                 --#STATE NONOPERATIONAL
                 ::= 304
		 
fmtStorageworksCritical    TRAP-TYPE
		ENTERPRISE  eMylexRaidEventInformation
		VARIABLES   {
			a9EventCode,
			a9ControllerNumber,
			a9ChannelNumber,
			a9EventTimeStamp
		}
                  DESCRIPTION
                   "Storage-Works Enclosure is Critical"
                 --#SUMMARY "[Event %d ctl %d chn %d Time %d :] Storage-Works Enclosure is Critical."
                 --#ARGUMENTS {0,1,2,3}
                 --#SEVERITY MAJOR
                 --#TIMEINDEX 3
                 --#STATE DEGRADED
                 ::= 305
		 
fmtStorageworksOK    TRAP-TYPE
		ENTERPRISE  eMylexRaidEventInformation
		VARIABLES   {
			a9EventCode,
			a9ControllerNumber,
			a9ChannelNumber,
			a9EventTimeStamp
		}
                  DESCRIPTION
                   "Storage-Works Enclosure is OK"
                 --#SUMMARY "[Event %d ctl %d chn %d Time %d :] Storage-Works Enclosure is OK."
                 --#ARGUMENTS {0,1,2,3}
                 --#SEVERITY INFORMATIONAL
                 --#TIMEINDEX 3
                 --#STATE OPERATIONAL
                 ::= 306
		 
---
--- trap 384 to trap 511 are misc trap
---
fCArrayAssistant58	TRAP-TYPE
		ENTERPRISE  eMylexRaidEventInformation
		VARIABLES   {
			a9EventCode,
			a9ControllerNumber,
			a9EventTimeStamp
		}
                 DESCRIPTION
                  "GAM server software started successfully."
                 --#SUMMARY "[Event %d ctl %d Time %d :] GAM server software started successfully."
                 --#ARGUMENTS {0,1,2}
                 --#SEVERITY INFORMATIONAL
                 --#TIMEINDEX 2
                 --#STATE OPERATIONAL
                 ::= 384

fCArrayAssistant59	TRAP-TYPE
		ENTERPRISE  eMylexRaidEventInformation
		VARIABLES   {
			a9EventCode,
			a9ControllerNumber,
			a9EventTimeStamp
		}
                 DESCRIPTION
                  "Write back error occurred."
                 --#SUMMARY  "[Event %d ctl %d Time %d :] Writeback error. Data corruption may be seen."
                 --#ARGUMENTS {0,1,2}
                 --#SEVERITY CRITICAL
                 --#TIMEINDEX 2
                 --#STATE OPERATIONAL
                 ::= 385

fCArrayAssistant60	TRAP-TYPE
		ENTERPRISE  eMylexRaidEventInformation
		VARIABLES   {
			a9EventCode,
			a9ControllerNumber,
			a9EventTimeStamp
		}
                 DESCRIPTION
                   "State change table full."
                 --#SUMMARY  "[Event %d ctl %d Time %d :] State change table full."
                 --#ARGUMENTS {0,1,2}
                 --#SEVERITY INFORMATIONAL
                 --#TIMEINDEX 2
                 --#STATE OPERATIONAL
                 ::= 386

fCArrayAssistant61	TRAP-TYPE
		ENTERPRISE  eMylexRaidEventInformation
		VARIABLES   {
			a9EventCode,
			a9ControllerNumber,
			a9EventTimeStamp
		}
                 DESCRIPTION
                  "controller is no more functional."
                 --#SUMMARY  "[Event %d ctl %d Time %d :] Controller is not functional any more."
                 --#ARGUMENTS {0,1,2}
                 --#SEVERITY CRITICAL
                 --#TIMEINDEX 2
                 --#STATE NONOPERATIONAL
                 ::= 388

fCArrayAssistant62	TRAP-TYPE
		ENTERPRISE  eMylexRaidEventInformation
		VARIABLES   {
			a9EventCode,
			a9ControllerNumber,
			a9EventTimeStamp
		}
                 DESCRIPTION
                  "controller has been reset."
                 --#SUMMARY "[Event %d ctl %d Time %d :] controller has been reset."
                 --#ARGUMENTS {0,1,2}
                 --#SEVERITY INFORMATIONAL
                 --#TIMEINDEX 2
                 --#STATE OPERATIONAL
                 ::= 389

fCArrayAssistant63	TRAP-TYPE
		ENTERPRISE  eMylexRaidEventInformation
		VARIABLES   {
			a9EventCode,
			a9ControllerNumber,
			a9EventTimeStamp
		}
                 DESCRIPTION
                  "controller is found."
                 --#SUMMARY "[Event %d ctl %d Time %d :] controller is found."
                 --#ARGUMENTS {0,1,2}
                 --#SEVERITY INFORMATIONAL
                 --#TIMEINDEX 2
                 --#STATE OPERATIONAL
                 ::= 390

fCArrayAssistant64	TRAP-TYPE
		ENTERPRISE  eMylexRaidEventInformation
		VARIABLES   {
			a9EventCode,
			a9ControllerNumber,
			a9EventTimeStamp
		}
                 DESCRIPTION
                  "controller is gone."
                 --#SUMMARY "[Event %d ctl %d Time %d :] controller is gone."
                 --#ARGUMENTS {0,1,2}
                 --#SEVERITY INFORMATIONAL
                 --#TIMEINDEX 2
                 --#STATE NONOPERATIONAL
                 ::= 391

fCArrayAssistant65	TRAP-TYPE
		ENTERPRISE  eMylexRaidEventInformation
		VARIABLES   {
			a9EventCode,
			a9ControllerNumber,
			a9EventTimeStamp
		}
                 DESCRIPTION
                  "Battery Backup unit is present."
                 --#SUMMARY "[Event %d ctl %d Time %d :] Battery Backup unit is present."
                 --#ARGUMENTS {0,1,2}
                 --#SEVERITY INFORMATIONAL
                 --#TIMEINDEX 2
                 --#STATE OPERATIONAL
                 ::= 392

fCArrayAssistant66	TRAP-TYPE
		ENTERPRISE  eMylexRaidEventInformation
		VARIABLES   {
			a9EventCode,
			a9ControllerNumber,
			a9EventTimeStamp
		}
                 DESCRIPTION
                  "Battery Power Low."
                 --#SUMMARY "[Event %d ctl %d Time %d :] Battery Power Low."
                 --#ARGUMENTS {0,1,2}
                 --#SEVERITY MAJOR
                 --#TIMEINDEX 2
                 --#STATE DEGRADED
                 ::= 393

fCArrayAssistant67	TRAP-TYPE
		ENTERPRISE  eMylexRaidEventInformation
		VARIABLES   {
			a9EventCode,
			a9ControllerNumber,
			a9EventTimeStamp
		}
                 DESCRIPTION
                  "Battery Power OK."
                 --#SUMMARY "[Event %d ctl %d Time %d :] Battery Power OK."
                 --#ARGUMENTS {0,1,2}
                 --#SEVERITY INFORMATIONAL
                 --#TIMEINDEX 2
                 --#STATE OPERATIONAL
                 ::= 394

fCArrayAssistant68	TRAP-TYPE
		ENTERPRISE  eMylexRaidEventInformation
		VARIABLES   {
			a9EventCode,
			a9ControllerNumber,
			a9EventTimeStamp
		}
                 DESCRIPTION
                  "Controller Powered Off."
                 --#SUMMARY "[Event %d ctl %d Time %d :] Controller Powered Off."
                 --#ARGUMENTS {0,1,2}
                 --#SEVERITY CRITICAL
                 --#TIMEINDEX 2
                 --#STATE NONOPERATIONAL
                 ::= 395

fCArrayAssistant69	TRAP-TYPE
		ENTERPRISE  eMylexRaidEventInformation
		VARIABLES   {
			a9EventCode,
			a9ControllerNumber,
			a9EventTimeStamp
		}
                 DESCRIPTION
                  "Controller Powered On."
                 --#SUMMARY "[Event %d ctl %d Time %d :] Controller Powered On."
                 --#ARGUMENTS {0,1,2}
                 --#SEVERITY INFORMATIONAL
                 --#TIMEINDEX 2
                 --#STATE OPERATIONAL
                 ::= 396
		 
fCArrayAssistant70	TRAP-TYPE
		ENTERPRISE  eMylexRaidEventInformation
		VARIABLES   {
			a9EventCode,
			a9ControllerNumber,
			a9EventTimeStamp
		}
                 DESCRIPTION
                  "Controller Online."
                 --#SUMMARY "[Event %d ctl %d Time %d :] Controller Online."
                 --#ARGUMENTS {0,1,2}
                 --#SEVERITY INFORMATIONAL
                 --#TIMEINDEX 2
                 --#STATE OPERATIONAL
                 ::= 397
		 
fCArrayAssistant71	TRAP-TYPE
		ENTERPRISE  eMylexRaidEventInformation
		VARIABLES   {
			a9EventCode,
			a9ControllerNumber,
			a9EventTimeStamp
		}
                 DESCRIPTION
                  "Controller Offline."
                 --#SUMMARY "[Event %d ctl %d Time %d :] Controller Offline."
                 --#ARGUMENTS {0,1,2}
                 --#SEVERITY CRITICAL
                 --#TIMEINDEX 2
                 --#STATE NONOPERATIONAL
                 ::= 398
		 
fCArrayAssistant72	TRAP-TYPE
		ENTERPRISE  eMylexRaidEventInformation
		VARIABLES   {
			a9EventCode,
			a9ControllerNumber,
			a9EventTimeStamp
		}
                 DESCRIPTION
                  "Controller's Partner is Gone."
                 --#SUMMARY "[Event %d ctl %d Time %d :] Controller's Partner is gone."
                 --#ARGUMENTS {0,1,2}
                 --#SEVERITY CRITICAL
                 --#TIMEINDEX 2
                 --#STATE NONOPERATIONAL
                 ::= 399
		 
fCArrayAssistant73	TRAP-TYPE
		ENTERPRISE  eMylexRaidEventInformation
		VARIABLES   {
			a9EventCode,
			a9ControllerNumber,
			a9EventTimeStamp
		}
                 DESCRIPTION
                  "Battery Backup Recondition Started."
                 --#SUMMARY "[Event %d ctl %d Time %d :] Battery Backup Recondition Started."
                 --#ARGUMENTS {0,1,2}
                 --#SEVERITY INFORMATIONAL
                 --#TIMEINDEX 2
                 --#STATE OPERATIONAL
                 ::= 400
		 
fCArrayAssistant74	TRAP-TYPE
		ENTERPRISE  eMylexRaidEventInformation
		VARIABLES   {
			a9EventCode,
			a9ControllerNumber,
			a9EventTimeStamp
		}
                 DESCRIPTION
                  "Battery Backup Recondition Finished."
                 --#SUMMARY "[Event %d ctl %d Time %d :] Battery Backup Recondition Finished."
                 --#ARGUMENTS {0,1,2}
                 --#SEVERITY INFORMATIONAL
                 --#TIMEINDEX 2
                 --#STATE OPERATIONAL
                 ::= 401
		 
fCArrayAssistant75	TRAP-TYPE
		ENTERPRISE  eMylexRaidEventInformation
		VARIABLES   {
			a9EventCode,
			a9ControllerNumber,
			a9EventTimeStamp
		}
                 DESCRIPTION
                  "Battery Backup Recondition Cancelled."
                 --#SUMMARY "[Event %d ctl %d Time %d :] Battery Backup Recondition Cancelled."
                 --#ARGUMENTS {0,1,2}
                 --#SEVERITY INFORMATIONAL
                 --#TIMEINDEX 2
                 --#STATE OPERATIONAL
                 ::= 402
---
--- trap 512 to trap 640 are system trap
---
gamSystemStarted          TRAP-TYPE
		ENTERPRISE  eMylexRaidEventInformation
		VARIABLES   {
			a9EventCode,
			a9EventTimeStamp
		}
                 DESCRIPTION
                  "GAM server software started successfully."
                 --#SUMMARY "[Event %d Time %d :] GAM server software started successfully."
                 --#ARGUMENTS {0,1}
                 --#SEVERITY INFORMATIONAL
                 --#TIMEINDEX 1
                 --#STATE OPERATIONAL
                 ::= 512
		 
fCArrayAssistant76	TRAP-TYPE
		ENTERPRISE  eMylexRaidEventInformation
		VARIABLES   {
			a9EventCode,
			a9EventTimeStamp
		}
                 DESCRIPTION
                  "GAM driver, internal size table full."
                 --#SUMMARY "[Event %d Time %d :] GAM driver, internal size table full."
                 --#ARGUMENTS {0,1}
                 --#SEVERITY INFORMATIONAL
                 --#TIMEINDEX 1
                 --#STATE OPERATIONAL
                 ::= 513
		 
systemUserLoggedIn          TRAP-TYPE
		ENTERPRISE  eMylexRaidEventInformation
		VARIABLES   {
			a9EventCode,
			a9EventTimeStamp
		}
                 DESCRIPTION
                  "User logged into GAM server environment."
                 --#SUMMARY "[Event %d Time %d :] User logged into GAM server environment."
                 --#ARGUMENTS {0,1}
                 --#SEVERITY INFORMATIONAL
                 --#TIMEINDEX 1
                 --#STATE OPERATIONAL
                 ::= 514
		 
systemUserLoggedOut          TRAP-TYPE
		ENTERPRISE  eMylexRaidEventInformation
		VARIABLES   {
			a9EventCode,
			a9EventTimeStamp
		}
                 DESCRIPTION
                  "User logged out of GAM server environment."
                 --#SUMMARY "[Event %d Time %d :] User logged out of GAM server environment."
                 --#ARGUMENTS {0,1}
                 --#SEVERITY INFORMATIONAL
                 --#TIMEINDEX 1
                 --#STATE OPERATIONAL
                 ::= 515

END
