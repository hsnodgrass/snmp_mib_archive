HPOV-OVIS-MIB DEFINITIONS ::= BEGIN

IMPORTS
  MODULE-IDENTITY, OBJECT-IDENTITY, NOTIFICATION-TYPE, enterprises
  	FROM SNMPv2-SMI;


hp		OBJECT IDENTIFIER ::= { enterprises 11 }
nm		OBJECT IDENTIFIER ::= { hp 2 }
openView	OBJECT IDENTIFIER ::= { nm 17 }

hpOVInternetServices  MODULE-IDENTITY
	LAST-UPDATED "200405190000Z"	
	 ORGANIZATION "Hewlett-Packard, OpenView Internet Services"
	 CONTACT-INFO
		"Support: Hewlett-Packard Response Center
                     Tel: +1 (800) 633-3600"
       
	DESCRIPTION 
	    "HP OpenView Internet Services can be configured to
             send traps for threshold violations."

	::= { openView 16 }

hpOVISTrapVars OBJECT IDENTIFIER ::= { hpOVInternetServices 2 }

hpOVISTargetHost OBJECT-TYPE
	SYNTAX OCTET STRING
	ACCESS accessible-for-notify
 	STATUS current
	DESCRIPTION 
		"Target Hostname"
	::= { hpOVISTrapVars 1 }

hpOVISProbeSystem OBJECT-TYPE
        SYNTAX OCTET STRING
        ACCESS accessible-for-notify
        STATUS current
        DESCRIPTION
                "Probe System"
        ::= { hpOVISTrapVars 2 }

hpOVISProbeType OBJECT-TYPE
        SYNTAX OCTET STRING
        ACCESS accessible-for-notify
        STATUS current
        DESCRIPTION
                "Probe Type"
        ::= { hpOVISTrapVars 3 }

hpOVISAlarmText OBJECT-TYPE
        SYNTAX OCTET STRING
        ACCESS accessible-for-notify
        STATUS current
        DESCRIPTION
                "Alarm Text"
        ::= { hpOVISTrapVars 4 }

hpOVISDrillDownUrl OBJECT-TYPE
	SYNTAX OCTET STRING
	ACCESS accessible-for-notify
	STATUS current
	DESCRIPTION 
		"URL related to this trap"
	::= { hpOVISTrapVars 5 }


hpOVISTraps	 OBJECT IDENTIFIER ::= { hpOVInternetServices 0 }
	--
	-- OVIS Trap Definitions
	--
       hpOVISNormalAlarm NOTIFICATION-TYPE
           OBJECTS    { hpOVISTargetHost,
           				hpOVISProbeSystem,
           				hpOVISProbeType,
           				hpOVISAlarmText,
           				hpOVISDrillDownUrl }
           STATUS     current
           DESCRIPTION "Normal alarm"
           ::= { hpOVISTraps 1 }

       hpOVISWarningAlarm NOTIFICATION-TYPE
           OBJECTS    { hpOVISTargetHost,
           				hpOVISProbeSystem,
           				hpOVISProbeType,
           				hpOVISAlarmText,
           				hpOVISDrillDownUrl }
           STATUS     current
           DESCRIPTION "Warning alarm"
           ::= { hpOVISTraps 2 }

       hpOVISMinorAlarm NOTIFICATION-TYPE
           OBJECTS    { hpOVISTargetHost,
           				hpOVISProbeSystem,
           				hpOVISProbeType,
           				hpOVISAlarmText,
           				hpOVISDrillDownUrl }
           STATUS     current
           DESCRIPTION "Minor alarm"
           ::= { hpOVISTraps 3 }

       hpOVISMajorAlarm NOTIFICATION-TYPE
           OBJECTS    { hpOVISTargetHost,
           				hpOVISProbeSystem,
           				hpOVISProbeType,
           				hpOVISAlarmText,
           				hpOVISDrillDownUrl }
           STATUS     current
           DESCRIPTION "Major alarm"
           ::= { hpOVISTraps 4 }

       hpOVISCriticalAlarm NOTIFICATION-TYPE
           OBJECTS    { hpOVISTargetHost,
           				hpOVISProbeSystem,
           				hpOVISProbeType,
           				hpOVISAlarmText,
           				hpOVISDrillDownUrl }
           STATUS     current
           DESCRIPTION "Critical alarm"
           ::= { hpOVISTraps 5 }

END
