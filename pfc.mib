PATROL-MIB DEFINITIONS ::= BEGIN

        IMPORTS
      TRAP-TYPE
         FROM RFC-1215
        DisplayString
         FROM SNMPv2-TC

                enterprises, IpAddress, TimeTicks, mgmt
              FROM RFC1155-SMI

                OBJECT-TYPE
                           FROM RFC-1212;

                mib-2      OBJECT IDENTIFIER ::= { mgmt 1 }
                 snmp       OBJECT IDENTIFIER ::= { mib-2 11 }

        bmc             OBJECT IDENTIFIER ::= { enterprises 1031 }


        patrolMIB OBJECT IDENTIFIER ::= { bmc 1 }

        --
        -- Agent subtree
        --
        -- This is the main subtree for Patrol MIB
        -- All managed objects on Agent side will be in this subtree

        patrolAgent      OBJECT IDENTIFIER ::= { patrolMIB 1 }

        --
        -- Console subtree
        --
        -- Patrol Console (For Future Use)
        patrolConsole    OBJECT IDENTIFIER ::= { patrolMIB 2 }

        --
        -- Groups in Patrol MIB , Agent/... view
        --

        patrolObjects          OBJECT IDENTIFIER ::= { patrolAgent 1 }
        patrolTraps            OBJECT IDENTIFIER ::= { patrolAgent 2 }

        --In SNMP RowStatus is not defined so here is RowStatus
        --In SNMP V2 remove following defintions.

        PRowStatus ::= INTEGER {
                          active(1),
                          notInService(2),
                          notReady(3),
                          createAndGo(4),
                          createAndWait(5),
                          destroy(6)
        }

   -- parameterOutputMode is of type OutputMode
   -- OutputMode is enumerated as follows

        OutputMode ::= INTEGER {
                          none(0),
                          text(1),
                          gauge(2),
                          graph(3),
                          console(4)
        }

   -- application and parameter state
   -- refer XpwState

        States ::=   INTEGER {
                          ok(0),
                          warn(1),
                          alarm(2),
                          offline(3),
                          void(4)
        }

   -- fields like parameterAutoScale and applInstCreateIcon
   -- are Boolen type

        PBoolean ::=   INTEGER {
                          false(0),
                          true(1)
        }


    -- A primitive support for rpc
    -- setting this variable executes the given command

    agentExecuteCommand OBJECT-TYPE
        SYNTAX      DisplayString
        ACCESS      read-write
        STATUS      mandatory
        DESCRIPTION
            "Executes the PSL command sent in the same message."
    ::= { patrolAgent 3 }


    -- patrolObjects

--    objectsMask OBJECT-TYPE
--        SYNTAX      DisplayString
--        ACCESS      read-write
--        STATUS      obsolete
--        DESCRIPTION
--            "This is a regular expression (see UNIX regexp(5))
--            to match with objectsTable.objectsEntry.objectName.
--            If objectsMask is started from /, all objects are searched
--            from top-level, otherwise - from objectsCwd node.
--            Example: /.* means all object from the tree root
--                     [^/]* means mandatory-level objects only"
--        DEFVAL {"[^/]*"}     all first-level objects, i.e. /FILESYSTEM,
--                             /ORACLE , ...
--    ::= { patrolObjects 1 }

    objectsCwd  OBJECT-TYPE
        SYNTAX      DisplayString
        ACCESS      read-write
        STATUS      mandatory
        DESCRIPTION
            "Current node, used as a root for subtree to be examined."
    ::= { patrolObjects 2 }

    objectsTable OBJECT-TYPE
        SYNTAX          SEQUENCE OF ObjectsEntry
        ACCESS          not-accessible
        STATUS          deprecated
        DESCRIPTION
            "This table is used to get/set Patrol Agent Objects.
            Patrol Agent Objects are nodes (and not leaves) of the
            information tree. Object represents a KM definition."
    ::= { patrolObjects 3 }


    objectsEntry OBJECT-TYPE
        SYNTAX  ObjectsEntry
        ACCESS  not-accessible
        STATUS  mandatory
        DESCRIPTION
            "An objectsEntry contains value and description (in future)
            for a given PSL Agent''s object."

        INDEX   { objectName }
    ::= { objectsTable 1 }

    ObjectsEntry ::= SEQUENCE {
        objectName      DisplayString,  -- name of the object, starting from "/"
        objectDescr     DisplayString,  -- Description (if any)
        objectRowStatus INTEGER         -- Row status for a new row creation
    }

    objectName OBJECT-TYPE
        SYNTAX          DisplayString
        ACCESS          read-only
        STATUS          mandatory
        DESCRIPTION
                "Name of the mandatory object."
    ::= { objectsEntry 1 }

    objectDescr OBJECT-TYPE
        SYNTAX          DisplayString
        ACCESS          read-only
        STATUS          mandatory
        DESCRIPTION
                "Textual description of the mandatory object."
    ::= { objectsEntry 3 }

    objectRowStatus OBJECT-TYPE
        SYNTAX       INTEGER {
                          active(1),
                          notInService(2),
                          notReady(3),
                          createAndGo(4),
                          createAndWait(5),
                          destroy(6) 
			}
        ACCESS          read-write
        STATUS          mandatory
        DESCRIPTION
                "Row status as defined in SNMPv2 - for new row creation control."
    ::= { objectsEntry 4 }


    -- -------------
    -- variables
    -- -------------

    variablesTable OBJECT-TYPE
        SYNTAX          SEQUENCE OF VariablesEntry
        ACCESS      not-accessible
        STATUS          deprecated
        DESCRIPTION
            "This table is used to get/set Patrol Agent Object variables.
            Patrol Agent Object Variables are leaves (and not nodes) of the
            information tree."
    ::= { patrolObjects 5 }


    variablesEntry OBJECT-TYPE
        SYNTAX      VariablesEntry
        ACCESS  not-accessible
        STATUS      mandatory
        DESCRIPTION
            "An variablesEntry contains value and description (in future)
            for a given PSL Agent''s object."
        INDEX   {
             variableName
        }
    ::= { variablesTable 1 }

    VariablesEntry ::= SEQUENCE {
        variableName    DisplayString,
        variableType    DisplayString,
        variableValue   DisplayString,
        variableDesr    DisplayString,
        variableRowStatus INTEGER
    }

    variableName    OBJECT-TYPE
        SYNTAX      DisplayString
        ACCESS      read-only
        STATUS      mandatory
        DESCRIPTION
            "Variable name, with path removed."
    ::= { variablesEntry 2 }

    -- this type should be enumerated, synchronized with values
    -- in symtab.h. Correspondent part in patrol_vars.c (int->string)
    -- should be removed
    variableType    OBJECT-TYPE
        SYNTAX      DisplayString
        ACCESS      read-only
        STATUS      mandatory
        DESCRIPTION
            "A string describing variable type. May be used
            by a sophisticated management to open gauges/graphs/multi-media etc."
    ::= { variablesEntry 3 }

    variableValue   OBJECT-TYPE
        SYNTAX      DisplayString
        ACCESS      read-write
        STATUS      mandatory
        DESCRIPTION
            "Current value of the variable."
    ::= { variablesEntry 4 }

    variableDesr    OBJECT-TYPE
        SYNTAX      DisplayString
        ACCESS      read-write
        STATUS      mandatory
        DESCRIPTION
            "The variable''s text description, 
              a-ka dynamic help about this very variable."
    ::= { variablesEntry 5 }

    variableRowStatus   OBJECT-TYPE
        SYNTAX      INTEGER {
                          active(1),
                          notInService(2),
                          notReady(3),
                          createAndGo(4),
                          createAndWait(5),
                          destroy(6)
        }

        ACCESS      read-write
        STATUS      mandatory
        DESCRIPTION
            "Used for new row creation - according to snmpv2 row craation mechanism."
    ::= { variablesEntry 6 }

    -- --------------
    -- applications
    -- --------------

    applicationsTable OBJECT-TYPE
        SYNTAX          SEQUENCE OF ApplicationsEntry
        ACCESS          not-accessible
        STATUS          deprecated
        DESCRIPTION
            "This table is used to get/set Patrol monitored applications.
            Patrol Agent Applications are nodes of the information tree."
    ::= { patrolObjects 6 }


     applicationsEntry OBJECT-TYPE
        SYNTAX      ApplicationsEntry
        ACCESS      not-accessible
        STATUS      mandatory
        DESCRIPTION
            "An  applicationsEntry contains value and description (in future)
            for a given PSL Agent''s applications."
        INDEX   {
             applicationOid
        }
    ::= { applicationsTable 1 }


    ApplicationsEntry ::= SEQUENCE {
        applicationName          DisplayString,             --
        applicationState         INTEGER,                    --
--        applWorstInst            DisplayString,             --
--        applMasterVersion        DisplayString,             --
        applWorstInst            DisplayString,             --
        applMasterVersion        INTEGER,                   --
        applMinorRevision        INTEGER,                   --
        applicationRowStatus     INTEGER,
        applicationOid           INTEGER (SIZE (0..65535))
    }

    applicationName    OBJECT-TYPE
        SYNTAX         DisplayString
        ACCESS         read-only
        STATUS         mandatory
        DESCRIPTION
            "Application Name."
    ::= { applicationsEntry 1 }

    applicationState OBJECT-TYPE
        SYNTAX      INTEGER {
                          ok(0),
                          warn(1),
                          alarm(2),
                          offline(3),
                          void(4)
        }

        ACCESS      read-only
        STATUS      mandatory
        DESCRIPTION
            "Application State."
    ::= { applicationsEntry 2 }

    applWorstInst   OBJECT-TYPE
        SYNTAX      DisplayString
        ACCESS      read-only
        STATUS      mandatory
        DESCRIPTION
            "Application Worst Instance."
    ::= { applicationsEntry 3 }


    applMasterVersion OBJECT-TYPE
        SYNTAX      INTEGER
        ACCESS      read-only
        STATUS      mandatory
        DESCRIPTION
            "Version number of the application."
    ::= { applicationsEntry 4 }

    applMinorRevision OBJECT-TYPE
        SYNTAX      INTEGER
        ACCESS      read-only
        STATUS      mandatory
        DESCRIPTION
            "Minor revision number of the application."
    ::= { applicationsEntry 5 }

    applicationRowStatus OBJECT-TYPE
        SYNTAX      INTEGER {
                          active(1),
                          notInService(2),
                          notReady(3),
                          createAndGo(4),
                          createAndWait(5),
                          destroy(6)
        }

        ACCESS      read-only
        STATUS      mandatory
        DESCRIPTION
            "Used for new row creation according to snmpv2 row craation mechanism."
    ::= { applicationsEntry 6 }

    applicationOid      OBJECT-TYPE
        SYNTAX          INTEGER
        ACCESS          not-accessible
        STATUS          mandatory
        DESCRIPTION
                "Application Object Id."
    ::= { applicationsEntry 7 }


    -- ----------------------------------
    -- application Instance aka applInst
    -- ----------------------------------

    applInstTable OBJECT-TYPE
        SYNTAX          SEQUENCE OF ApplInstEntry
        ACCESS          not-accessible
        STATUS          deprecated
        DESCRIPTION
            "This table is used to get/set Patrol monitored application Instance.
            Patrol Agent application Instance are nodes of the information tree."
    ::= { patrolObjects 7 }


     applInstEntry OBJECT-TYPE
        SYNTAX      ApplInstEntry
        ACCESS      not-accessible
        STATUS      mandatory
        DESCRIPTION
            "An  applInstEntry contains value and description (in future)
            for a given PSL Agent''s applInst."
       INDEX	{ applicationOid, applInstOid }
    ::= { applInstTable 1 }

    ApplInstEntry ::= SEQUENCE {
   applInstName        DisplayString, --
   applInstRuleState   INTEGER,        --
   applInstStatus      INTEGER,        --
   applInstWorstParam  DisplayString,
   applInstCreateIcon  INTEGER,
   applInstRowStatus   INTEGER,
   applInstOid         INTEGER (SIZE (0..65535)),
   applInstPInstOid    INTEGER (SIZE (0..65535)),
   applInstPApplOid    INTEGER (SIZE (0..65535))
    }

    applInstName    OBJECT-TYPE
        SYNTAX      DisplayString
        ACCESS      read-only
        STATUS      mandatory
        DESCRIPTION
            "Application Instance Name."
    ::= { applInstEntry 1 }

    applInstRuleState   OBJECT-TYPE
        SYNTAX      INTEGER {
                          ok(0),
                          warn(1),
                          alarm(2),
                          offline(3),
                          void(4)
        }

        ACCESS      read-only
        STATUS      mandatory
        DESCRIPTION
            "Application Instance State."
    ::= { applInstEntry 2 }

    applInstStatus  OBJECT-TYPE
        SYNTAX      INTEGER {
                          ok(0),
                          warn(1),
                          alarm(2),
                          offline(3),
                          void(4)
        }

        ACCESS      read-only
        STATUS      mandatory
        DESCRIPTION
            "Application instance status is the worst of rule state and 
            its worst parameter''s status."
    ::= { applInstEntry 3 }

    applInstWorstParam  OBJECT-TYPE
        SYNTAX      DisplayString
        ACCESS      read-only
        STATUS      mandatory
        DESCRIPTION
            "Application instance worst parameter."
    ::= { applInstEntry 4 }

    applInstCreateIcon  OBJECT-TYPE
        SYNTAX      INTEGER
        ACCESS      read-only
        STATUS      mandatory
        DESCRIPTION
            "True means create icons for Application instance(s).
             False means not necessary to create icons for the instance(s)."
    ::= { applInstEntry 5 }

    applInstRowStatus OBJECT-TYPE
        SYNTAX      INTEGER {
                          active(1),
                          notInService(2),
                          notReady(3),
                          createAndGo(4),
                          createAndWait(5),
                          destroy(6)
        }

        ACCESS      read-only
        STATUS      mandatory
        DESCRIPTION
            "Used for new row creation, according to snmpv2 row craation mechanism."
    ::= { applInstEntry 6 }

    applInstOid     OBJECT-TYPE
        SYNTAX          INTEGER
        ACCESS          not-accessible
        STATUS          mandatory
        DESCRIPTION
                "Application Instance Object Id."
    ::= { applInstEntry 7 }

      applInstPInstOid         OBJECT-TYPE
        SYNTAX          INTEGER
        ACCESS          read-only
        STATUS          mandatory
        DESCRIPTION
                "Application instance''s parent object id."
    ::= { applInstEntry 8 }

       applInstPApplOid         OBJECT-TYPE
        SYNTAX          INTEGER
        ACCESS          read-only
        STATUS          mandatory
        DESCRIPTION
                "Application instance''s parent application object id."
    ::= { applInstEntry 9 }


    -- ----------------------------------
    -- parameters
    -- ----------------------------------

    parametersTable OBJECT-TYPE
        SYNTAX          SEQUENCE OF ParametersEntry
        ACCESS      not-accessible
        STATUS          deprecated
        DESCRIPTION
            "This table is used to get/set Patrol application instance
             monitored parameters.
             Patrol Agent parameters are leaves of the information tree."
    ::= { patrolObjects 8 }


     parametersEntry OBJECT-TYPE
        SYNTAX      ParametersEntry
        ACCESS  not-accessible
        STATUS      mandatory
        DESCRIPTION
            "An  ParametersEntry contains value and description (in future)
            for a given PSL Agent''s parameters."
        INDEX { applicationOid, applInstOid, parameterObjId }
    ::= { parametersTable 1 }


    ParametersEntry ::= SEQUENCE {
        parameterName         DisplayString,
        parameterState        INTEGER,
        parameterCurrentTime  TimeTicks,
        parameterCurrentValue DisplayString,
        parameterPollingInt   INTEGER,
        parameterRetries      INTEGER,
        parameterOutputMode   INTEGER,
        parameterAutoScale    INTEGER,
        parameterYaxisMin     INTEGER,
        parameterYaxisMax     INTEGER,
        parameterRowStatus    INTEGER,
        parameterObjId        INTEGER (SIZE (0..65535)),
        parameterIntValue     INTEGER (SIZE (0..65535)),
        parameterActiveStat   INTEGER,
        parameterRunningStat  INTEGER
    }

    parameterName   OBJECT-TYPE
        SYNTAX      DisplayString
        ACCESS      read-only
        STATUS      mandatory
        DESCRIPTION
            "Parameter Name."
    ::= { parametersEntry 1 }

    parameterState  OBJECT-TYPE
        SYNTAX      INTEGER {
                          ok(0),
                          warn(1),
                          alarm(2),
                          offline(3),
                          void(4)
        }

        ACCESS      read-only
        STATUS      mandatory
        DESCRIPTION
            "Parameter State."
    ::= { parametersEntry 2 }

    parameterCurrentTime     OBJECT-TYPE
        SYNTAX          TimeTicks
        ACCESS          read-only
        STATUS          mandatory
        DESCRIPTION
                "Time stamp when current value was produced."
    ::= { parametersEntry 3 }

    parameterCurrentValue  OBJECT-TYPE
        SYNTAX          DisplayString
        ACCESS          read-only
        STATUS          mandatory
        DESCRIPTION
                "Parameter''s current value."
    ::= { parametersEntry 4 }

    parameterPollingInt  OBJECT-TYPE
        SYNTAX      INTEGER
        ACCESS      read-only
        STATUS      mandatory
        DESCRIPTION
            "Parameter''s polling interval."
    ::= { parametersEntry 5 }

    parameterRetries  OBJECT-TYPE
        SYNTAX      INTEGER
        ACCESS      read-only
        STATUS      mandatory
        DESCRIPTION
            "Parameter''s timeout  retries."
    ::= { parametersEntry 6 }

    parameterOutputMode  OBJECT-TYPE
        SYNTAX      INTEGER {
                          none(0),
                          text(1),
                          gauge(2),
                          graph(3),
                          console(4)
	}

        ACCESS      read-only
        STATUS      mandatory
        DESCRIPTION
            "Parameter''s output mode."
    ::= { parametersEntry 7 }

    parameterAutoScale  OBJECT-TYPE
        SYNTAX      INTEGER
        ACCESS      read-only
        STATUS      mandatory
        DESCRIPTION
            "true(1): use automatic scale; false(0):use following YaxisMin and YaxisMax fields to draw y-axis scale."
    ::= { parametersEntry 8 }

    parameterYaxisMin  OBJECT-TYPE
        SYNTAX      INTEGER
        ACCESS      read-only
        STATUS      mandatory
        DESCRIPTION
            "Minimum value for drawing y-axis scale if parameterAutoScale is false(0)."
    ::= { parametersEntry 9 }

    parameterYaxisMax  OBJECT-TYPE
        SYNTAX      INTEGER
        ACCESS      read-only
        STATUS      mandatory
        DESCRIPTION
            "Maximum value for drawing y-axis scale if parameterAutoScale is false(0)."
    ::= { parametersEntry 10 }

    parameterRowStatus OBJECT-TYPE
        SYNTAX      INTEGER {
                          active(1),
                          notInService(2),
                          notReady(3),
                          createAndGo(4),
                          createAndWait(5),
                          destroy(6)
        }

        ACCESS      read-write
        STATUS      mandatory
        DESCRIPTION
            "Used for new row creation - according to snmpv2 row craation mechanism."
    ::= { parametersEntry 11 }

    parameterObjId  OBJECT-TYPE
        SYNTAX      INTEGER
        ACCESS      not-accessible
        STATUS      mandatory
        DESCRIPTION
            "Parameter''s object id."
    ::= { parametersEntry 12 }


    parameterIntValue  OBJECT-TYPE
        SYNTAX      INTEGER
        ACCESS      read-only
        STATUS      mandatory
        DESCRIPTION
           "Integer value of the parameter. Valid only for
      parameters with outputType gauge or graph. (0 for all the others)."
    ::= { parametersEntry 13 }

    parameterActiveStat  OBJECT-TYPE
        SYNTAX      INTEGER
        ACCESS      read-write
        STATUS      mandatory
        DESCRIPTION
           "Boolean value of the parameter explaining whether
      parameter was created as active."
    ::= { parametersEntry 14 }

    parameterRunningStat  OBJECT-TYPE
        SYNTAX      INTEGER
        ACCESS      read-write
        STATUS      mandatory
        DESCRIPTION
           "Boolean value indicating the parameter is either
      running or suspended for the current instance."
    ::= { parametersEntry 15 }


   -- snmp V1 traps
   -- --------------

   patrolTrapText OBJECT-TYPE
      SYNTAX OCTET STRING ( SIZE (0..127))
      ACCESS read-only
      STATUS   optional
      DESCRIPTION
         "String passed from PSL to inform about the trap reason,
         or event information."
   ::= { patrolTraps 1 }


   patrolTrapOrigin OBJECT-TYPE
      SYNTAX OCTET STRING ( SIZE (0..127))
      ACCESS read-only
      STATUS   optional
      DESCRIPTION
         "Name of the object that originated the trap."
   ::= { patrolTraps 2 }


   patrolTrapExtra OBJECT-TYPE
      SYNTAX OCTET STRING ( SIZE (0..127))
      ACCESS read-only
      STATUS   optional
      DESCRIPTION
         "Extra information, usually parameter value."
   ::= { patrolTraps 3 }


   -- --------------------------------------------
   -- Patrol Interested (snmp V1) Managers Table
   -- --------------------------------------------

   piV1mTable OBJECT-TYPE
      SYNTAX    SEQUENCE OF PiV1mEntry
        ACCESS      not-accessible
        STATUS          mandatory
        DESCRIPTION
            "This table keeps information about SNMP V1 management stations,
         interested in receiving traps from the Patrol Agent."
    ::= { patrolTraps 10 }


    piV1mEntry OBJECT-TYPE
        SYNTAX      PiV1mEntry
        ACCESS  not-accessible
           STATUS      mandatory
        DESCRIPTION
            "An piV1mTable describes one SNMP V1 management station interested in
         getting traps from the Patrol Agent."
        INDEX   {
           piV1mIp,
      piV1mPort,
      piV1mCommunity
        }
    ::= { piV1mTable 1 }

    PiV1mEntry ::= SEQUENCE {
      piV1mIp        IpAddress,
      piV1mPort      INTEGER (SIZE (0..65535)),
      piV1mCommunity OCTET STRING (SIZE (0..127)),
      piV1mRowStatus INTEGER
    }

   piV1mIp OBJECT-TYPE
      SYNTAX       IpAddress
      ACCESS    not-accessible
      STATUS      mandatory
      DESCRIPTION
         "IP address of the interested manager."
   ::= { piV1mEntry 1 }

   piV1mPort  OBJECT-TYPE
      SYNTAX INTEGER
      ACCESS    not-accessible
      STATUS  mandatory
      DESCRIPTION
         "Port number of the interested manager."
      DEFVAL { 161 }
   ::= { piV1mEntry 2 }


   piV1mCommunity OBJECT-TYPE
--      SYNTAX OCTET STRING
      SYNTAX OCTET STRING (SIZE (0..127))
           ACCESS    not-accessible
      STATUS  mandatory
      DESCRIPTION
         "Community string for the interested manager."
      DEFVAL { "public" }
   ::= { piV1mEntry 3 }


--   NOTE: Below piV1mRowStatus should have a MAX-ACCESS of "read-create"
--   but due to lack of support for this we have used ACCESS of "read-write"

   piV1mRowStatus OBJECT-TYPE
      SYNTAX    INTEGER {
                          active(1),
                          notInService(2),
                          notReady(3),
                          createAndGo(4),
                          createAndWait(5),
                          destroy(6)
        }

      ACCESS       read-write
      STATUS     mandatory
      DESCRIPTION
         "Row status for row creation/deletion."
   ::= { piV1mEntry 4 }

     patrolInformation       TRAP-TYPE
               ENTERPRISE    patrolTraps
      VARIABLES       { patrolTrapText, patrolTrapOrigin,
                       patrolTrapExtra }
           DESCRIPTION
        "A ''PATROL Information'' trap indicates a PATROL Information event has 
         occurred. Specific information is detailed below."

        --#TYPE "PATROL Information"
        --#SUMMARY "Status is now %d."
        --#ARGUMENTS {3}
        --#SEVERITY INFORMATIONAL
        --#TIMEINDEX 99
         ::= 1

-- This is similar in meaning to patrolTrapV1StateChanged trap.
-- Which trap is sent has something to do with agent configuration,
-- but not sure what exactly that is.
--
     patrolChangeStatus      TRAP-TYPE
               ENTERPRISE    patrolTraps
               VARIABLES     { patrolTrapText, patrolTrapOrigin,
                             patrolTrapExtra }
           DESCRIPTION
        "A ''PATROL State Change'' trap indicates a monitored PATROL object 
         has changed status. Specific information is detailed below."

        --#TYPE "PATROL State Change"
        --#SUMMARY "Status is now %d."
        --#ARGUMENTS {3}
        --#SEVERITY INFORMATIONAL
        --#TIMEINDEX 99

         ::= 2


     patrolWarning      TRAP-TYPE
                        ENTERPRISE    patrolTraps
                        VARIABLES     { patrolTrapText, patrolTrapOrigin,
                                        patrolTrapExtra }
           DESCRIPTION
        "A ''PATROL Warning'' trap indicates a monitored PATROL object is in the 
        warning state. Specific information is detailed below."
        --#TYPE "PATROL Warning"
        --#SUMMARY "Status is now %d."
        --#ARGUMENTS {3}
        --#SEVERITY MAJOR
        --#TIMEINDEX 99

         ::= 4

     patrolAlarm      TRAP-TYPE
                      ENTERPRISE    patrolTraps
      VARIABLES       { patrolTrapText, patrolTrapOrigin,
                        patrolTrapExtra }
           DESCRIPTION
       "A ''PATROL Alarm'' trap indicates a monitored PATROL object is in the 
       alarm state. Specific information is detailed below."
        --#TYPE "PATROL Alarm"
        --#SUMMARY "Status is now %d."
        --#ARGUMENTS {3}
        --#SEVERITY MAJOR
        --#TIMEINDEX 99

         ::= 5


     patrolTrapV1StateChanged TRAP-TYPE
               ENTERPRISE    patrolTraps
      VARIABLES       { patrolTrapText }
           DESCRIPTION
        "A ''PATROL V1 State Change'' trap indicates a monitored PATROL object 
         has changed status. Specific information is detailed below."

        --#TYPE "PATROL V1 State Changed"
        --#SUMMARY "Status is now %d."
        --#ARGUMENTS {1}
        --#SEVERITY INFORMATIONAL
        --#TIMEINDEX 99

         ::= 11


END
