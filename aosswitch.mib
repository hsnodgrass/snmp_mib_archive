-- Copyright (c) Nortel Networks, 2004
-- All rights reserved
-- 
-- HISTORY
-- $Log: aosswitch.mib_raw $
-- Revision submit_cheetah_21240/1 2006/10/12 09:11:55 dilliba
-- Removed range specification for file size object, which is used
-- to specify size for both Bogon and Symantec. For Bogon Max Size
-- is 2MB where as for Symantec 174KB.
-- 
-- Revision submit_cheetah_20599/1 2006/05/23 04:26:27 rvakkala
-- Fixed typo in switch general capacity mib.
-- 
-- Revision submit_cheetah_20578/1 2006/05/19 14:46:14 rvakkala
-- Corrected Misspell which is in my previous checkin.
-- 
-- Revision submit_cheetah_19277/2 2006/05/02 04:44:45 rvakkala
-- Fixed CRQ01007809 Added lack of mibs support to SNMP.
-- 
-- Revision submit_cheetah_18323/2 2006/04/26 04:16:34 rvakkala
-- Fixed CRQ01335381 Added multicast mib support .
-- 
-- Revision submit_cheetah_19723/1 2006/04/17 07:34:55 rvakkala
-- Fixed CRQ01323839 Added agent support for dynamic memory stats.
-- 
-- Revision submit_cheetah_19277/1 2006/05/02 04:34:50 rvakkala
-- Fixed CRQ01007809 Added lack of mibs support to SNMP.
-- 
-- Revision submit_cheetah_18886/2 2006/03/17 06:27:26 rvakkala
-- implementation of SNMP FT error table
-- 
-- Revision submit_cheetah_18325/2 2006/03/14 05:37:01 rvakkala
-- Fixed CRQ01305747, Changed syntax of symantec mibs.
-- 
-- Revision submit_cheetah_18886/1 2006/03/16 18:25:49 rvakkala
-- implementation of SNMP FT error table
-- 
-- Revision submit_cheetah_18416/1 2006/02/28 18:51:09 mmacnt
-- support for MIB var agSymantecGlobalState
-- 
-- Revision submit_cheetah_18325/1 2006/03/14 05:15:37 rvakkala
-- Fixed CRQ01305747 Syntax error for some symantec mibs.
-- 
-- Revision submit_cheetah_18323/1 2006/04/26 04:05:49 rvakkala
-- Fixed CRQ01335815 mcast variables should be added in aosswitch MIB.
-- 
-- Revision submit_cheetah_17722/1 2006/02/03 20:58:58 mmacnt
-- change to support mib vars agTunresCurrentProfile and agSymLicenseSwKeyRenewalPending
-- 
-- Revision submit_cheetah_17614/2 2006/02/01 23:17:51 mmacnt
-- add mib objects -
-- 1. agSymLicenseSwKeyRenewalPending - Symantec License Renewal Pending
-- 2. agTunresCurrentProfile - Tunable Resource Current Profile
-- 
-- Revision submit_cheetah_17625/1 2006/02/01 19:18:10 mp1
-- SNMP instrumentation for IPACL syslog feature
-- 
-- Revision submit_cheetah_16973/2 2006/01/27 23:38:44 angamuth
-- Support for Symantec statistics
-- 
-- Revision submit_cheetah_17416/1 2006/01/26 11:04:12 rvakkala
-- Fixed CRQ01276944 , In SNMP Timeout should be as range like CLI.
-- 
-- Revision submit_cheetah_17123/2 2006/01/14 03:37:22 mp1
-- EUED type changes
-- 
-- Revision submit_cheetah_17055/1 2006/01/13 04:37:17 rvakkala
-- Changed  enum values in description of agApplyConfig in aosswitch.mib.
-- 
-- Revision submit_cheetah_16542/2 2005/12/08 11:35:11 drosu
-- Merging with latest changes.
-- 
-- Revision submit_cheetah_16392/1 2005/12/08 10:23:44 vrincian
-- Lucian Badescu: Add SNMP support for RDCP feature.
-- 
-- Revision submit_cheetah_16542/1 2005/12/08 11:16:59 drosu
-- Added agCurCfgHttpsServerAccess and agNewCfgHttpsServerAccess
-- leaves to enable/disable https access from snmp.
-- 
-- Revision submit_cheetah_16446/1 2005/12/06 17:29:22 drosu
-- Ported submit 16445 from elmo branch
-- 
-- Revision submit_cheetah_16394/1 2005/12/05 18:37:31 bshao
-- CR 1223294: Dynamically compile out MIB objects that are 
-- not applicable to the product.
-- 
-- Revision submit_cheetah_16181/1 2005/11/25 16:35:15 coman
-- Fix for Oscar build, added ELMO_PROJECT for FastFwd objects
-- 
-- Revision submit_cheetah_16445/1 2005/12/06 17:21:33 drosu
-- Increased size for hwSwitchSoftwareVersion
-- 
-- Revision submit_cheetah_16146/1 2005/11/24 11:27:41 coman
-- Added snmp support on Elmo for Port Fast Forwarding (only on external ports)
-- 
-- Revision submit_cheetah_14828/2 2005/11/10 19:35:34 rmundhra
-- Merge with latest.
-- 
-- Revision submit_cheetah_15643/1 2005/11/02 12:21:08 vrincian
-- Added entries and ids for get/put active config.
-- 
-- Revision submit_cheetah_15308/1 2005/10/28 09:13:55 rvakkala
-- Fixed CRQ01217762 "agPortCurCfgPreferred" does not return 
-- right value in Alteon 3408.
-- 
-- Revision submit_cheetah_15219/1 2005/10/14 11:35:28 drosu
-- Changes for adding /cfg/sys/access/user menu in SNMP.
-- 
-- Revision submit_cheetah_15005/1 2005/10/06 15:49:43 angamuth
-- Changed MIB variable symSigFileVersionSeqString to symSigFileVersionSeqNumber.
-- 
-- Revision submit_cheetah_14904/1 2005/10/04 12:17:20 angamuth
-- Changed max size of symSigFileVersionSeqString to 12.
-- 
-- Revision submit_cheetah_14834/1 2005/10/03 16:01:47 angamuth
-- Added symSigFileVersionSeqString MIB.
-- 
-- Revision submit_cheetah_14828/1 2005/11/05 00:39:24 rmundhra
-- Added initial support for auto-discovery.
-- 
-- Revision submit_cheetah_14768/2 2005/09/28 16:27:28 angamuth
-- Merged with previous changes.
-- 
-- Revision submit_cheetah_14775/1 2005/09/28 12:55:47 vrincian
-- Added new leaf agTftpBkCfgFileName in agentConfig->agTftp for the backup
-- configuration filename to be transferred to/from.
-- Added two more possible values for agTftpAction:
-- - bkcfg-get (10) - Download switch backup configuration from a specified
-- file (agTftpBkCfgFileName) on the TFTP server.
-- - bkcfg-put (11) - Upload switch backup configuration to a specified
-- file (agTftpBkCfgFileName) on the TFTP server.
-- 
-- Revision submit_cheetah_14768/1 2005/09/28 16:02:09 angamuth
-- Added symCurCfgDefaultAction and removed symSignatureFileVersion.
-- 
-- Revision submit_cheetah_14741/1 2005/09/27 19:31:56 angamuth
-- Added MIBs for Symantec Licensing, Symantec Info and default action
-- for Symantec configuration.
-- 
-- Revision submit_cheetah_14320/1 2005/09/09 19:37:37 angamuth
-- Moved SymantecState from SLB port table to Security port table
-- and removed PolicyAction MIB variable from SigBwmMappingTable.
-- 
-- Revision submit_cheetah_13685/1 2005/08/11 19:08:59 rrekha
-- More cleanup of excludes from the Makefile. Moved them
-- to #if defines in the corresponding *.ctl_raw and *.mib_raw files.
-- 
-- Revision submit_cheetah_13638/1 2005/08/07 16:22:14 rrekha
-- Fixed Elmo build.
-- 
-- Revision submit_cheetah_13565/1 2005/08/06 00:09:27 rrekha
-- Fixed Zoe build error.
-- 
-- Revision submit_cheetah_13628/1 2005/08/05 22:46:04 rrekha
-- Fixed Q01186464: Add mibs agPortCur/NewCfgTagPVID under the proper flag
-- otherwise for Cheetah getnext operation fails.
-- 
-- Revision submit_cheetah_13563/1 2005/08/05 17:39:32 rrekha
-- Moved all the BWM related flags into the raw files.
-- 
-- Revision submit_cheetah_13555/1 2005/08/03 16:16:22 angamuth
-- Fixed the duplicate MIBs for SYMANTEC.
-- 
-- Revision submit_cheetah_13044/2 2005/08/02 14:54:46 angamuth
-- Merged with previous changes.
-- 
-- Revision submit_cheetah_13132/1 2005/07/13 10:35:58 angamuth
-- Initial check-in for the MIBs to be available. Found under the build flag
-- SYMANTEC. 
-- 
-- Revision submit_cheetah_13044/1 2005/08/02 14:45:45 angamuth
-- Added MIBs for Symantec BWM table.
-- 
-- Revision submit_cheetah_12797/1 2005/06/22 05:53:47 virgiliu
-- MIB object to get switch serial number and other general switch info
-- 
-- Revision submit_cheetah_12000/3 2005/06/17 02:03:54 angamuth
-- Merged with previous previous changes.
-- 
-- Revision submit_cheetah_12688/1 2005/06/16 22:41:38 angamuth
-- Modified MIBs for adding/removing all DoS attacks for a port.
-- 
-- Revision submit_cheetah_12000/2 2005/06/17 02:00:11 angamuth
-- Merged with previous changes.
-- 
-- Revision submit_cheetah_12292/2 2005/06/15 03:43:16 angamuth
-- Merged with previous changes.
-- 
-- Revision submit_cheetah_12539/1 2005/06/09 18:36:31 dtai
-- Q01143008: France Telecom enhancement to allow PVID be tagged/untagged
-- in IBM SOL feature
-- 
-- Revision submit_cheetah_12489/1 2005/06/02 12:22:26 radu
-- Alin T: Added build flags.
-- 
-- Revision submit_cheetah_12088/1 2005/06/01 13:44:18 radu
-- Alin T: Added TACACS+ new features.
-- 
-- Revision submit_cheetah_12302/1 2005/06/01 12:21:11 rvakkala
-- Fixed CR1139837 Added MIB support for RMON syslog.
-- 
-- Revision submit_cheetah_12292/1 2005/06/15 03:26:32 angamuth
-- Added MIB support for DoS Attacks aadd and arem commands.
-- 
-- Revision submit_cheetah_12130/1 2005/05/13 15:16:59 yatsze
-- Allow seclog rate threshold to be 0
-- 
-- Revision submit_cheetah_11908/2 2005/05/13 13:49:40 angamuth
-- Merged with previous changes.
-- 
-- Revision submit_cheetah_11991/2 2005/05/13 05:37:54 angamuth
-- Merged with previous changes.
-- 
-- Revision submit_cheetah_12098/1 2005/05/12 13:55:58 yatsze
-- Rename agDosPortStatsARPBCast to agDosPortStatsARPNuCast
-- 
-- Revision submit_cheetah_11990/2 2005/05/12 10:10:40 rvakkala
-- Added mib support for BWM stats via data/mgmt port
-- 
-- Revision submit_cheetah_12000/1 2005/06/17 01:31:47 angamuth
-- Added MIBs for SNMP File Transfer (SNMP_FT) and IP ACL BOGON Info.
-- 
-- Revision submit_cheetah_11768/4 2005/05/09 09:07:27 rvakkala
-- Added mib support for ntp oper
-- 
-- Revision submit_cheetah_11990/1 2005/05/12 09:34:28 rvakkala
-- Added MIBs for BWM stat mgmt/data port
-- 
-- Revision submit_cheetah_11991/1 2005/05/13 05:30:10 angamuth
-- Removed agSaveNeeded from the leaf agSave.
-- 
-- Revision submit_cheetah_11945/1 2005/05/05 16:14:49 angamuth
-- Fixing build errors for Bert/Zoe.
-- 
-- Revision submit_cheetah_11920/2 2005/05/04 14:05:56 mp1
-- SNMP for XML config
-- 
-- Revision submit_cheetah_11908/1 2005/05/13 12:12:54 angamuth
-- Added MIBs for per port DoS attacks.
-- 
-- Revision submit_cheetah_11669/1 2005/05/03 14:38:44 angamuth
-- Added MIBs for Asynchrnous SNMP Save.
-- 
-- Revision submit_cheetah_11768/3 2005/05/08 08:16:38 rvakkala
-- Added mib support for ntp oper req
-- 
-- Revision submit_cheetah_11768/2 2005/05/08 08:13:13 rvakkala
-- Added mib support for ntp oper req
-- 
-- Revision submit_cheetah_11768/1 2005/05/08 08:04:55 rvakkala
-- Added mibs for ntp oper req
-- 
-- Revision submit_cheetah_11584/1 2005/04/14 21:19:00 yatsze
-- Obsolete security fragment
-- 
-- Revision submit_cheetah_11549/1 2005/04/13 18:57:36 yatsze
-- Rename udploop attack to pepsi attack, add rc8 udp attack and add icmp and igmp type check
-- 
-- Revision submit_cheetah_11512/1 2005/04/12 21:06:20 yatsze
-- Add code for icmpoff DoS attack
-- 
-- Revision submit_cheetah_11468/1 2005/04/08 13:27:53 yatsze
-- Add agDosPortStatsARPBCast and agDosPortStatsGARP
-- 
-- Revision submit_cheetah_11446/1 2005/04/07 17:53:05 mp1
-- dst IP acl BBI & SNMP
-- 
-- Revision submit_cheetah_11200/2 2005/04/06 06:01:14 angamuth
-- Merged with previous changes.
-- 
-- Revision submit_cheetah_11356/1 2005/03/30 21:12:21 yatsze
-- Add PORT_ACCESS MIB objects
-- 
-- Revision submit_cheetah_11345/1 2005/03/30 02:30:17 rrekha
-- Remove the range for the VlanID since it defers in 
-- Cheetah/Elmo/Zoe. Added a new MIB variable vlanMaxVlanID which
-- will give the max. value for the VLAN ID.
-- 
-- Revision submit_cheetah_11200/1 2005/04/06 05:07:16 angamuth
-- Added MIB Objects for DoS Attack Prevention Configuration and DoS Attack Port Statistics.
-- 
-- Revision submit_cheetah_11267/1 2005/03/23 20:47:11 yatsze
-- Add agPortCurCfgPortAlias and agPortNewCfgPortAlias
-- 
-- Revision submit_cheetah_11186/1 2005/03/15 02:47:01 rrekha
-- Remove the following flags from Makefile and added to the *.raw
-- files : WLM_SASP, SLB_SIP, X_FORWARDED_FOR, SLB_PBIND_CIP_NORPORT,
-- SLB_PORT_BIND
-- 
-- Revision submit_cheetah_11025/1 2005/03/02 21:00:31 rrekha
-- SNMP support for WLM SASP.
-- 
-- Revision submit_cheetah_10888/1 2005/02/08 16:49:07 mp1
-- add bogon enable capability
-- 
-- Revision submit_cheetah_10843/1 2005/02/04 18:07:58 mp1
-- implement bogon get
-- 
-- Revision submit_cheetah_10393/1 2005/01/05 21:01:35 mmacnt
-- code reorg - moved from lib/agent
-- 
-- Revision submit_cheetah_10538/1 2004/12/13 19:09:43 yatsze
-- Add agSslprocNewCfgFilt and agSslprocCurCfgFilt
-- aosswitch.mib_raw
-- Revision submit_cheetah_10514/1 2004/12/09 02:41:25 dillibab
-- Added snmp objects to enable/disable syslog and trap for Security pack.
-- 
-- Revision submit_cheetah_10219/2 2004/11/16 18:58:29 dillibab
-- Merged with previous changes.
-- 
-- Revision submit_cheetah_10207/1 2004/11/15 21:07:06 mp1
-- Q01021582 - ability to get and clear ACL stats
-- 
-- Revision submit_cheetah_10219/1 2004/11/16 18:40:20 dillibab
-- Added SNMP object to configure Idle CLI sessions timeout.
-- 
-- Revision submit_cheetah_10057/1 2004/11/03 20:47:29 dillibab
-- Added mib object for port dscp remarking state.
-- 
-- Revision submit_cheetah_10030/1 2004/11/01 22:10:21 bshao
-- CR 1004595: Rework this CR by adding new MIB objects at the
-- end of the table so that the MIB objects will be backward
-- compatible with the older version of AOS.
-- 
-- Revision submit_cheetah_10011/1 2004/10/28 21:42:03 bshao
-- CR 1016054: Changed VLAN range to 0..4095.
-- 
-- Revision submit_cheetah_9994/1 2004/10/27 01:28:21 bshao
-- CR 999848: Fixed Vlan range for Zoe's SNMP configuration.
-- 
-- Revision submit_cheetah_9892/1 2004/10/20 17:38:30 bshao
-- CR 1004595: Added Gig port's mode, and speed configuration
-- options for SNMP.
-- 
-- Revision submit_cheetah_9848/1 2004/10/18 18:40:23 yatsze
-- Obsolete agEnabledAgslbKey mib object
-- 
-- Revision submit_cheetah_9821/1 2004/10/15 00:45:17 ocheung
-- Added support for packet depth for pattern matching.
-- 
-- Revision submit_cheetah_9593/1 2004/09/30 00:29:57 rrekha
-- Added change in the enum as requested by Wendell. This is because the EMS
-- parse cannot handle the long enums. 
-- 
-- Revision submit_cheetah_9626/1 2004/09/29 19:18:01 yatsze
-- Add code to support ptimg and gtimg of boot from BBI and SNMP
-- 
-- Revision submit_cheetah_9269/1 2004/09/07 16:27:00 yatsze
-- Add code for put ts dump
-- 
-- Revision submit_cheetah_9196/1 2004/09/01 21:43:06 rrekha
-- Minor changes for SMIv2 compliance.
-- 
-- Revision submit_cheetah_8961/1 2004/08/19 05:51:49 dillibab
-- Added MIB objects for daylight savings configuration.
-- 
-- Revision submit_cheetah_8858/1 2004/08/12 17:45:46 yatsze
-- Add FTP_SUPPORT code
-- 
-- Revision submit_cheetah_8644/1 2004/08/02 21:42:02 rrekha
-- Fixed Q00949352: Changed range for agCur/NewCfgNTPResyncInterval to 1..44640.
-- 
-- Revision submit_cheetah_8578/1 2004/07/30 00:36:29 rrekha
-- Update the copyright header.
-- 
-- Revision submit_cheetah_8551/1 2004/07/28 00:53:04 rrekha
-- Added mibs needed for zoe.
-- 
-- Revision submit_cheetah_8437/1 2004/07/21 17:20:51 rrekha
-- Obsolete agSlotNumber since it is not used in Cheetah.
-- 
-- Revision submit_cheetah_8433/1 2004/07/20 18:56:29 rrekha
-- Fixed Q00949352: Change agCur/NewCfgNTPResyncInterval to 1..1080.
-- 
-- Revision submit_cheetah_8336/1 2004/07/15 17:12:59 mp1
-- Q00935759 - SFP enhancement, Q00945606 refer to SFP instead of optical
-- 
-- Revision submit_cheetah_8173/2 2004/07/09 09:05:25 dillibab
-- Merged with previous changes.
-- 
-- Revision submit_cheetah_8078/2 2004/07/07 16:04:39 dillibab
-- Merged with previous changes.
-- 
-- Revision submit_cheetah_8173/1 2004/07/09 08:38:02 dillibab
-- Added object for Current system time in ntp statistics.
-- 
-- Revision submit_cheetah_8079/1 2004/06/30 07:17:20 dillibab
-- Corrected Chassis info mib variable name and description.
-- 
-- Revision submit_cheetah_8078/1 2004/07/07 15:28:16 dillibab
-- Added mib objects for nonip for port.
-- 
-- Revision submit_cheetah_7956/1 2004/06/29 02:26:08 dillibab
-- Added mib objects for Chasis info.
-- 
-- Revision submit_cheetah_7669/1 2004/06/08 07:04:51 dillibab
-- Added mib objects to secondary NTP server and NTP statistics.
-- 
-- Revision submit_cheetah_7529/1 2004/05/25 18:48:39 dleu
-- Added SNMP and WebUI support for TACACS+ command 
-- authorization and logging.
-- 
-- Revision submit_cheetah_7524/1 2004/05/24 22:42:53 dleu
-- Added SNMP support for the secondary TACACS+ server 
-- secret.
-- 
-- Revision submit_cheetah_7493/1 2004/05/24 21:38:34 dleu
-- Added SNMP support for the secondary Radius server
-- secret.
-- 
-- Revision submit_cheetah_7421/1 2004/05/18 23:22:58 dleu
-- The correct TACACS+ server timout range should 
-- be 4..15.
-- 
-- Revision submit_cheetah_7342/1 2004/05/18 09:57:05 dillibab
-- Added SNMP Support for TFTP Put Image.
-- 
-- Revision submit_cheetah_7267/1 2004/05/12 14:28:25 yatsze
-- Add mib object mpMemStats
-- 
-- Revision submit_cheetah_7248/1 2004/05/11 21:33:52 hkavulur
-- Added KEY support for inbound link loadbalancing
-- 
-- Revision submit_cheetah_7173/1 2004/05/05 17:29:04 mp1
-- changed MIB description for port to be SFP instead of optical
-- 
-- Revision submit_cheetah_7132/1 2004/05/04 19:13:22 mp1
-- implement SNMP for bkp dumps and https
-- 
-- Revision submit_cheetah_7088/1 2004/04/29 02:00:57 mmacnt
-- CR Q00794609 - add support for a few more hardware related MIB variables
-- 
-- Revision submit_cheetah_6019/1 2004/01/08 00:45:06 rrekha
-- Fixed Q00768791: Obsoleted mib objects agMgmtNewCfgBroadcast and
-- agMgmtCurCfgBroadcast since the broadcast address is now 
-- auto-generated based on the IP/mask.
-- 
-- Revision submit_cheetah_6011/1 2004/01/08 00:11:41 rrekha
-- Fixed Q00747892: Changed the names in enum for agCurCfgSyslog2Sev, agNewCfgSyslog2Sev,
-- agCurCfgSyslogSev and agNewCfgSyslogSev.
-- 
-- Revision submit_cheetah_5944/1 2003/12/18 00:20:40 rrekha
-- Fixed Q00784146: Added a new MIB object snmpClearStats to
-- clear SNMP statistics.
-- 
-- Revision submit_cheetah_5838/1 2003/12/08 19:41:08 yatsze
-- Add agEnabledAgslbKey to handle AGSLB swkey query
-- 
-- Revision submit_cheetah_5693/1 2003/11/16 19:34:33 rrekha
-- Converted MIBs to SMIv2.
-- 
-- Revision submit_cheetah_5313/1 2003/10/15 00:09:05 rrekha
-- Ported from 21.0 branch. 
-- Added LYNX related mibs. Since agSonmp and agSslproc used the 
-- same OID changed agSonmp OID.
-- 
-- Revision submit_cheetah_4828/1 2003/08/27 21:35:34 rrekha
-- Changed udpBlastNewCfgudpPortLowIndx and udpBlastNewCfgudpPortHighIndx
-- to read-only variables are indices are always read only.
-- 
-- Revision submit_cheetah_4631/1 2003/08/18 19:56:33 rrekha
-- Fixed Q00659950: Added MIB objects agCurCfgSyslogSev/agNewCfgSyslogSev
-- and agCurCfgSyslogSev2/agNewCfgSyslogSev2 to set the syslog severity.
-- 
-- Revision submit_cheetah_4435/1 2003/08/12 22:59:56 rrekha
-- Changed name of mib file for cheetah*.mib to aos*.mib.
-- 
-- Revision submit_cheetah_4356/1 2003/08/01 01:44:13 rrekha
-- Added MIB object agNewCfgPgrpDelete to delete pgroup entry.
-- 
-- Revision submit_cheetah_4016/1 2003/07/18 18:55:03 ocheung
-- Added MIB and agent support for /cf/security/seclog and
-- /cf/security/fragment commands.  Also added agent code to
-- handle security swkey.
-- 
-- Revision submit_cheetah_3944/2 2003/07/16 17:50:00 ocheung
-- Merged file.
-- 
-- Revision submit_cheetah_3927/1 2003/07/15 23:43:56 yhuang1
-- fixed Q00711779: ported fix from 21.0 branch.
-- 
-- Revision submit_cheetah_3944/1 2003/07/16 17:43:31 ocheung
-- Added agEnabledSecurityKey for Security Pack feature.
-- 
-- Revision submit_cheetah_3296/1 2003/07/09 22:53:37 rrekha
-- Added new mib objects agMgmtCurCfgSonmp/agMgmtNewCfgSonmp.
-- 
-- Revision submit_cheetah_3761/1 2003/07/02 19:37:31 mp1
-- port agent fix from GE branch
-- 
-- Revision submit_cheetah_3705/1 2003/06/27 00:33:08 rmundhra
-- Implemented the SNMP bitmap for UDP pattern matching.
-- Which represents the strings that are part of this
-- Pattern group.
-- 
-- Revision submit_cheetah_3633/1 2003/06/25 17:52:44 yhuang1
-- IP_ACL: moved under security item.
-- 
-- Revision submit_cheetah_3584/1 2003/06/23 20:07:11 yhuang1
-- UDP_BLAST: moved under security item.
-- 
-- Revision submit_cheetah_3563/2 2003/06/20 23:03:07 rrekha
-- merging out.
-- 
-- Revision submit_cheetah_3569/1 2003/06/19 20:13:35 rmundhra
-- Adding DOS port statistics blat.
-- 
-- Revision submit_cheetah_3563/1 2003/06/20 22:59:42 rrekha
-- Grouped all Pgroup related items under a single node 
-- agPgroup.
-- 
-- Revision submit_cheetah_3476/1 2003/06/19 01:03:57 rmundhra
-- Adding SNMP/WebUI support for UDP pattern matching
-- and DOS attack detection.
-- 
-- Revision submit_cheetah_3379/1 2003/06/10 01:36:52 rrekha
-- Added node agSecurity under agent to be consistent with the 
-- CLI. All the security related menu items will be moved to
-- under this node.
-- 
-- Revision submit_cheetah_3231/1 2003/05/22 23:28:30 rtsai
-- Fixed mib name typo.
-- 
-- Revision submit_cheetah_3122/2 2003/05/16 14:22:00 rtsai
-- Changed the mib description.
-- 
-- Revision submit_cheetah_3122/1 2003/05/16 00:42:22 rtsai
-- Added more mibs for ICMP_RATE_CTRL and ENH_RATE_LIM.
-- 
-- Revision submit_cheetah_3023/1 2003/05/12 18:40:03 yatsze
-- Add mgmt port stats object
-- 
-- Revision submit_cheetah_2881/1 2003/05/07 02:12:42 ocheung
-- Added MIB variables for ICM_RATE_CTRL feature.
-- 
-- Revision submit_cheetah_2752/1 2003/04/30 20:35:38 yatsze
-- Change mgmt port intr and retry to read-write
-- 
-- Revision submit_cheetah_2846/1 2003/04/30 00:23:28 abhijitk
-- Added the MIB for some of the new 21.0 BWM features.
-- 
-- Revision submit_cheetah_2669/1 2003/04/21 13:52:40 yatsze
-- Add mgmt port gw interval and retries
-- 
-- Revision submit_cheetah_2591/1 2003/04/11 21:09:26 rmundhra
-- Obsoleted agCurCfgMgmtNetwork, agNewCfgMgmtNetwork,
-- agCurCfgMgmtMask, agNewCfgMgmtMask as MULTI_MNET 
-- build flag is enabled and must use agMgmtNetTable instead.
-- 
-- Revision submit_cheetah_2506/1 2003/04/04 18:56:47 rmundhra
-- Porting code from Tigon for Scheduled Reboot.
-- 
-- Revision submit_cheetah_2494/3 2003/04/02 21:54:37 mp1
-- added GE pref/backup access
-- 
-- Revision submit_cheetah_2468/2 2003/04/02 18:48:46 rmundhra
-- Merging out.
-- 
-- Revision submit_cheetah_2461/2 2003/04/01 04:01:30 mp1
-- changes to MIB for GE Cheetah
-- 
-- Revision submit_cheetah_2468/1 2003/04/02 18:43:00 rmundhra
-- Added MULTI_MNET MIB objects.
-- 
-- Revision submit_cheetah_2362/1 2003/03/31 18:14:18 rmundhra
-- Porting SNMP Trap Interface from Tigon.
-- 
-- Revision submit_cheetah_2168/1 2003/03/24 18:25:35 sukhvipa
-- Added TACACS snmp support.
-- 
-- Revision submit_cheetah_2293/1 2003/03/15 01:05:02 rrekha
-- Added agCurCfgSonmpSrcIf and agNewCfgSonmpSrcIf.
-- 
-- Revision submit_cheetah_2244/1 2003/03/11 21:31:08 andyrao
-- Defined the MIB objects agCurCfgNortelMultipleStgMode and
-- agNewCfgNortelMultipleStpMode.
-- 
-- Revision submit_cheetah_1919/1 2003/02/05 20:07:00 rrekha
-- Changed the include paths for integrating support
-- for SNMP V3 Windmanage Stack.
-- 
-- Revision submit_cheetah_1620/1 2002/12/04 21:56:40 rmundhra
-- Fixed CR Q00574195: EMS: Port Ena/Dis does not
-- seem to work.
-- Added SNMP support for /oper/port x commands.
-- 
-- Revision submit_cheetah_1544/1 2002/11/20 00:24:03 rrekha
-- Fixed Q00542489: Added mib object agClearFlashDump to clear the 
-- dump.
-- 
-- Revision submit_cheetah_1520/1 2002/11/16 00:20:24 rrekha
-- Added mib objects agMgmtCurCfgDns/agMgmtNewCfgDns.
-- 
-- Revision submit_cheetah_1368/1 2002/10/24 20:14:46 rrekha
-- Fixed Q00546514: Added missing SP maintenance statistics.
-- 
-- Revision submit_cheetah_1329/1 2002/10/22 02:14:49 rrekha
-- Added mib objects to get mgmt port info.
-- 
-- Revision submit_cheetah_1324/1 2002/10/21 23:23:01 rrekha
-- Fixed typo in pktStatsDiscards description.
-- 
-- Revision submit_cheetah_1286/1 2002/10/17 23:48:45 rrekha
-- Fixed Q00543161: Remove coldReset/warmReset from enum in agReset
-- as cheetah has only one reset.
-- 
-- Revision submit_cheetah_1248/1 2002/10/16 16:40:59 rmundhra
-- Fixed CR Q00536352 & CR Q00538316: EMS & WebUI
-- not able to view Man port stats.
-- 
-- Revision submit_cheetah_1231/1 2002/10/14 23:25:33 rmundhra
-- Fixed CR Q00540448: WebUI: always shows speed as
-- 10 and shows flow control for Man port.
-- 
-- Removed flow control as its been removed from CLI.
-- 
-- Revision submit_cheetah_1148/2 2002/10/11 22:48:42 rmundhra
-- Merged Rekha S. changes.
-- 
-- Revision submit_cheetah_1165/1 2002/10/10 18:39:31 rrekha
-- Added MIB object pktStatsDiscards.
-- 
-- Revision submit_cheetah_1150/1 2002/10/07 23:38:06 rrekha
-- Fixed Q00534536: Added agCurCfgTelnetServerPort/agNewCfgTelnetSeverPort.
-- 
-- Revision submit_cheetah_1124/1 2002/10/06 19:02:56 rrekha
-- Added objects for mgmt port defaults, agTfptPort for user input of data/mgmt
-- port for tftp.
-- Removed agMgmtPortDelete and agCurCfgNtpPort/agNewCfgNtpPort.
-- 
-- Revision submit_cheetah_1114/1 2002/10/04 00:38:46 rrekha
-- Added agCurCfgSnmpTimeout/agNewCfgSnmpTimeout.
-- Removed seperate timeout for apply, diff and dump.
-- 
-- Revision submit_cheetah_1068/1 2002/10/01 01:16:19 rrekha
-- Changed value of clear in enum to 2 to be consistent with 
-- other mibs as per Wendell's request.
-- 
-- Revision submit_cheetah_1058/1 2002/09/30 18:51:13 rrekha
-- Fixed Q00529961: Remove agNewCfgSyslogTrapIsd/agCurCfgSyslogTrapIsd.
-- 
-- Revision submit_cheetah_959/1 2002/09/18 23:50:41 rrekha
-- Added MIB objects and method routines for configuration dump.
-- 
-- Revision submit_cheetah_900/1 2002/09/09 21:30:50 rrekha
-- Added more description to agApplyConfig and agDiffState 
-- variables.
-- 
-- Revision submit_cheetah_833/1 2002/09/03 20:59:13 rmundhra
-- Fixed CR Q00512335: EMS cannot provision NTP to use
-- management port or data port.
-- Fixed CR Q00512343: WebUI cannot provision NTP to use
-- management port or data port.
-- 
-- Revision submit_cheetah_787/1 2002/08/28 20:08:54 rrekha
-- Added mib variables agHwTemperatureStatus and agHwFanStatus.
-- Removed old mib variables agHwPowerSupplyStatus and agHwSensor1Temp
-- as they are no longer available in Cheetah.
-- 
-- Revision submit_cheetah_649/1 2002/08/16 02:10:54 rrekha
-- Added MIB objects and method routines for management port 
-- support.
-- 
-- Revision submit_cheetah_507/1 2002/07/31 17:44:56 rrekha
-- Correct descriptions for pkt statistics.
-- 
-- Revision submit_cheetah_501/1 2002/07/29 23:26:09 rrekha
-- Added mib objects for ptk alloc hi-watermark statistics.
-- Remove unused mib objects agTftpServerIpAddr and agTftpDownload.
-- 
-- Revision submit_cheetah_405/1 2002/07/22 18:32:21 rmundhra
-- Fixed Q00487022: EMS: There should be OSPF syslog
-- messages implemented under Syslog-Trap.
-- 
-- Revision submit_cheetah_365/1 2002/07/16 19:01:51 rrekha
-- Ported NTP changes for GE_LATEST.
-- Changed ntp timezone setting from hours to hours:minutes, to support 
-- locales with a non-zero minute offset.
-- 
-- Revision submit_cheetah_176/1 2002/06/20 23:47:50 rmundhra
-- Added mib objects to clear the port statistics.
-- 
-- Revision submit_cheetah_162/1 2002/06/19 18:56:00 rrekha
-- Added entry 'failed' to agApplyConfig enum.
-- 
-- Revision submit_cheetah_81/1 2002/06/18 23:29:17 rrekha
-- Added a new node agApply to support apply warning/error messages
-- via SNMP.
-- 
-- Revision ch_1_0_0_dev/11 2002/06/04 18:55:00 rrekha
-- Fixed CR Q00436747: Ported fix from ge_latest.
-- Change type for pktStatsMediums, pktStatsJumbos, pktStatsSmalls to Gauge.
-- Added better descpritions for pktStats.
-- 
-- Revision ch_1_0_0_dev/10 2002/06/04 02:21:46 rrekha
-- Added remaining SP maint statistics.
-- 
-- Revision ch_1_0_0_dev/9 2002/06/03 20:29:21 rrekha
-- Added MIB objects for SP maint and CPU utilization statistics.
-- 
-- Revision ch_1_0_0_dev/8 2002/05/31 01:24:12 rrekha
-- Added node agDiff for SNMP diff support.
-- 
-- Revision ch_1_0_0_dev/7 2002/05/15 21:55:36 rrekha
-- Removed memStats as they no longer apply.
-- 
-- Revision ch_1_0_0_dev/6 2002/05/09 21:00:53 smiao
-- Removed TEMP_REMOVE_FOR_CHEETAH flag. Broght back CPU utilization stats.
-- 
-- Revision ch_1_0_0_dev/5 2002/04/30 20:42:46 rrekha
-- Added agSyslogMsgTable for the list of syslog messages.
-- 
-- Revision ch_1_0_0_dev/4 2002/04/25 01:04:49 rrekha
-- Removed mib objects agCurCfgSpanningTree/agNewCfgSpanningTree as
-- they are no longer used. 
-- Rearranged nodes under agGeneralGroup and agGeneralConfig group
-- into more meaningful groups : agSystem, agTftp, agNtp, agSyslog.
-- 
-- Revision ch_1_0_0_dev/3 2002/04/23 21:49:30 smiao
-- Renamed node cheetah to aws-switches.
-- 
-- Revision ch_1_0_0_dev/2 2002/04/09 18:03:04 ocheung
-- Bring back pkt stats for jumbo frames.
-- 
-- Revision ch_1_0_0_dev/1 2002/03/07 19:01:57 smiao
-- Removed unnecssary MIB objects for CHEEATH.
-- 
-- Revision ch10latest_smiao/2 2002/02/13 01:41:50 smiao
-- 	Initial checked in for cheetah MIB files.
-- 
-- $EndLog$
-- 
--

ALTEON-CHEETAH-SWITCH-MIB DEFINITIONS ::= BEGIN

IMPORTS
    MODULE-IDENTITY, OBJECT-TYPE, Integer32, Counter32, Gauge32,
    IpAddress, TimeTicks
        FROM SNMPv2-SMI
    DisplayString, PhysAddress
        FROM SNMPv2-TC
    aws-switch 
        FROM ALTEON-ROOT-MIB;

agent MODULE-IDENTITY
    LAST-UPDATED "200409010000Z" --  1 September, 2004
    ORGANIZATION "Nortel Networks"
    CONTACT-INFO "Rekha Singamsetty
                  Suresh Batchu

                  Nortel Networks
                  4655 Great America Parkway
                  Santa Clara CA 95054

                  +1 408 495 2400
                  rrekha@nortelnetworks.com
                  sbatchu@nortelnetworks.com"
    DESCRIPTION
        "The MIB module for the Alteon OS Switch."
    REVISION "200409010000Z"     -- 1 September, 2004
    DESCRIPTION
        "Added revision clause for SMIv2 compliance."
    ::= { aws-switch 1 }

agentConfig       OBJECT IDENTIFIER ::= { agent 1 }
agentStats        OBJECT IDENTIFIER ::= { agent 2 }
agentInfo         OBJECT IDENTIFIER ::= { agent 3 }
agentOper         OBJECT IDENTIFIER ::= { agent 4 }

agSystem          OBJECT IDENTIFIER ::= { agentConfig 1 }
agPortConfig      OBJECT IDENTIFIER ::= { agentConfig 2 }
agRadiusConfig    OBJECT IDENTIFIER ::= { agentConfig 3 }
agNTP	          OBJECT IDENTIFIER ::= { agentConfig 4 }
agSyslog          OBJECT IDENTIFIER ::= { agentConfig 5 }
agTrapHost        OBJECT IDENTIFIER ::= { agentConfig 6 }
agTftp            OBJECT IDENTIFIER ::= { agentConfig 7 }
agApply           OBJECT IDENTIFIER ::= { agentConfig 8 }
agMgmt            OBJECT IDENTIFIER ::= { agentConfig 9 }
agSslproc         OBJECT IDENTIFIER ::= { agentConfig 10 }
agTacacsConfig    OBJECT IDENTIFIER ::= { agentConfig 11 }
agMgmtNetConfig   OBJECT IDENTIFIER ::= { agentConfig 12 }
agBoot            OBJECT IDENTIFIER ::= { agentConfig 13 }
agSecurity        OBJECT IDENTIFIER ::= { agentConfig 14 }
agSonmp           OBJECT IDENTIFIER ::= { agentConfig 15 }
agPortAccessCfg   OBJECT IDENTIFIER ::= { agentConfig 16 }
agSave		  OBJECT IDENTIFIER ::= { agentConfig 17 }
agFileTransfer	  OBJECT IDENTIFIER ::= { agentConfig 18 }


agPgroup          OBJECT IDENTIFIER ::= { agSecurity 1 }
ipAclCfg          OBJECT IDENTIFIER ::= { agSecurity 3 }
udpBlastCfg       OBJECT IDENTIFIER ::= { agSecurity 4 }
secGeneralCfg     OBJECT IDENTIFIER ::= { agSecurity 5 }
dosAttackPrevCfg  OBJECT IDENTIFIER ::= { agSecurity 6 }
ipDstAclCfg       OBJECT IDENTIFIER ::= { agSecurity 7 }
symantecCfg       OBJECT IDENTIFIER ::= { agSecurity 8 }

pktStats	  OBJECT IDENTIFIER ::= { agentStats 1 }
mpCpuStats	  OBJECT IDENTIFIER ::= { agentStats 2 }
portStats	  OBJECT IDENTIFIER ::= { agentStats 3 }
spStats	          OBJECT IDENTIFIER ::= { agentStats 4 }
mgmtStats	  OBJECT IDENTIFIER ::= { agentStats 5 }
securityStats	  OBJECT IDENTIFIER ::= { agentStats 6 }
agClearStats	  OBJECT IDENTIFIER ::= { agentStats 7 }
mpMemStats        OBJECT IDENTIFIER ::= { agentStats 8 }
ntpStats          OBJECT IDENTIFIER ::= { agentStats 9 }
portMirrorStats   OBJECT IDENTIFIER ::= { agentStats 11 }

hardware          OBJECT IDENTIFIER ::= { agentInfo 1 }
portInfo          OBJECT IDENTIFIER ::= { agentInfo 2 }
swKeyInfo         OBJECT IDENTIFIER ::= { agentInfo 3 }
agDiff            OBJECT IDENTIFIER ::= { agentInfo 4 }
agCfgDump         OBJECT IDENTIFIER ::= { agentInfo 5 }
mgmtInfo          OBJECT IDENTIFIER ::= { agentInfo 6 }
securityInfo      OBJECT IDENTIFIER ::= { agentInfo 7 }
capacityInfo      OBJECT IDENTIFIER ::= { agentInfo 9 }

agNTPOper         OBJECT IDENTIFIER ::= { agentOper 2 }

-- There are two configuration blocks for Alteon switches.
-- The "current_config" reflects the configuration parameters that the
-- switch is operating on and it is read-only.  The objects with "CurCfg"
-- in the name are reflect to this configuration block.
--
-- The "new_config" accepts user configurations on set.  The objects with
-- "NewCfg" in the name are reflect to this configuration block.
--
-- The newly set configurations will not take effect until a "apply"
-- command has been issued (See agApplyConfiguration object defined in
-- ALTEON-PRIVATE-MIBS).
--
-- The newly set configurations will not be saved through next restarting
-- of the switch unless a "save" command has been issued (See
-- agSaveConfiguration object defined in ALTEON-PRIVATE-MIBS).

-- Hardware Information

hwPartNumber OBJECT-TYPE
    SYNTAX  DisplayString (SIZE(0..16))
    MAX-ACCESS  read-only
    STATUS  current
    DESCRIPTION
        "The hardware part number of the Alteon Switch." 
    ::= { hardware 1 }

hwRevision OBJECT-TYPE
    SYNTAX DisplayString (SIZE(0..16))
    MAX-ACCESS read-only
    STATUS current
    DESCRIPTION
	"The hardware revision.  If the revision is not
	 available, a zero length string should be returned."
    ::= { hardware 2 }

hwTemperatureStatus OBJECT-TYPE
    SYNTAX  INTEGER {
        ok(1),
        exceed(2)
        }
    MAX-ACCESS  read-only
    STATUS  current
    DESCRIPTION
	"The status of the temperature sensor."
    ::= { hardware 3 }

hwFanStatus OBJECT-TYPE
    SYNTAX  INTEGER {
        ok(1),
        fail(2)
        }
    MAX-ACCESS  read-only
    STATUS  current
    DESCRIPTION
	"The status of the fan."
    ::= { hardware 4 }


switchCapL2Info          OBJECT IDENTIFIER ::= { capacityInfo  1 }
switchCapL3Info          OBJECT IDENTIFIER ::= { capacityInfo  2 }
switchCapSlbInfo         OBJECT IDENTIFIER ::= { capacityInfo  3 }
switchCapSlbPortInfo     OBJECT IDENTIFIER ::= { capacityInfo  4 }
switchCapBwmInfo         OBJECT IDENTIFIER ::= { capacityInfo  5 }
switchCapSecInfo         OBJECT IDENTIFIER ::= { capacityInfo  6 }
switchCapGeneralInfo     OBJECT IDENTIFIER ::= { capacityInfo  7 }

switchCapFDBMaxEnt OBJECT-TYPE
    SYNTAX Integer32
    MAX-ACCESS read-only
    STATUS current
    DESCRIPTION
        "Maximum number of entries for FDB in device."
    ::= { switchCapL2Info 1 }

switchCapFDBCurrEnt OBJECT-TYPE
    SYNTAX Integer32
    MAX-ACCESS read-only
    STATUS current
    DESCRIPTION
        "Current number of entries for FDB in device."
    ::= { switchCapL2Info 2 }

switchCapFDBPerSPMaxEnt OBJECT-TYPE
    SYNTAX Integer32
    MAX-ACCESS read-only
    STATUS current
    DESCRIPTION
        "Maximun number of entries for FDB per SP in device."
    ::= { switchCapL2Info 3 }

switchCapVlanMaxEnt OBJECT-TYPE
    SYNTAX Integer32
    MAX-ACCESS read-only
    STATUS current
    DESCRIPTION
        "Maximum number of entries for vlan in device."
    ::= { switchCapL2Info 4 }

switchCapVlanCurrEnt OBJECT-TYPE
    SYNTAX DisplayString
    MAX-ACCESS read-only
    STATUS current
    DESCRIPTION
        "Current number of entries for vlan in device, the value
         is in the form x(y) where 'x' indicates number of current
         entries and 'y' indicates number of enabled entries only."
    ::= { switchCapL2Info 5 }

switchCapStaticTrunkGrpsMaxEnt OBJECT-TYPE
    SYNTAX Integer32
    MAX-ACCESS read-only
    STATUS current
    DESCRIPTION
        "Maximum number of entries for static trunk groups in device."
    ::= { switchCapL2Info 6 }

switchCapStaticTrunkGrpsCurrEnt OBJECT-TYPE
    SYNTAX DisplayString
    MAX-ACCESS read-only
    STATUS current
    DESCRIPTION
        "Current number of entries for static trunk groups
         in device, the value is in the form x(y) where 'x'
         indicates number of current entries and 'y' indicates
         number of enabled entries only."
    ::= { switchCapL2Info 7 }

switchCapLACPTrunkGRs OBJECT-TYPE
    SYNTAX Integer32
    MAX-ACCESS read-only
    STATUS current
    DESCRIPTION
        "LACP Trunk groups in device."
    ::= { switchCapL2Info 8 }

switchCapTrunksperTrunkGR OBJECT-TYPE
    SYNTAX Integer32
    MAX-ACCESS read-only
    STATUS current
    DESCRIPTION
        "Trunks per trunk group in device."
    ::= { switchCapL2Info 9 }

switchCapSTGsMaxEnt OBJECT-TYPE
    SYNTAX Integer32
    MAX-ACCESS read-only
    STATUS  current
    DESCRIPTION
        "Maximum number of entries for STG in device."
    ::= { switchCapL2Info 10 }

switchCapSTGsCurrEnt OBJECT-TYPE
    SYNTAX DisplayString
    MAX-ACCESS read-only
    STATUS current
    DESCRIPTION
        "Current number of entries for STG in device, the
         value is in the form x(y) where 'x' indicates number
         of current entries and 'y' indicates number of
         enabled entries only."
    ::= { switchCapL2Info 11 }

switchCapPortTeamsMaxEnt OBJECT-TYPE
    SYNTAX Integer32
    MAX-ACCESS read-only
    STATUS  current
    DESCRIPTION
        "Maximum number of entries for port teams in device."
    ::= { switchCapL2Info 12 }

switchCapPortTeamsCurrEnt OBJECT-TYPE
    SYNTAX DisplayString
    MAX-ACCESS read-only
    STATUS current
    DESCRIPTION
        "Current number of entries for port teams in device, the
         value is in the form x(y) where 'x' indicates number
         of current entries and 'y' indicates number of
         enabled entries only."
    ::= { switchCapL2Info 13 }

switchCapMonitorPorts OBJECT-TYPE
    SYNTAX Integer32
    MAX-ACCESS read-only
    STATUS current
    DESCRIPTION
        "Maximum number of monitor ports."
    ::= { switchCapL2Info 14 }

switchCapIpIntfMaxEnt OBJECT-TYPE
    SYNTAX Integer32
    MAX-ACCESS read-only
    STATUS current
    DESCRIPTION
        "Maximum number of entries for interfaces in device."
    ::= { switchCapL3Info 1 }

switchCapIpIntfCurrEnt OBJECT-TYPE
    SYNTAX DisplayString
    MAX-ACCESS read-only
    STATUS current
    DESCRIPTION
        "Current number of entries for interfaces in device, the
         value is in the form x(y) where 'x' indicates number
         of current entries and 'y' indicates number of
         enabled entries only."
    ::= { switchCapL3Info 2 }

switchCapIpGWMaxEnt OBJECT-TYPE
    SYNTAX DisplayString
    MAX-ACCESS read-only
    STATUS current
    DESCRIPTION
        "Maximum number of entries for gateways in device, the
         value is in the form x+y where 'x' indicates number
         of default gateways and 'y' indicates number of
         VLAN gateways."
    ::= { switchCapL3Info 3 }

switchCapIpGWCurrEnt OBJECT-TYPE
    SYNTAX DisplayString
    MAX-ACCESS read-only
    STATUS current
    DESCRIPTION
        "Current number of entries for gateways in device, the
         value is in the form x+y(a+b) where 'x' indicates number
         of current default gateways, 'y' indicates number of
         current VLAN gateways, 'a' indicates number
         of  enabled default gateways, 'b' indicates number of
         enabled VLAN gateways only."
    ::= { switchCapL3Info 4 }

switchCapIpRoutesMaxEnt OBJECT-TYPE
    SYNTAX Integer32
    MAX-ACCESS read-only
    STATUS current
    DESCRIPTION
        "Maximum number of entries for routes in device."
    ::= { switchCapL3Info 5 }

switchCapIpRoutesCurrEnt OBJECT-TYPE
    SYNTAX Integer32
    MAX-ACCESS read-only
    STATUS current
    DESCRIPTION
        "Current number of entries for routes in device."
    ::= { switchCapL3Info 6 }

switchCapIpStaticRoutesMaxEnt OBJECT-TYPE
    SYNTAX Integer32
    MAX-ACCESS read-only
    STATUS current
    DESCRIPTION
        "Maximum number of entries for static routes in device."
    ::= { switchCapL3Info 7 }

switchCapIpStaticRoutesCurrEnt OBJECT-TYPE
    SYNTAX Integer32
    MAX-ACCESS read-only
    STATUS current
    DESCRIPTION
        "Current number of entries for static routes in device."
    ::= { switchCapL3Info 8 }

switchCapIpARPMaxEnt OBJECT-TYPE
    SYNTAX Integer32
    MAX-ACCESS read-only
    STATUS current
    DESCRIPTION
        "Maximum number of entries for ARP in device."
    ::= { switchCapL3Info 9 }

switchCapIpARPCurrEnt OBJECT-TYPE
    SYNTAX Integer32
    MAX-ACCESS read-only
    STATUS current
    DESCRIPTION
        "Current number of entries for ARP in device."
    ::= { switchCapL3Info 10 }

switchCapIpStaticARPMaxEnt OBJECT-TYPE
    SYNTAX Integer32
    MAX-ACCESS read-only
    STATUS current
    DESCRIPTION
        "Maximum number of entries for static ARP in device."
    ::= { switchCapL3Info 11 }

switchCapIpStaticARPCurrEnt OBJECT-TYPE
    SYNTAX Integer32
    MAX-ACCESS read-only
    STATUS current
    DESCRIPTION
        "Current number of entries for static ARP in device."
    ::= { switchCapL3Info 12 }

switchCapLocNetsMaxEnt OBJECT-TYPE
    SYNTAX Integer32
    MAX-ACCESS read-only
    STATUS current
    DESCRIPTION
        "Maximum number of entries for local nets in device."
    ::= { switchCapL3Info 13 }

switchCapLocNetsCurrEnt OBJECT-TYPE
    SYNTAX Integer32
    MAX-ACCESS read-only
    STATUS current
    DESCRIPTION
        "Current number of entries for local nets in device."
    ::= { switchCapL3Info 14 }

switchCapDNSSerMaxEnt OBJECT-TYPE
    SYNTAX Integer32
    MAX-ACCESS read-only
    STATUS current
    DESCRIPTION
        "Maximum number of entries for DNS servers in device."
    ::= { switchCapL3Info 15 }

switchCapDNSSerCurrEnt OBJECT-TYPE
    SYNTAX Integer32
    MAX-ACCESS read-only
    STATUS current
    DESCRIPTION
        "Current number of entries for DNS servers in device."
    ::= { switchCapL3Info 16 }

switchCapBootpSerMaxEnt OBJECT-TYPE
    SYNTAX Integer32
    MAX-ACCESS read-only
    STATUS current
    DESCRIPTION
        "Maximum number of entries for BOOTP servers in device."
    ::= { switchCapL3Info 17 }

switchCapBootpSerCurrEnt OBJECT-TYPE
    SYNTAX Integer32
    MAX-ACCESS read-only
    STATUS current
    DESCRIPTION
        "Current number of entries for BOOTP servers in device."
    ::= { switchCapL3Info 18 }

switchCapRIPIntfMaxEnt OBJECT-TYPE
    SYNTAX Integer32
    MAX-ACCESS read-only
    STATUS current
    DESCRIPTION
        "Maximum number of entries of RIP interfaces in device."
    ::= { switchCapL3Info 19 }

switchCapRIPIntfCurrEnt OBJECT-TYPE
    SYNTAX Integer32
    MAX-ACCESS read-only
    STATUS current
    DESCRIPTION
        "Current number of entries of RIP interfaces in device."
    ::= { switchCapL3Info 20 }

switchCapOSPFIntfMaxEnt OBJECT-TYPE
    SYNTAX Integer32
    MAX-ACCESS read-only
    STATUS current
    DESCRIPTION
        "Maximum number of entries for OSPF interfaces in device."
    ::= { switchCapL3Info 21 }

switchCapOSPFIntfCurrEnt OBJECT-TYPE
    SYNTAX DisplayString
    MAX-ACCESS read-only
    STATUS current
    DESCRIPTION
        "Current number of entries for OSPF interfaces in device, the
         value is in the form x(y) where 'x' indicates number
         of current entries and 'y' indicates number of
         enabled entries only."
    ::= { switchCapL3Info 22 }

switchCapOSPFAreasMaxEnt OBJECT-TYPE
    SYNTAX Integer32
    MAX-ACCESS read-only
    STATUS current
    DESCRIPTION
        "Maximum number of entries for OSPF areas in device."
    ::= { switchCapL3Info 23}

switchCapOSPFAreasCurrEnt OBJECT-TYPE
    SYNTAX DisplayString
    MAX-ACCESS read-only
    STATUS  current
    DESCRIPTION
        "Current number of entries for OSPF areas in device, the
         value is in the form x(y) where 'x' indicates number
         of current entries and 'y' indicates number of
         enabled entries only."
    ::= { switchCapL3Info 24 }

switchCapOSPFSummaryRangesMaxEnt OBJECT-TYPE
    SYNTAX Integer32
    MAX-ACCESS read-only
    STATUS current
    DESCRIPTION
        "Maximum number of entries for OSPF summary ranges in device."
    ::= { switchCapL3Info 25 }

switchCapOSPFSummaryRangesCurrEnt OBJECT-TYPE
    SYNTAX DisplayString
    MAX-ACCESS read-only
    STATUS current
    DESCRIPTION
        "Current number of entries for OSPF summary ranges in
         device, the value is in the form x(y) where 'x' indicates
         number of current entries and 'y' indicates number of
         enabled entries only."
    ::= { switchCapL3Info 26 }

switchCapOSPFVirtLinksMaxEnt OBJECT-TYPE
    SYNTAX Integer32
    MAX-ACCESS read-only
    STATUS current
    DESCRIPTION
        "Maximum number of entries for OSPF virtual links in device."
    ::= { switchCapL3Info 27 }

switchCapOSPFVirtLinksCurrEnt OBJECT-TYPE
    SYNTAX DisplayString
    MAX-ACCESS read-only
    STATUS current
    DESCRIPTION
        "Current number of entries for OSPF virtual links in device,
         the value is in the form x(y) where 'x' indicates number
         of current entries and 'y' indicates number of
         enabled entries only."
    ::= { switchCapL3Info 28 }

switchCapOSPFHostsMaxEnt OBJECT-TYPE
    SYNTAX Integer32
    MAX-ACCESS read-only
    STATUS current
    DESCRIPTION
        "Maximum number of entries for OSPF hosts in device."
    ::= { switchCapL3Info 29 }

switchCapOSPFHostsCurrEnt OBJECT-TYPE
    SYNTAX DisplayString
    MAX-ACCESS read-only
    STATUS current
    DESCRIPTION
        "Current number of entries for OSPF hosts in device, the
         value is in the form x(y) where 'x' indicates number
         of current entries and 'y' indicates number of
         enabled entries only."
    ::= { switchCapL3Info 30 }

switchCapLSDBLimit OBJECT-TYPE
    SYNTAX Integer32
    MAX-ACCESS read-only
    STATUS current
    DESCRIPTION
        "LSDB limit in device."
    ::= { switchCapL3Info 31 }

switchCapBGPPeersMaxEnt OBJECT-TYPE
    SYNTAX Integer32
    MAX-ACCESS read-only
    STATUS current
    DESCRIPTION
        "Maximum number of entries for BGP peers in device."
    ::= { switchCapL3Info 32 }

switchCapBGPPeersCurrEnt OBJECT-TYPE
    SYNTAX DisplayString
    MAX-ACCESS read-only
    STATUS current
    DESCRIPTION
        "Current number of entries for BGP peers in device, the
         value is in the form x(y) where 'x' indicates number
         of current entries and 'y' indicates number of
         enabled entries only."
    ::= { switchCapL3Info 33 }

switchCapBGPRouteAggrsMaxEnt OBJECT-TYPE
    SYNTAX Integer32
    MAX-ACCESS read-only
    STATUS current
    DESCRIPTION
        "Maximum number of entries for BGP route aggregators in device."
    ::= { switchCapL3Info 34 }

switchCapBGPRouteAggrsCurrEnt OBJECT-TYPE
    SYNTAX DisplayString
    MAX-ACCESS read-only
    STATUS current
    DESCRIPTION
        "Current number of entries for BGP route aggregators in
         device, the value is in the form x(y) where 'x' indicates
         number of current entries and 'y' indicates number of
         enabled entries only."
    ::= { switchCapL3Info 35 }

switchCapRouteMapsMaxEnt OBJECT-TYPE
    SYNTAX Integer32
    MAX-ACCESS read-only
    STATUS current
    DESCRIPTION
        "Maximum number of entries for route maps in device."
    ::= { switchCapL3Info 36 }

switchCapRouteMapsCurrEnt OBJECT-TYPE
    SYNTAX DisplayString
    MAX-ACCESS read-only
    STATUS current
    DESCRIPTION
        "Current number of entries for route maps in device, the
         value is in the form x(y) where 'x' indicates number
         of current entries and 'y' indicates number of
         enabled entries only."
    ::= { switchCapL3Info 37 }

switchCapNwkFltsMaxEnt OBJECT-TYPE
    SYNTAX Integer32
    MAX-ACCESS read-only
    STATUS current
    DESCRIPTION
        "Maximum number of entries for network filters in device."
    ::= { switchCapL3Info 38 }

switchCapNwkFltsCurrEnt OBJECT-TYPE
    SYNTAX DisplayString
    MAX-ACCESS read-only
    STATUS current
    DESCRIPTION
        "Current number of entries for network filters in device, the
         value is in the form x(y) where 'x' indicates number
         of current entries and 'y' indicates number of
         enabled entries only."
    ::= { switchCapL3Info 39 }

switchCapASFlts OBJECT-TYPE
    SYNTAX Integer32
    MAX-ACCESS read-only
    STATUS current
    DESCRIPTION
        "Maximum number of entries for AS filters in device."
    ::= { switchCapL3Info 40 }

switchCapVRRPRtrsMaxEnt OBJECT-TYPE
    SYNTAX Integer32
    MAX-ACCESS read-only
    STATUS current
    DESCRIPTION
        "Maximum number of entries for VRRP routers in device."
    ::= { switchCapL3Info 41 }

switchCapVRRPRtrsCurrEnt OBJECT-TYPE
    SYNTAX DisplayString
    MAX-ACCESS read-only
    STATUS current
    DESCRIPTION
        "Current number of entries for VRRP routers in device, the
         value is in the form x(y) where 'x' indicates number
         of current entries and 'y' indicates number of
         enabled entries only."
    ::= { switchCapL3Info 42 }

switchCapVRRPRtrGRsMaxEnt OBJECT-TYPE
    SYNTAX Integer32
    MAX-ACCESS read-only
    STATUS current
    DESCRIPTION
        "Maximum number of entries for VRRP router groups in device."
    ::= { switchCapL3Info 43 }

switchCapVRRPRtrGRsCurrEnt OBJECT-TYPE
    SYNTAX DisplayString
    MAX-ACCESS read-only
    STATUS current
    DESCRIPTION
        "Current number of entries for VRRP router groups in device,the
         value is in the form x(y) where 'x' indicates number
         of current entries and 'y' indicates number of
         enabled entries only."
    ::= { switchCapL3Info 44 }

switchCapVRRPIntfsMaxEnt OBJECT-TYPE
    SYNTAX Integer32
    MAX-ACCESS read-only
    STATUS current
    DESCRIPTION
        "Maximum number of entries for VRRP interfaces in device."
    ::= { switchCapL3Info 45 }

switchCapVRRPIntfsCurrEnt OBJECT-TYPE
    SYNTAX Integer32
    MAX-ACCESS read-only
    STATUS current
    DESCRIPTION
        "Current number of entries for VRRP interfaces in device."
    ::= { switchCapL3Info 46 }

switchCapRealSersMaxEnt OBJECT-TYPE
    SYNTAX Integer32
    MAX-ACCESS read-only
    STATUS current
    DESCRIPTION
        "Maximum number of entries for real servers in device."
    ::= { switchCapSlbInfo 1 }

switchCapRealSersCurrEnt OBJECT-TYPE
    SYNTAX DisplayString
    MAX-ACCESS read-only
    STATUS current
    DESCRIPTION
        "Current number of entries for real servers in device, the
         value is in the form x(y) where 'x' indicates number
         of current entries and 'y' indicates number of
         enabled entries only."
    ::= { switchCapSlbInfo 2 }

switchCapSerGRsMaxEnt OBJECT-TYPE
    SYNTAX Integer32
    MAX-ACCESS read-only
    STATUS current
    DESCRIPTION
        "Maximum number of entries for real server groups in device."
    ::= { switchCapSlbInfo 3 }

switchCapSerGRsCurrEnt OBJECT-TYPE
    SYNTAX Integer32
    MAX-ACCESS read-only
    STATUS current
    DESCRIPTION
        "Current number of entries for real server groups in device."
    ::= { switchCapSlbInfo 4 }

switchCapVirtSersMaxEnt OBJECT-TYPE
    SYNTAX Integer32
    MAX-ACCESS read-only
    STATUS current
    DESCRIPTION
        "Maximum number of entries for virtual servers in device."
    ::= { switchCapSlbInfo 5 }

switchCapVirtSersCurrEnt OBJECT-TYPE
    SYNTAX DisplayString
    MAX-ACCESS read-only
    STATUS current
    DESCRIPTION
        "Current number of entries for virtual servers in device, the
         value is in the form x(y) where 'x' indicates number
         of current entries and 'y' indicates number of
         enabled entries only."
    ::= { switchCapSlbInfo 6 }

switchCapVirtServicesEnt OBJECT-TYPE
    SYNTAX Integer32
    MAX-ACCESS read-only
    STATUS current
    DESCRIPTION
        "Maximum number of entries for virtual services in device."
    ::= { switchCapSlbInfo 7 }

switchCapRealServicesEnt OBJECT-TYPE
    SYNTAX Integer32
    MAX-ACCESS read-only
    STATUS current
    DESCRIPTION
        "Current number of entries for real services in device."
    ::= { switchCapSlbInfo 8 }

switchCapRealIDSSer OBJECT-TYPE
    SYNTAX Integer32
    MAX-ACCESS read-only
    STATUS current
    DESCRIPTION
        "Maximum number of entries for real IDS servers."
    ::= { switchCapSlbInfo 9 }

switchCapIDSSerGRs OBJECT-TYPE
    SYNTAX Integer32
    MAX-ACCESS read-only
    STATUS current
    DESCRIPTION
        "Maximum number of entries for IDS server groups."
    ::= { switchCapSlbInfo 10 }

switchCapGSLBDomainsMaxEnt OBJECT-TYPE
    SYNTAX Integer32
    MAX-ACCESS read-only
    STATUS current
    DESCRIPTION
        "Maximum number of entries for global SLB domains in device."
    ::= { switchCapSlbInfo 11 }

switchCapGSLBDomainsCurrEnt OBJECT-TYPE
    SYNTAX DisplayString
    MAX-ACCESS read-only
    STATUS current
    DESCRIPTION
        "Current number of entries for global SLB domains in
         device, the value is in the form x(y) where 'x' indicates
         number of current entries and 'y' indicates number of
         enabled entries only."
    ::= { switchCapSlbInfo 12 }

switchCapGSLBServicesMaxEnt OBJECT-TYPE
    SYNTAX Integer32
    MAX-ACCESS read-only
    STATUS current
    DESCRIPTION
        "Maximum number of entries for global SLB services in device."
    ::= { switchCapSlbInfo 13 }

switchCapGSLBServicesCurrEnt OBJECT-TYPE
    SYNTAX DisplayString
    MAX-ACCESS read-only
    STATUS current
    DESCRIPTION
        "Current number of entries for global SLB services in device, the
         value is in the form x(y) where 'x' indicates number
         of current entries and 'y' indicates number of
         enabled entries only."
    ::= { switchCapSlbInfo 14 }

switchCapGSLBLocSersMaxEnt OBJECT-TYPE
    SYNTAX Integer32
    MAX-ACCESS read-only
    STATUS current
    DESCRIPTION
        "Maximum number of entries for global SLB local servers in device."
    ::= { switchCapSlbInfo 15 }

switchCapGSLBLocSersCurrEnt OBJECT-TYPE
    SYNTAX DisplayString
    MAX-ACCESS read-only
    STATUS current
    DESCRIPTION
        "Current number of entries for global SLB local servers
         in device, the value is in the form x(y) where 'x' indicates
         number of current entries and 'y' indicates number of
         enabled entries only."
    ::= { switchCapSlbInfo 16 }

switchCapGSLBRemSersMaxEnt OBJECT-TYPE
    SYNTAX Integer32
    MAX-ACCESS read-only
    STATUS current
    DESCRIPTION
        "Maximum number of entries for global SLB remote servers in device."
    ::= { switchCapSlbInfo 17 }

switchCapGSLBRemSersCurrEnt OBJECT-TYPE
    SYNTAX DisplayString
    MAX-ACCESS read-only
    STATUS current
    DESCRIPTION
        "Current number of entries for global SLB remote servers
         in device, the value is in the form x(y) where 'x' indicates
         number of current entries and 'y' indicates number of
         enabled entries only."
    ::= { switchCapSlbInfo 18 }

switchCapGSLBRemSitesMaxEnt OBJECT-TYPE
    SYNTAX Integer32
    MAX-ACCESS read-only
    STATUS current
    DESCRIPTION
        "Maximum number of entries for global SLB sites in device."
    ::= { switchCapSlbInfo 19 }

switchCapGSLBRemSitesCurrEnt OBJECT-TYPE
    SYNTAX DisplayString
    MAX-ACCESS read-only
    STATUS current
    DESCRIPTION
        "Current number of entries for global SLB sites in device, the
         value is in the form x(y) where 'x' indicates number of current
         entries and 'y' indicates number of enabled entries only."
    ::= { switchCapSlbInfo 20 }

switchCapGSLBFailoversPerRemSiteMaxEnt OBJECT-TYPE
    SYNTAX Integer32
    MAX-ACCESS read-only
    STATUS current
    DESCRIPTION
        "Maximum number of entries for global SLB failovers
         per site in device."
    ::= { switchCapSlbInfo 21 }

switchCapGSLBFailoversPerRemSiteCurrEnt OBJECT-TYPE
    SYNTAX DisplayString
    MAX-ACCESS read-only
    STATUS current
    DESCRIPTION
        "Current number of entries for global SLB failovers per site in
         device, the value is in the form x(y) where 'x' indicates number
         of current entries and 'y' indicates number of
         enabled entries only."
    ::= { switchCapSlbInfo 22 }

switchCapGSLBNetworksMaxEnt OBJECT-TYPE
    SYNTAX Integer32
    MAX-ACCESS read-only
    STATUS current
    DESCRIPTION
        "Maximum number of entries for global SLB networks in device."
    ::= { switchCapSlbInfo 23 }

switchCapGSLBNetworksCurrEnt OBJECT-TYPE
    SYNTAX DisplayString
    MAX-ACCESS read-only
    STATUS current
    DESCRIPTION
        "Current number of entries for global SLB networks in device, the
         value is in the form x(y) where 'x' indicates number of current
         entries and 'y' indicates number of enabled entries only."
    ::= { switchCapSlbInfo 24 }

switchCapGSLBGeographicalRegionsMaxEnt OBJECT-TYPE
    SYNTAX Integer32
    MAX-ACCESS read-only
    STATUS current
    DESCRIPTION
        "Maximum number of entries for global geographical regions in device."
    ::= { switchCapSlbInfo 25 }

switchCapGSLBGeographicalRegionsCurrEnt OBJECT-TYPE
    SYNTAX DisplayString
    MAX-ACCESS read-only
    STATUS current
    DESCRIPTION
        "Current number of entries for global geographical regions in device,
         the value is in the form x(y) where 'x' indicates number of current
         entries and 'y' indicates number of enabled entries only."
    ::= { switchCapSlbInfo 26 }

switchCapGSLBRulesMaxEnt OBJECT-TYPE
    SYNTAX Integer32
    MAX-ACCESS read-only
    STATUS current
    DESCRIPTION
        "Maximum number of entries for global SLB rules in device."
    ::= { switchCapSlbInfo 27 }

switchCapGSLBRulesCurrEnt OBJECT-TYPE
    SYNTAX DisplayString
    MAX-ACCESS read-only
    STATUS current
    DESCRIPTION
        "Current number of entries for global SLB rules in device, the
         value is in the form x(y) where 'x' indicates number of current
         entries and 'y' indicates number of enabled entries only."
    ::= { switchCapSlbInfo 28 }

switchCapGSLBMetricsPerRuleMaxEnt OBJECT-TYPE
    SYNTAX Integer32
    MAX-ACCESS read-only
    STATUS current
    DESCRIPTION
        "Maximum number of entries for global SLB metrics per rule in device."
    ::= { switchCapSlbInfo 29 }

switchCapGSLBMetricPerRuleCurrEnt OBJECT-TYPE
    SYNTAX DisplayString
    MAX-ACCESS read-only
    STATUS current
    DESCRIPTION
        "Current number of entries for global SLB metrics per rule in device,
         the value is in the form x(y) where 'x' indicates number of current
         entries and 'y' indicates number of enabled entries only."
    ::= { switchCapSlbInfo 30 }

switchCapGSLBDNSPersCacheMaxEnt OBJECT-TYPE
    SYNTAX Integer32
    MAX-ACCESS read-only
    STATUS current
    DESCRIPTION
        "Maximum number of entries for global SLB DNS persistence cache in device."
    ::= { switchCapSlbInfo 31 }

switchCapGSLBDNSPersCacheCurrEnt  OBJECT-TYPE
    SYNTAX DisplayString
    MAX-ACCESS read-only
    STATUS current
    DESCRIPTION
        "Current number of entries for global SLB DNS persistence cache in device,
         the value is in the form x(y) where 'x' indicates number of current
         entries and 'y' indicates number of enabled entries only."
    ::= { switchCapSlbInfo 32 }

switchCapFltsMaxEnt OBJECT-TYPE
    SYNTAX Integer32
    MAX-ACCESS read-only
    STATUS current
    DESCRIPTION
        "Maximum number of entries for filters in device."
    ::= { switchCapSlbInfo 33 }

switchCapFltsCurrEnt OBJECT-TYPE
    SYNTAX DisplayString
    MAX-ACCESS read-only
    STATUS current
    DESCRIPTION
        "Current number of entries for filters in device, the
         value is in the form x(y) where 'x' indicates number of current
         entries and 'y' indicates number of enabled entries only."
    ::= { switchCapSlbInfo 34 }

switchCapPIPsMaxEnt OBJECT-TYPE
    SYNTAX Integer32
    MAX-ACCESS read-only
    STATUS current
    DESCRIPTION
        "Maximum number of entries for PIPs in device."
    ::= { switchCapSlbInfo 35 }

switchCapPIPsCurrEnt OBJECT-TYPE
    SYNTAX Integer32
    MAX-ACCESS read-only
    STATUS current
    DESCRIPTION
        "Current number of entries for pips in device."
    ::= { switchCapSlbInfo 36 }

switchCapScriptHealthChecksMaxEnt OBJECT-TYPE
    SYNTAX Integer32
    MAX-ACCESS read-only
    STATUS current
    DESCRIPTION
        "Maximum number of entries for scriptable health checks in device."
    ::= { switchCapSlbInfo 37 }

switchCapScriptHealthChecksCurrEnt OBJECT-TYPE
    SYNTAX Integer32
    MAX-ACCESS read-only
    STATUS current
    DESCRIPTION
        "Current number of entries for scriptable health checks in device."
    ::= { switchCapSlbInfo 38 }

switchCapSNMPHealthChecksMaxEnt OBJECT-TYPE
    SYNTAX Integer32
    MAX-ACCESS read-only
    STATUS current
    DESCRIPTION
        "Maximum number of entries for SNMP health checks in device."
    ::= { switchCapSlbInfo 39 }

switchCapSNMPHealthChecksCurrEnt OBJECT-TYPE
    SYNTAX Integer32
    MAX-ACCESS  read-only
    STATUS current
    DESCRIPTION
        "Current number of entries for snmp health checks in device."
    ::= { switchCapSlbInfo 40 }

switchCapRulesforURLParsingMaxEnt OBJECT-TYPE
    SYNTAX Integer32
    MAX-ACCESS read-only
    STATUS current
    DESCRIPTION
        "Maximum number of entries for rules for URL parsing in device."
    ::= { switchCapSlbInfo 41 }

switchCapRulesforURLParsingCurrEnt OBJECT-TYPE
    SYNTAX Integer32
    MAX-ACCESS read-only
    STATUS current
    DESCRIPTION
        "Current number of entries for rules for URL parsing in device."
    ::= { switchCapSlbInfo 42 }

switchCapSLBSessionsMaxEnt OBJECT-TYPE
    SYNTAX Integer32
    MAX-ACCESS read-only
    STATUS current
    DESCRIPTION
        "Maximum number of entries for SLB sessions in device."
    ::= { switchCapSlbInfo 43 }

switchCapSLBSessionsCurrEnt OBJECT-TYPE
    SYNTAX Integer32
    MAX-ACCESS read-only
    STATUS current
    DESCRIPTION
        "Current number of entries for SLB sessions in device."
    ::= { switchCapSlbInfo 44 }

switchCapNumofRportstoVport OBJECT-TYPE
    SYNTAX Integer32
    MAX-ACCESS read-only
    STATUS current
    DESCRIPTION
        "Maximum number of rports to vport."
    ::= { switchCapSlbInfo 45 }

switchCapDomianRecordsMaxEnt OBJECT-TYPE
    SYNTAX Integer32
    MAX-ACCESS read-only
    STATUS current
    DESCRIPTION
        "Maximum number of entries for domain records in device."
    ::= { switchCapSlbInfo 46 }

switchCapDomainRecordsCurrEnt OBJECT-TYPE
    SYNTAX DisplayString
    MAX-ACCESS read-only
    STATUS current
    DESCRIPTION
        "Current number of entries for domain records in device, the
         value is in the form x(y) where 'x' indicates number of current
         entries and 'y' indicates number of enabled entries only."
    ::= { switchCapSlbInfo 47 }

switchCapMappingPerDomainrecord OBJECT-TYPE
    SYNTAX Integer32
    MAX-ACCESS read-only
    STATUS current
    DESCRIPTION
        "Maximum number of entries for mapping per domain record in device."
    ::= { switchCapSlbInfo 48 }

switchCapSlbPortInfoTable OBJECT-TYPE
    SYNTAX  SEQUENCE OF SwitchCapSlbPortInfoTableEntry
    MAX-ACCESS  not-accessible
    STATUS  current
    DESCRIPTION
        "The table of slb port information."
    ::= { switchCapSlbPortInfo 1 }

switchCapSlbPortInfoTableEntry OBJECT-TYPE
    SYNTAX SwitchCapSlbPortInfoTableEntry
    MAX-ACCESS not-accessible
    STATUS current
    DESCRIPTION
        "A row in the slb port information table."
    INDEX  { switchCapSlbPortInfoIndx}
    ::= { switchCapSlbPortInfoTable 1 }

SwitchCapSlbPortInfoTableEntry ::= SEQUENCE {
    switchCapSlbPortInfoIndx         Integer32,
    switchCapSlbPortClientState      INTEGER,
    switchCapSlbPortSerState         INTEGER,
    switchCapSlbPortFltState         DisplayString,
    switchCapSlbPortRTSState         INTEGER
    }

switchCapSlbPortInfoIndx OBJECT-TYPE
    SYNTAX Integer32
    MAX-ACCESS read-only
    STATUS current
    DESCRIPTION
        "Index of switch port."
    ::= { switchCapSlbPortInfoTableEntry 1 }

switchCapSlbPortClientState OBJECT-TYPE
    SYNTAX INTEGER {
        enabled(1),
        disabled(2)
        }
    MAX-ACCESS read-only
    STATUS current
    DESCRIPTION
        "Client state on the switch port."
    ::= { switchCapSlbPortInfoTableEntry 2 }

switchCapSlbPortSerState OBJECT-TYPE
    SYNTAX INTEGER {
        enabled(1),
        disabled(2)
        }
    MAX-ACCESS read-only
    STATUS current
    DESCRIPTION
        "Server state on the switch port."
    ::= { switchCapSlbPortInfoTableEntry 3 }

switchCapSlbPortFltState OBJECT-TYPE
    SYNTAX DisplayString
    MAX-ACCESS read-only
    STATUS current
    DESCRIPTION
        "It is in the form E(x) where filter is enabled on the port and
         x is the number of filters configured for port. Otherwise disable."
    ::= { switchCapSlbPortInfoTableEntry 4 }

switchCapSlbPortRTSState OBJECT-TYPE
    SYNTAX INTEGER {
        enabled(1),
        disabled(2)
        }
    MAX-ACCESS read-only
    STATUS current
    DESCRIPTION
        "RTS processing state on the switch port."
    ::= { switchCapSlbPortInfoTableEntry 5 }

bwmPoliciesMaxEnt OBJECT-TYPE
    SYNTAX Integer32
    MAX-ACCESS read-only
    STATUS current
    DESCRIPTION
        "Maximum number of entries for bwm policies in device ."
    ::= { switchCapBwmInfo 1 }

bwmPoliciesCurrEnt OBJECT-TYPE
    SYNTAX Integer32
    MAX-ACCESS  read-only
    STATUS current
    DESCRIPTION
        "Current number of entries for bwm policies in device."
    ::= { switchCapBwmInfo 2 }

bwmContsMaxEnt OBJECT-TYPE
    SYNTAX Integer32
    MAX-ACCESS read-only
    STATUS current
    DESCRIPTION
        "Maximum number of entries for bwm contracts  in device."
    ::= { switchCapBwmInfo 3 }

bwmContsCurrEnt OBJECT-TYPE
    SYNTAX DisplayString
    MAX-ACCESS  read-only
    STATUS current
    DESCRIPTION
        "Current number of entries for bwm contracts  in device, the
         value is in the form x(y) where 'x' indicates number of current
         entries and 'y' indicates number of enabled entries only."
    ::= { switchCapBwmInfo 4 }

bwmGRsMaxEnt OBJECT-TYPE
    SYNTAX Integer32
    MAX-ACCESS read-only
    STATUS current
    DESCRIPTION
        "Maximum number of entries for bwm groups  in device."
    ::= { switchCapBwmInfo 5 }

bwmGRsCurrEnt OBJECT-TYPE
    SYNTAX Integer32
    MAX-ACCESS read-only
    STATUS current
    DESCRIPTION
        "Current number of entries for bwm groups  in device."
    ::= { switchCapBwmInfo 6 }

bwmContsPerGRs OBJECT-TYPE
    SYNTAX Integer32
    MAX-ACCESS read-only
    STATUS current
    DESCRIPTION
        "Maximum number of entries for bwm contracts per group in device."
    ::= { switchCapBwmInfo  7 }

bwmTimePoliciesPerCont OBJECT-TYPE
    SYNTAX Integer32
    MAX-ACCESS read-only
    STATUS current
    DESCRIPTION
        "Current number of entries for  bwm time policies per contract."
    ::= { switchCapBwmInfo  8 }

configSrcIPACLsMaxEnt OBJECT-TYPE
    SYNTAX Integer32
    MAX-ACCESS read-only
    STATUS current
    DESCRIPTION
        "Maximum number of entries for configuration source IP ACLs."
    ::= { switchCapSecInfo 1 }

configSrcIPACLsCurrEnt OBJECT-TYPE
    SYNTAX Integer32
    MAX-ACCESS read-only
    STATUS current
    DESCRIPTION
        "Current number of entries for configuration source IP ACLs."
    ::= { switchCapSecInfo 2 }

bogonSrcIPACLsMaxEnt OBJECT-TYPE
    SYNTAX Integer32
    MAX-ACCESS read-only
    STATUS current
    DESCRIPTION
        "Maximum number of entries for bogon source IP ACLs."
    ::= { switchCapSecInfo 3 }

bogonSrcIPACLsCurrEnt OBJECT-TYPE
    SYNTAX Integer32
    MAX-ACCESS read-only
    STATUS current
    DESCRIPTION
        "Current number of entries for bogon source IP ACLs."
    ::= { switchCapSecInfo 4 }

operSrcIPACLsMaxEnt OBJECT-TYPE
    SYNTAX Integer32
    MAX-ACCESS read-only
    STATUS current
    DESCRIPTION
        "Maximum number of entries for operation source IP ACLs."
    ::= { switchCapSecInfo 5 }

operSrcIPACLsCurrEnt OBJECT-TYPE
    SYNTAX Integer32
    MAX-ACCESS read-only
    STATUS current
    DESCRIPTION
        "Current number of entries for operaion source IP ACLs."
    ::= { switchCapSecInfo 6 }

totalSrcIPACLsMaxEnt OBJECT-TYPE
    SYNTAX Integer32
    MAX-ACCESS read-only
    STATUS current
    DESCRIPTION
        "Maximum number of entries for total source IP ACLs."
    ::= { switchCapSecInfo 7 }

totalSrcIPACLsCurrEnt OBJECT-TYPE
    SYNTAX Integer32
    MAX-ACCESS read-only
    STATUS current
    DESCRIPTION
        "Current number of entries for total source IP ACLs."
    ::= { switchCapSecInfo 8 }

configDstIPACLsMaxEnt OBJECT-TYPE
    SYNTAX Integer32
    MAX-ACCESS read-only
    STATUS current
    DESCRIPTION
        "Maximum number of entries for configuration destination  IP ACLs."
    ::= { switchCapSecInfo 9 }

configDstIPACLsCurrEnt OBJECT-TYPE
    SYNTAX Integer32
    MAX-ACCESS read-only
    STATUS current
    DESCRIPTION
        "Current number of entries for configuration destination IP ACLs."
    ::= { switchCapSecInfo 10 }

operDstIPACLsMaxEnt OBJECT-TYPE
    SYNTAX Integer32
    MAX-ACCESS read-only
    STATUS current
    DESCRIPTION
        "Maximum number of entries for operation destination IP ACLs."
    ::= { switchCapSecInfo 11 }

operDstIPACLsCurrEnt OBJECT-TYPE
    SYNTAX Integer32
    MAX-ACCESS read-only
    STATUS current
    DESCRIPTION
        "Current number of entries for operaion destination IP ACLs."
    ::= { switchCapSecInfo 12 }

totalDstIPACLsMaxEnt OBJECT-TYPE
    SYNTAX Integer32
    MAX-ACCESS read-only
    STATUS current
    DESCRIPTION
        "Maximum number of entries for total destination IP ACLs."
    ::= { switchCapSecInfo 13 }

totalDstIPACLsCurrEnt OBJECT-TYPE
    SYNTAX Integer32
    MAX-ACCESS read-only
    STATUS current
    DESCRIPTION
        "Current number of entries for total destination IP ACLs."
    ::= { switchCapSecInfo 14 }
ipDosAtkPrevention OBJECT-TYPE
    SYNTAX Integer32
    MAX-ACCESS read-only
    STATUS current
    DESCRIPTION
        "Maximum number of entries for IP DOS attack prevention."
    ::= { switchCapSecInfo 15 }

tcpDosAtkPrevention OBJECT-TYPE
    SYNTAX Integer32
    MAX-ACCESS read-only
    STATUS current
    DESCRIPTION
        "Maximum number of entries for TCP DOS attack prevention."
    ::= { switchCapSecInfo 16 }

udpDosAtkPrevention OBJECT-TYPE
    SYNTAX Integer32
    MAX-ACCESS read-only
    STATUS current
    DESCRIPTION
        "Maximum number of entries for UDP DOS attack prevention."
    ::= { switchCapSecInfo 17 }

icmpDosAtkPrevention OBJECT-TYPE
    SYNTAX Integer32
    MAX-ACCESS read-only
    STATUS current
    DESCRIPTION
        "Maximum number of entries for ICMP DOS attack prevention."
    ::= { switchCapSecInfo 18 }

igmpDosAtkPrevention OBJECT-TYPE
    SYNTAX Integer32
    MAX-ACCESS read-only
    STATUS current
    DESCRIPTION
        "Maximum number of entries for IGMP DOS attack prevention."
    ::= { switchCapSecInfo 19 }

arpDosAtkPrevention OBJECT-TYPE
    SYNTAX Integer32
    MAX-ACCESS read-only
    STATUS current
    DESCRIPTION
        "Maximum number of entries for ARP DOS attack prevention."
    ::= { switchCapSecInfo 20 }

ipv6DosAtkPrevention OBJECT-TYPE
    SYNTAX Integer32
    MAX-ACCESS read-only
    STATUS current
    DESCRIPTION
        "Maximum number of entries for ipv6 DOS attack prevention."
    ::= { switchCapSecInfo 21 }

totalDosAtkPrevention OBJECT-TYPE
    SYNTAX Integer32
    MAX-ACCESS read-only
    STATUS current
    DESCRIPTION
        "Total number of entries for DOS attack preventions."
    ::= { switchCapSecInfo 22 }
udpBlastProtection OBJECT-TYPE
    SYNTAX Integer32
    MAX-ACCESS read-only
    STATUS current
    DESCRIPTION
        "Specifies UDP ports for UDP blast protection."
    ::= { switchCapSecInfo 23 }

syslogHostMaxEnt OBJECT-TYPE
    SYNTAX Integer32
    MAX-ACCESS read-only
    STATUS current
    DESCRIPTION
        "Maximum number of entries for syslog hosts  in device."
    ::= { switchCapGeneralInfo 1 }

syslogHostCurrEnt OBJECT-TYPE
    SYNTAX Integer32
    MAX-ACCESS read-only
    STATUS current
    DESCRIPTION
        "Current number of entries for syslog hosts in device."
    ::= { switchCapGeneralInfo 2 }

radiusSerMaxEnt OBJECT-TYPE
    SYNTAX Integer32
    MAX-ACCESS read-only
    STATUS current
    DESCRIPTION
        "Maximum number of entries for radius servers in device ."
    ::= { switchCapGeneralInfo 3 }

radiusSerCurrEnt OBJECT-TYPE
    SYNTAX Integer32
    MAX-ACCESS read-only
    STATUS current
    DESCRIPTION
        "Current number of entries for radius servers in device."
    ::= { switchCapGeneralInfo 4 }

tacacsSerMaxEnt OBJECT-TYPE
    SYNTAX Integer32
    MAX-ACCESS read-only
    STATUS current
    DESCRIPTION
        "Maximum number of entries for tacacs+ server in device."
    ::= { switchCapGeneralInfo 5 }

tacacsSerCurrEnt OBJECT-TYPE
    SYNTAX Integer32
    MAX-ACCESS read-only
    STATUS current
    DESCRIPTION
        "Current number of entries for tacacs+ server in device."
    ::= { switchCapGeneralInfo 6 }

ntpSerMaxEnt OBJECT-TYPE
    SYNTAX Integer32
    MAX-ACCESS read-only
    STATUS current
    DESCRIPTION
        "Maximum number of entries for ntp servers in device ."
    ::= { switchCapGeneralInfo 7 }

ntpSerCurrEnt OBJECT-TYPE
    SYNTAX Integer32
    MAX-ACCESS read-only
    STATUS current
    DESCRIPTION
        "Current number of entries for ntp servers in device."
    ::= { switchCapGeneralInfo 8 }

smtpHostsMaxEnt OBJECT-TYPE
    SYNTAX Integer32
    MAX-ACCESS read-only
    STATUS current
    DESCRIPTION
        "Maximum number of entries for smtp hosts in device."
    ::= { switchCapGeneralInfo 9 }

smtpHostsCurrEnt OBJECT-TYPE
    SYNTAX Integer32
    MAX-ACCESS read-only
    STATUS current
    DESCRIPTION
        "Current number of entries for smtp hosts in device."
    ::= { switchCapGeneralInfo 10 }

mgmtNetworksMaxEnt OBJECT-TYPE
    SYNTAX Integer32
    MAX-ACCESS read-only
    STATUS current
    DESCRIPTION
        "Maximum number of entries for management networks in device ."
    ::= { switchCapGeneralInfo 11 }

mgmtNetworksCurrEnt OBJECT-TYPE
    SYNTAX Integer32
    MAX-ACCESS read-only
    STATUS current
    DESCRIPTION
        "Current number of entries for management networks in device."
    ::= { switchCapGeneralInfo 12 }

endUsers OBJECT-TYPE
    SYNTAX Integer32
    MAX-ACCESS read-only
    STATUS current
    DESCRIPTION
        "Maximum number of entries for end users in device."
    ::= { switchCapGeneralInfo 13 }

panicDumps OBJECT-TYPE
    SYNTAX Integer32
    MAX-ACCESS read-only
    STATUS current
    DESCRIPTION
        "Maximum panic dumps in device."
    ::= { switchCapGeneralInfo 14 }

mpMemory OBJECT-TYPE
    SYNTAX DisplayString
    MAX-ACCESS read-only
    STATUS current
    DESCRIPTION
        "Total capacity of MP memory in MBs in device."
    ::= { switchCapGeneralInfo 15 }

spMemory OBJECT-TYPE
    SYNTAX DisplayString
    MAX-ACCESS read-only
    STATUS current
    DESCRIPTION
        "Total capacity of SP memory in MBs in device."
    ::= { switchCapGeneralInfo 16 }

snmpv3UsersMaxEnt OBJECT-TYPE
    SYNTAX Integer32
    MAX-ACCESS read-only
    STATUS current
    DESCRIPTION
        "Maximum number of entries for snmpv3 users in device."
    ::= { switchCapGeneralInfo 17 }

snmpv3UsersCurrEnt OBJECT-TYPE
    SYNTAX Integer32
    MAX-ACCESS read-only
    STATUS current
    DESCRIPTION
        "Current number of entries for snmpv3 users in device."
    ::= { switchCapGeneralInfo 18 }

snmpv3ViewsMaxEnt OBJECT-TYPE
    SYNTAX Integer32
    MAX-ACCESS read-only
    STATUS current
    DESCRIPTION
        "Maximum number of entries for snmpv3 views in device."
    ::= { switchCapGeneralInfo 19 }

snmpv3ViewsCurrEnt OBJECT-TYPE
    SYNTAX Integer32
    MAX-ACCESS read-only
    STATUS current
    DESCRIPTION
        "Current number of entries for snmpv3 views in device."
    ::= { switchCapGeneralInfo 20 }

snmpv3AccessGRsMaxEnt OBJECT-TYPE
    SYNTAX Integer32
    MAX-ACCESS read-only
    STATUS current
    DESCRIPTION
        "Maximum number of entries for snmpv3 access groups in device."
    ::= { switchCapGeneralInfo 21 }

snmpv3AccessGRsCurrEnt OBJECT-TYPE
    SYNTAX Integer32
    MAX-ACCESS read-only
    STATUS current
    DESCRIPTION
        "Current number of entries for snmpv3 access groups in device."
    ::= { switchCapGeneralInfo 22 }

snmpv3TargetAddrMaxEnt OBJECT-TYPE
    SYNTAX Integer32
    MAX-ACCESS read-only
    STATUS current
    DESCRIPTION
        "Maximum number of entries for snmpv3 target addresses in device."
    ::= { switchCapGeneralInfo 23 }

snmpv3TargetAddrCurrEnt OBJECT-TYPE
    SYNTAX Integer32
    MAX-ACCESS read-only
    STATUS current
    DESCRIPTION
        "Current number of entries for snmpv3 target addresses in device."
    ::= { switchCapGeneralInfo 24 }

snmpv3TargetParamsMaxEnt OBJECT-TYPE
    SYNTAX Integer32
    MAX-ACCESS read-only
    STATUS current
    DESCRIPTION
        "Maximum number of entries for snmpv3 target parameters in device."
    ::= { switchCapGeneralInfo 25 }

snmpv3TargetParamsCurrEnt OBJECT-TYPE
    SYNTAX Integer32
    MAX-ACCESS read-only
    STATUS current
    DESCRIPTION
        "Current number of entries for snmpv3 target parameters in device."
    ::= { switchCapGeneralInfo 26 }


-- Port operation table
agPortOperTable OBJECT-TYPE
    SYNTAX  SEQUENCE OF AgPortOperTableEntry
    MAX-ACCESS  not-accessible
    STATUS  current
    DESCRIPTION
        "The table of port operations."
    ::= { agentOper 1 }

agPortOperTableEntry OBJECT-TYPE
    SYNTAX  AgPortOperTableEntry
    MAX-ACCESS  not-accessible
    STATUS  current
    DESCRIPTION
        "A row in the port operations table."
    INDEX   { portOperIdx }
    ::= { agPortOperTable 1 }

AgPortOperTableEntry ::=
    SEQUENCE {
	portOperIdx	    Integer32,
	portOperRmon	    INTEGER,
	portOperState	    INTEGER
    }

portOperIdx OBJECT-TYPE
    SYNTAX  Integer32  
    MAX-ACCESS  read-only
    STATUS  current
    DESCRIPTION
        "The port index."
    ::= { agPortOperTableEntry 1 }

portOperState OBJECT-TYPE
    SYNTAX  INTEGER {
        enabled(1),
        disabled(2)
        }
    MAX-ACCESS  read-write
    STATUS  current
    DESCRIPTION
        "Enable/Disable port."
    ::= { agPortOperTableEntry 2 }

portOperRmon OBJECT-TYPE
    SYNTAX  INTEGER {
        enabled(1),
        disabled(2)
        }
    MAX-ACCESS  read-write
    STATUS  current
    DESCRIPTION
        "Enable/Disable RMON for port."
    ::= { agPortOperTableEntry 3 }

ntpOperSendReq OBJECT-TYPE
    SYNTAX  INTEGER {
        no(1),
        yes(2)
        }
    MAX-ACCESS  read-write
    STATUS  current
    DESCRIPTION
        "Allows the user to send requests to the NTP server."
    ::= { agNTPOper 1 }

-- Port information table

portInfoTable OBJECT-TYPE
    SYNTAX  SEQUENCE OF PortInfoTableEntry
    MAX-ACCESS  not-accessible
    STATUS  current
    DESCRIPTION
        "The table of port information."
    ::= { portInfo 1 }

portInfoTableEntry OBJECT-TYPE
    SYNTAX  PortInfoTableEntry
    MAX-ACCESS  not-accessible
    STATUS  current
    DESCRIPTION
        "A row in the port information table."
    INDEX   { portInfoIndx }
    ::= { portInfoTable 1 }

PortInfoTableEntry ::= SEQUENCE {
    portInfoIndx        	Integer32,
    portInfoSpeed       	INTEGER,
    portInfoMode        	INTEGER,
    portInfoFlowCtrl    	INTEGER,
    portInfoLink        	INTEGER,
    portInfoPhyIfDescr  	DisplayString,
    portInfoPhyIfType   	INTEGER,
    portInfoPhyIfMtu    	Integer32,
    portInfoPhyIfPhysAddress  	PhysAddress,
    portInfoPhyIfOperStatus	INTEGER, 
    portInfoPhyIfLastChange	TimeTicks,
    portInfoPhyConnType   	INTEGER,
    portInfoPreferred	   	INTEGER,
    portInfoBackup	  	INTEGER,
    portInfoSFPName	  	DisplayString,
    portInfoSFPType		INTEGER
    }

portInfoIndx OBJECT-TYPE
    SYNTAX  Integer32
    MAX-ACCESS  read-only
    STATUS  current
    DESCRIPTION
        "The port index."
    ::= { portInfoTableEntry 1 }

portInfoSpeed OBJECT-TYPE
    SYNTAX  INTEGER {
        mbs10(2),
        mbs100(3),
        mbs1000(4),
        any(5)
        }
    MAX-ACCESS  read-only
    STATUS  current
    DESCRIPTION
        "The current operational speed of the port."
    ::= { portInfoTableEntry 2 }

portInfoMode OBJECT-TYPE
    SYNTAX  INTEGER {
        full-duplex(2),
        half-duplex(3)
        }
    MAX-ACCESS  read-only
    STATUS  current
    DESCRIPTION
        "The current operational mode of the port."
    ::= { portInfoTableEntry 3 }

portInfoFlowCtrl OBJECT-TYPE
    SYNTAX  INTEGER {
        transmit(2),
        receive(3),
        both(4),
        none(5)
        }
    MAX-ACCESS  read-only
    STATUS  current
    DESCRIPTION
        "The current operational flow control of the port."
    ::= { portInfoTableEntry 4 }

portInfoLink OBJECT-TYPE
    SYNTAX  INTEGER {
        up(1),
        down(2),
        disabled(3),
        inoperative(4) -- unrecognized PCI device
        }
     MAX-ACCESS  read-only
     STATUS  current
     DESCRIPTION
         "The current operational link status of the port."
     ::= { portInfoTableEntry 5 }

portInfoPhyIfDescr OBJECT-TYPE
    SYNTAX  DisplayString (SIZE (0..255))
    MAX-ACCESS  read-only
    STATUS  current
    DESCRIPTION
	    "A textual string containing information about the
	    interface.  This string should include the name of
	    the manufacturer, the product name and the version
	    of the hardware interface."
    ::= { portInfoTableEntry 6 }

portInfoPhyIfType OBJECT-TYPE
    SYNTAX  INTEGER {
		other(1),          -- none of the following
		regular1822(2),
		hdh1822(3),
		ddn-x25(4),
		rfc877-x25(5),
		ethernet-csmacd(6),
		iso88023-csmacd(7),
		iso88024-tokenBus(8),
		iso88025-tokenRing(9),
		iso88026-man(10),
		starLan(11),
		proteon-10Mbit(12),
		proteon-80Mbit(13),
		hyperchannel(14),
		fddi(15),
		lapb(16),
		sdlc(17),
		ds1(18),           -- T-1
		e1(19),            -- european equiv. of T-1
		basicISDN(20),
		primaryISDN(21),   -- proprietary serial
		propPointToPointSerial(22),
		ppp(23),
		softwareLoopback(24),
		eon(25),            -- CLNP over IP [11]
		ethernet-3Mbit(26),
		nsip(27),           -- XNS over IP
		slip(28),           -- generic SLIP
		ultra(29),          -- ULTRA technologies
		ds3(30),            -- T-3
		sip(31),            -- SMDS
		frame-relay(32)
	    }
    MAX-ACCESS  read-only
    STATUS  current
    DESCRIPTION
	    "The type of interface, distinguished according to
	    the physical/link protocol(s) immediately `below'
	    the network layer in the protocol stack."
    ::= { portInfoTableEntry 7 }

portInfoPhyIfMtu OBJECT-TYPE
    SYNTAX  Integer32
    MAX-ACCESS  read-only
    STATUS  current
    DESCRIPTION
	    "The size of the largest datagram which can be
	    sent/received on the interface, specified in
	    octets.  For interfaces that are used for
	    transmitting network datagrams, this is the size
	    of the largest network datagram that can be sent
	    on the interface."
    ::= { portInfoTableEntry 8 }

portInfoPhyIfPhysAddress OBJECT-TYPE
    SYNTAX  PhysAddress
    MAX-ACCESS  read-only
    STATUS  current
    DESCRIPTION
	    "The interface's address at the protocol layer
	    immediately `below' the network layer in the
	    protocol stack.  For interfaces which do not have
	    such an address (e.g., a serial line), this object
	    should contain an octet string of zero length."
    ::= { portInfoTableEntry 9 }

portInfoPhyIfOperStatus OBJECT-TYPE
    SYNTAX  INTEGER {
	up(1),       -- ready to pass packets
	down(2),
	testing(3)   -- in some test mode
	}
    MAX-ACCESS  read-only
    STATUS  current
    DESCRIPTION
	    "The current operational state of the interface.
	    The testing(3) state indicates that no operational
	    packets can be passed."
    ::= { portInfoTableEntry 10 }

portInfoPhyIfLastChange OBJECT-TYPE
    SYNTAX  TimeTicks
    MAX-ACCESS  read-only
    STATUS  current
    DESCRIPTION
	    "The value of sysUpTime at the time the interface
	    entered its current operational state.  If the
	    current state was entered prior to the last re-
	    initialization of the local network management
	    subsystem, then this object contains a zero
	    value."
    ::= { portInfoTableEntry 11 }

portInfoPhyConnType OBJECT-TYPE
    SYNTAX  INTEGER {
		feCopper(1),
		geCopper(2),
		geSFP(3),
		unknown(4)
	    }
    MAX-ACCESS  read-only
    STATUS  current
    DESCRIPTION
	    "The physical connection type, i.e. copper or SFP port."
    ::= { portInfoTableEntry 12 }

portInfoPreferred OBJECT-TYPE
    SYNTAX  INTEGER {		
		invalid(1),
		copper(2),
		sfp(3)
	    }
    MAX-ACCESS  read-only
    STATUS  current
    DESCRIPTION
	    "The port preferred connection type. For dual ports only"
    ::= { portInfoTableEntry 13 }

portInfoBackup OBJECT-TYPE
    SYNTAX  INTEGER {
		invalid(1),
		none(2),
		copper(3),
		sfp(4)
	    }
    MAX-ACCESS  read-only
    STATUS  current
    DESCRIPTION
	    "The port backup setting. For dual ports only"
    ::= { portInfoTableEntry 14 }

portInfoSFPName OBJECT-TYPE
    SYNTAX  DisplayString (SIZE (0..255))
    MAX-ACCESS  read-only
    STATUS  current
    DESCRIPTION
	    "A textual string containing information about the
	    SFP manufacturer. For valid ports only."
    ::= { portInfoTableEntry 15 }

portInfoSFPType OBJECT-TYPE
    SYNTAX  INTEGER {		
		invalid(1),
		sfpTypeSX(2),
		sfpTypeLX(3),
		sfpTypeCX(4),
		sfpTypeCopper(5)
	    }
    MAX-ACCESS  read-only
    STATUS  current
    DESCRIPTION
	    "The inserted SFP type. For valid ports only."
    ::= { portInfoTableEntry 17 }

agEnabledSwFeatures OBJECT-TYPE
    SYNTAX  DisplayString
    MAX-ACCESS  read-only
    STATUS  current
    DESCRIPTION
        "The software features that are enabled on the switch."
    ::= { swKeyInfo 1 }

agEnabledGslbKey OBJECT-TYPE
    SYNTAX  INTEGER {
        enabled(1),
        disabled(2)
        }
    MAX-ACCESS  read-only
    STATUS  current
    DESCRIPTION
        "Query if software key Global slb enabled on switch."
    ::= { swKeyInfo 2 }

agEnabledBwmKey OBJECT-TYPE
    SYNTAX  INTEGER {
        enabled(1),
        disabled(2)
        }
    MAX-ACCESS  read-only
    STATUS  current
    DESCRIPTION
        "Query if software key Bandwidth Mgmt. enabled on switch."
    ::= { swKeyInfo 3 }

agEnabledSecurityKey OBJECT-TYPE
    SYNTAX  INTEGER {
        enabled(1),
        disabled(2)
        }
    MAX-ACCESS  read-only
    STATUS  current
    DESCRIPTION
        "Query if software key Security enabled on switch."
    ::= { swKeyInfo 4 }


agEnabledLinklbKey OBJECT-TYPE
    SYNTAX  INTEGER {
        enabled(1),
        disabled(2)
        }
    MAX-ACCESS  read-only
    STATUS  current
    DESCRIPTION
        "Query if software key Inbound Linklb is enabled on switch."
    ::= { swKeyInfo 6 }

agSymantecSwKeyInfo OBJECT-TYPE
    SYNTAX  INTEGER {
        enabled(1),
        disabled(2),
	expired(3)
        }
    MAX-ACCESS  read-only
    STATUS  current
    DESCRIPTION
        "Query about the Symantec Software key enabled(1) or disabled(2),
	 or expired(3) in the switch."
    ::= { swKeyInfo 7 }

agSymantecSwKeyRemainingDays OBJECT-TYPE
    SYNTAX  Integer32
    MAX-ACCESS  read-only
    STATUS  current
    DESCRIPTION
        "Query the number of remaining days for Symantec SwKey to expire."
    ::= { swKeyInfo 8 }

agSymLicenseSwKeyRenewalPending OBJECT-TYPE
    SYNTAX INTEGER { 
	no(1),
	yes(2)
        }
    MAX-ACCESS read-only 
    STATUS  current
    DESCRIPTION
        "Symantec License Renewal Pending indicator." 
    ::= { swKeyInfo 9 }


-- Agent System Group
-- This group of objects take effect on the 'SET' request.
-- There is no need to 'apply' or 'save'.
 
agApplyConfiguration OBJECT-TYPE
    SYNTAX  INTEGER {
        other(1),
        apply(2)
        }
    MAX-ACCESS  read-write
    STATUS  current
    DESCRIPTION
        "This is an action object to apply the changes made to configuration 
         of the switch. By setting the value to apply(2), all the changes 
         made since the last apply are written to the new_config block.

         other(1) is returned when this object ie read. "
    ::= { agSystem 2 }

agSavePending OBJECT-TYPE
    SYNTAX  INTEGER {
        saveNeeded(1),
        noSaveNeeded(2)
        }
    MAX-ACCESS  read-only
    STATUS  current
    DESCRIPTION
        "This object, when read, gives the user information
         whether an save action is needed and that the configuration
         has been applied but not saved to the flash."
    ::= { agSystem 3 }

agSaveConfiguration OBJECT-TYPE
    SYNTAX  INTEGER {
        ok(1),
        saveActive(2),
        notSaveActive(3)
        }
    MAX-ACCESS  read-write
    STATUS  current
    DESCRIPTION
        "This is an action object to write current configuration to 
         nonvolatile storage.

         When issued with the saveActive, the active configuration
         in flash is saved to backup in flash and then the new
         configuration is saved to the active configuration in flash.

         When issued with notSaveActive, the active configuration
         is NOT saved to the flash and the active configuration is
         overwritten with the new configuration.

         ok(1) is returned always when read."
    ::= { agSystem 4 }

agRevert OBJECT-TYPE
    SYNTAX  INTEGER {
        other(1),
        revert(2)
        }
    MAX-ACCESS  read-write
    STATUS  current
    DESCRIPTION
        "This is an action object to revert the unapplied changes 
         made to the switch. By setting the value to revert(2), 
         all the unapplied changes will be reverted. This action 
         will copy the current_config to the new_config block.

         other(1) is returned when this object is read. "
    ::= { agSystem 5 }

agRevertApply OBJECT-TYPE
    SYNTAX  INTEGER {
        other(1),
        revertApply(2)
        }
    MAX-ACCESS  read-write
    STATUS  current
    DESCRIPTION
        "This is an action object to revert the unsaved changes 
         made to the switch. By setting the value to revertApply(2), 
         all the unsaved as well as unapplied changes will be 
         reverted.

         other(1) is returned when this object is read. "
    ::= { agSystem 6 }

agReset OBJECT-TYPE
    SYNTAX  INTEGER {
        other(1),
        reset(2)
        }
    MAX-ACCESS  read-write
    STATUS  current
    DESCRIPTION
        "This is an action object to reboot the agent.
         other(1) is returned always when read."
    ::= { agSystem 7 }

agConfigForNxtReset OBJECT-TYPE
    SYNTAX  INTEGER {
        active(2),
        backup(3),
        default(4)
        }
    MAX-ACCESS  read-write
    STATUS  current
    DESCRIPTION
        "The configuration information to be loaded from at next reset.

          The following values are writable:
              active(2)...active configuration block
              backup(3)...backup configuration block
              default(4)..default configuration block"
    ::= { agSystem 8 }

agImageForNxtReset OBJECT-TYPE
    SYNTAX  INTEGER {
        image1(2),
        image2(3)
        }
    MAX-ACCESS  read-write
    STATUS  current
    DESCRIPTION
        "The software image to be booted from at next reset.

         The following values are writable:
             image1(2)...image 1
             image2(3)...image 2"
    ::= { agSystem 9 }

agSoftwareVersion OBJECT-TYPE
    SYNTAX  DisplayString (SIZE(0..16))
    MAX-ACCESS  read-only
    STATUS  current
    DESCRIPTION
        "The version of the software image that is currently running on the 
         system in the form of 'major.minor.maintenance.bugfix'.  A zero 
         length string is returned if version is not available."
    ::= { agSystem 10 }

agBootVer OBJECT-TYPE
    SYNTAX  DisplayString (SIZE(0..16))
    MAX-ACCESS  read-only
    STATUS  current
    DESCRIPTION
        "The version of the boot code in the form of 'major.minor.bugfix'.
         A zero length string is returned if version is not available."
    ::= { agSystem 11 }

agImage1Ver OBJECT-TYPE
    SYNTAX  DisplayString (SIZE(0..128))
    MAX-ACCESS  read-only
    STATUS  current
    DESCRIPTION
        "The version of the software image stored in image 1 storage in the 
         form of 'major.minor.bugfix'.  A zero length string is returned if 
         version is not available or there is no valid software image."
    ::= { agSystem 12 }

agImage2Ver OBJECT-TYPE
    SYNTAX  DisplayString (SIZE(0..128))
    MAX-ACCESS  read-only
    STATUS  current
    DESCRIPTION
        "The version of the software image stored in image 2 storage in the 
         form of 'major.minor.bugfix'.  A zero length string is returned if 
         version is not available or there is no valid software image."
    ::= { agSystem 13 }

agRtcDate OBJECT-TYPE
    SYNTAX  DisplayString (SIZE(0..16))
    MAX-ACCESS  read-write
    STATUS  current
    DESCRIPTION
        "The date on the real time clock in the form of 'mm/dd/yy'.  
         A zero length string is returned if date is not available."
    ::= { agSystem 14 }

agRtcTime OBJECT-TYPE
    SYNTAX  DisplayString (SIZE(0..16))
    MAX-ACCESS  read-write
    STATUS  current
    DESCRIPTION
        "The time on the real time clock in the form of 'hh:mm:ss'.  
         A zero length string is returned if time is not available."
    ::= { agSystem 15 }

agLastSetErrorReason   OBJECT-TYPE
    SYNTAX  DisplayString (SIZE(0..255))
    MAX-ACCESS  read-only
    STATUS  current
    DESCRIPTION
        "The error reason of the last SET failure."
    ::= { agSystem 16 }

agCurCfgHttpServerPort OBJECT-TYPE
    SYNTAX  INTEGER (1..65535)
    MAX-ACCESS  read-only
    STATUS  current
    DESCRIPTION
        "The TCP port number that the HTTP server is listening to 
         in the current_configuration block."
    ::= { agSystem 17 }

agNewCfgHttpServerPort OBJECT-TYPE
    SYNTAX  INTEGER (1..65535)
    MAX-ACCESS  read-write
    STATUS  current
    DESCRIPTION
        "The TCP port number that the HTTP server is listening to 
         in the new_configuration block."
    ::= { agSystem 18 }

agCurCfgLoginBanner OBJECT-TYPE
    SYNTAX  DisplayString (SIZE(0..79))
    MAX-ACCESS  read-only
    STATUS  current
    DESCRIPTION
        "The user defined login banner."
    ::= { agSystem 19 }

agNewCfgLoginBanner OBJECT-TYPE
    SYNTAX  DisplayString (SIZE(0..79))
    MAX-ACCESS  read-write
    STATUS  current
    DESCRIPTION
        "The user defined login banner."
    ::= { agSystem 20 }

agCurCfgSmtpHost OBJECT-TYPE
    SYNTAX  DisplayString (SIZE(0..127))
    MAX-ACCESS  read-only
    STATUS  current
    DESCRIPTION
        "The user defined SMTP host."
    ::= { agSystem 21 }

agNewCfgSmtpHost OBJECT-TYPE
    SYNTAX  DisplayString (SIZE(0..127))
    MAX-ACCESS  read-write
    STATUS  current
    DESCRIPTION
        "The user defined SMTP host."
    ::= { agSystem 22 }

agCurCfgConsole OBJECT-TYPE
    SYNTAX  INTEGER {
        enabled(1),
        disabled(2)
        }
    MAX-ACCESS  read-only
    STATUS  current
    DESCRIPTION
        "Enable or disable console output of syslog messages."
    ::= { agSystem 23 }

agNewCfgConsole OBJECT-TYPE
    SYNTAX  INTEGER {
        enabled(1),
        disabled(2)
        }
    MAX-ACCESS  read-write
    STATUS  current
    DESCRIPTION
        "Enable or disable console output of syslog messages."
    ::= { agSystem 24 }


agCurCfgBootp OBJECT-TYPE
    SYNTAX  INTEGER {
        enabled(2),
        disabled(3)
        }
    MAX-ACCESS  read-only
    STATUS  current
    DESCRIPTION
        "Enable or disable the use of BootP, as currently configured in the 
         current_configuration block."
    ::= { agSystem 29 }

agNewCfgBootp OBJECT-TYPE
    SYNTAX  INTEGER {
        enabled(2),
        disabled(3)
        }
    MAX-ACCESS  read-write
    STATUS  current
    DESCRIPTION
        "Enable or disable the use of BootP, in the new_configuration block."
    ::= { agSystem 30 }


agCurCfgSnmpTimeout OBJECT-TYPE
    SYNTAX  INTEGER (1..30)
    MAX-ACCESS  read-only
    STATUS  current
    DESCRIPTION
        "Once SNMP operations like agApplyConfig, agDiffState and  
         agDumpState, which use the state machine are done the resources
         used by these operations need to be freed by setting the state
         back to 'idle' so others can issue the commands via SNMP. 
         agSnmpTimeout indicates the number of minutes before the resources
         are freed and the state set back to 'idle' if this operation is not 
         performed by the user."
    ::= { agSystem 32 }

agNewCfgSnmpTimeout OBJECT-TYPE
    SYNTAX  INTEGER (1..30)
    MAX-ACCESS  read-write
    STATUS  current
    DESCRIPTION
        "Once SNMP operations like agApplyConfig, agDiffState and  
         agDumpState, which use the state machine are done the resources
         used by these operations need to be freed by setting the state
         back to 'idle' so others can issue the commands via SNMP. 
         agSnmpTimeout indicates the number of minutes before the resources
         are freed and the state set back to 'idle' if this operation is not 
         performed by the user."
    ::= { agSystem 33 }

agCurCfgTelnetServerPort OBJECT-TYPE
    SYNTAX  INTEGER (1..65535)
    MAX-ACCESS  read-only
    STATUS  current
    DESCRIPTION
        "The TCP port number that the telnet server listens for telnet 
         sessions."
    ::= { agSystem 34 }

agNewCfgTelnetServerPort OBJECT-TYPE
    SYNTAX  INTEGER (1..65535)
    MAX-ACCESS  read-write
    STATUS  current
    DESCRIPTION
        "The TCP port number that the telnet server listens for telnet 
         sessions."
    ::= { agSystem 35 }

agClearFlashDump OBJECT-TYPE
    SYNTAX  INTEGER {
        ok(1),
        clear(2)
        }
    MAX-ACCESS  read-write
    STATUS  current
    DESCRIPTION
        "This is an action object to clear the FLASH dump. 
         ok(1) is returned when this object is read. "
    ::= { agSystem 36 }

agCurCfgNortelMultipleStgMode OBJECT-TYPE
    SYNTAX  INTEGER {
        enabled(1),
        disabled(2)
        }
    MAX-ACCESS  read-only 
    STATUS  current
    DESCRIPTION
        "Enable or disable Nortel multiple STG mode."
    ::= { agSystem 37 }

agNewCfgNortelMultipleStgMode OBJECT-TYPE
    SYNTAX  INTEGER {
        enabled(1),
        disabled(2)
        }
    MAX-ACCESS  read-write
    STATUS  current
    DESCRIPTION
        "Enable or disable Nortel multiple STG mode."
    ::= { agSystem 38 }

agCurCfgTrapSrcIf OBJECT-TYPE
    SYNTAX  Integer32
    MAX-ACCESS  read-only
    STATUS  current
    DESCRIPTION
        "The SNMP trap source interface number."
    ::= { agSystem 39 }

agNewCfgTrapSrcIf OBJECT-TYPE
    SYNTAX  Integer32
    MAX-ACCESS  read-write
    STATUS  current
    DESCRIPTION
        "The SNMP trap source interface number."
    ::= { agSystem 40 }
    
agCurCfgARPMaxRate OBJECT-TYPE
    SYNTAX  INTEGER (0..65535)
    MAX-ACCESS  read-only
    STATUS  current
    DESCRIPTION
        "The maximum allowed rate of MP-destined ARP packets."
    ::= { agSystem 41 }

agNewCfgARPMaxRate OBJECT-TYPE
    SYNTAX  INTEGER (0..65535)
    MAX-ACCESS  read-write
    STATUS  current
    DESCRIPTION
        "The maximum allowed rate of MP-destined ARP packets."
    ::= { agSystem 42 }
    
agCurCfgICMPMaxRate OBJECT-TYPE
    SYNTAX  INTEGER (0..65535)
    MAX-ACCESS  read-only
    STATUS  current
    DESCRIPTION
        "The maximum allowed rate of MP-destined ICMP packets."
    ::= { agSystem 43 }

agNewCfgICMPMaxRate OBJECT-TYPE
    SYNTAX  INTEGER (0..65535)
    MAX-ACCESS  read-write
    STATUS  current
    DESCRIPTION
        "The maximum allowed rate of MP-destined ICMP packets."
    ::= { agSystem 44 }

agCurCfgTCPMaxRate OBJECT-TYPE
    SYNTAX  INTEGER (0..65535)
    MAX-ACCESS  read-only
    STATUS  current
    DESCRIPTION
        "The maximum allowed rate of MP-destined TCP packets."
    ::= { agSystem 45 }

agNewCfgTCPMaxRate OBJECT-TYPE
    SYNTAX  INTEGER (0..65535)
    MAX-ACCESS  read-write
    STATUS  current
    DESCRIPTION
        "The maximum allowed rate of MP-destined TCP packets."
    ::= { agSystem 46 }

agCurCfgUDPMaxRate OBJECT-TYPE
    SYNTAX  INTEGER (0..65535)
    MAX-ACCESS  read-only
    STATUS  current
    DESCRIPTION
        "The maximum allowed rate of MP-destined UDP packets."
    ::= { agSystem 47 }

agNewCfgUDPMaxRate OBJECT-TYPE
    SYNTAX  INTEGER (0..65535)
    MAX-ACCESS  read-write
    STATUS  current
    DESCRIPTION
        "The maximum allowed rate of MP-destined UDP packets."
    ::= { agSystem 48 }

agCurCfgHttpsServerPort OBJECT-TYPE
    SYNTAX  INTEGER (1..65535)
    MAX-ACCESS  read-only
    STATUS  current
    DESCRIPTION
        "The TCP port number that the HTTPS server is listening to 
         in the current_configuration block."
    ::= { agSystem 49 }

agNewCfgHttpsServerPort OBJECT-TYPE
    SYNTAX  INTEGER (1..65535)
    MAX-ACCESS  read-write
    STATUS  current
    DESCRIPTION
        "The TCP port number that the HTTPS server is listening to 
         in the new_configuration block."
    ::= { agSystem 50 }



agCurDaylightSavings   OBJECT-TYPE
    SYNTAX  INTEGER {
    none(0),
    africa-Algeria(1),
    africa-Angola(2),
    africa-Benin(3),
    africa-Botswana(4),
    africa-Burkina-Faso(5),
    africa-Burundi(6),
    africa-Cameroon(7),
    africa-Central-African-Rep(8),
    africa-Chad(9),
    africa-Congo-WestDemRepCongo(10),
    africa-Congo-EastDemRepCongo(11),
    africa-Congo-Rep(12),
    africa-Cote-dIvoire(13),
    africa-Djibouti(14),
    africa-Egypt(15),
    africa-Equatorial-Guinea(16),
    africa-Eritrea(17),
    africa-Ethiopia(18),
    africa-Gabon(19),
    africa-Gambia(20),
    africa-Ghana(21),
    africa-Guinea(22),
    africa-Guinea-Bissau(23),
    africa-Kenya(24),
    africa-Lesotho(25),
    africa-Liberia(26),
    africa-Libya(27),
    africa-Malawi(28),
    africa-Mali-SouthWestMali(29),
    africa-Mali-NorthEastMali(30),
    africa-Mauritania(31),
    africa-Morocco(32),
    africa-Mozambique(33),
    africa-Namibia(34),
    africa-Niger(35),
    africa-Nigeria(36),
    africa-Rwanda(37),
    africa-SaoTome-And-Principe(38),
    africa-Senegal(39),
    africa-SierraLeone(40),
    africa-Somalia(41),
    africa-SouthAfrica(42),
    africa-Spain-Mainland(43),
    africa-Spain-CeutaMelilla(44),
    africa-Spain-CanaryIslands(45),
    africa-Sudan(46), 
    africa-Swaziland(47),
    africa-Tanzania(48),
    africa-Togo(49),
    africa-Tunisia(50),
    africa-Uganda(51),
    africa-Western-Sahara(52),
    africa-Zambia(53),
    africa-Zimbabwe(54),
    americas-Anguilla(55),
    americas-Antigua-Barbuda(56),
    americas-Argentina-EArgentina(57),
    americas-Argentina-MostLocations(58),
    americas-Argentina-Jujuy(59),
    americas-Argentina-Catamarca(60),
    americas-Argentina-Mendoza(61),
    americas-Aruba(62),
    americas-Bahamas(63),
    americas-Barbados(64),
    americas-Belize(65),
    americas-Bolivia(66), 
    americas-Brazil-AtlanticIslands(67),
    americas-Brazil-AmapaEPara(68),
    americas-Brazil-NEBrazil(69),
    americas-Brazil-Pernambuco(70), 
    americas-Brazil-Tocantins(71),
    americas-Brazil-AlagoasSergipe(72),
    americas-Brazil-SSEBrazil(73),
    americas-Brazil-MatoGrossoDoSul(74),
    americas-Brazil-WParaRondonia(75),
    americas-Brazil-Roraima(76),
    americas-Brazil-EAmazonas(77),
    americas-Brazil-WAmazonas(78),
    americas-Brazil-Acre(79),
    americas-Canada-NewfoundlandIsland(80),
    americas-Canada-AtlanTime-NovaScotia(81),
    americas-Canada-AtlanTime-ELabrador(82),
    americas-Canada-EastTime-OntarioMostlocation(83),
    americas-Canada-EastTime-ThunderBay(84),
    americas-Canada-EastStdTime-PangnirtungNunavut(85),
    americas-Canada-EastStdTime-EastNunavut(86),
    americas-Canada-EastStdTime-CenNunavut(87),
    americas-Canada-CenTime-ManitobaWestOntario(88),
    americas-Canada-CenTime-RainyRiver(89),
    americas-Canada-CenTime-WestNunavut(90),
    americas-Canada-CenStdTime-SaskatchewanMostlocation(91),
    americas-Canada-CenStdTime-SaskatchewanMidwest(92),
    americas-Canada-MountTime-AlbertaEastBritishColumbia(93),
    americas-Canada-MountTime-CentralNorthwestTerritories(94),
    americas-Canada-MountTime-WestNorthwestTerritories(95),
    americas-Canada-MountStdTime-DawsonCrkStJohnBritColumbia(96),
    americas-Canada-PacificTime-WestBritishColumbia(97),
    americas-Canada-PacificTime-SouthYukon(98),
    americas-Canada-PacificTime-NorthYukon(99),
    americas-CaymanIslands(100),
    americas-Chile-MostLocation(101),
    americas-Chile-EasterIsland(102),
    americas-Colombia(103),
    americas-CostaRica(104),
    americas-Cuba(105),
    americas-Dominica(106), 
    americas-DominicanRepublic (107),
    americas-Ecuador(108),
    americas-ElSalvado(109),
    americas-FrenchGuiana(110),
    americas-Greenland-MostLocation(111),
    americas-Greenland-EastCoastNorthScoresbysund(112),
    americas-Greenland-ScoresbysundIttoqqortoormiit(113),
    americas-Greenland-ThulePituffik(114),
    americas-Grenada(115),
    americas-Guadeloupe(116),
    americas-Guatemala(117),
    americas-Guyana(118),
    americas-Haiti(119),
    americas-Honduras(120),
    americas-Jamaica(121),
    americas-Martinique(122),
    americas-Mexico-CentTime-Mostlocations(123),
    americas-Mexico-CentTime-QuintanaRoo(124),
    americas-Mexico-CentTime-CampecheYucatan(125),
    americas-Mexico-CentTime-CoahuilaDurangoNuevoLeonTamaulipas(126),
    americas-Mexico-MountTime-SBajaNayaritSinaloa(127),
    americas-Mexico-MountTime-Chihuahua(128),
    americas-Mexico-MountStdTime-Sonora(129),
    americas-Mexico-PacificTime(130),
    americas-Montserrat(131),
    americas-NetherlandsAntilles(132),
    americas-Nicaragua(133),
    americas-Panama(134),
    americas-Paraguay(135),
    americas-Peru(136),
    americas-PuertoRico(137),
    americas-StKittsAndNevis(138), 
    americas-StLucia(139),
    americas-StPierreAndMiquelon(140),
    americas-StVincent(141),
    americas-Suriname(142),
    americas-TrinidadAndTobago(143),
    americas-TurksAndCaicosIs(144),
    americas-USA-EastTime(145),
    americas-USA-EastTime-MichiganMostLocation(146),
    americas-USA-EastTime-KentuckyLouisvilleArea(147),
    americas-USA-EastTime-KentuckyWayneCounty(148),
    americas-USA-EastStdTime-IndianaMostLocations(149),
    americas-USA-EastStdTime-IndianaCrawfordCounty(150),
    americas-USA-EastStdTime-IndianaStarkeCounty(151),
    americas-USA-EastStdTime-IndianaSwitzerlandCounty(152),
    americas-USA-CentTime(153),
    americas-USA-CentTime-MichiganWisconsinborder(154),
    americas-USA-CentTime-NorthDakotaOliverCounty(155),
    americas-USA-MountTime(156),
    americas-USA-MountTime-SouthIdahoAndEastOregon(157),
    americas-USA-MountTime-Navajo(158),
    americas-USA-MountStdTime-Arizona(159),
    americas-USA-PacificTime(160),
    americas-USA-AlaskaTime(161),
    americas-USA-AlaskaTime-AlaskaPanhandle(162),
    americas-USA-AlaskaTime-AlaskaPanhandleNeck(163),
    americas-USA-AlaskaTime-WestAlaska(164),
    americas-USA-AleutianIslands(165),
    americas-USA-Hawaii(166),
    americas-Uruguay(167),
    americas-Venezuela(168),
    americas-VirginIslands-UK(169),
    americas-VirginIslands-US(170),
    antarctica-McMurdoStationRossIsland(171),
    antarctica-Amundsen-ScottStationSouthPole(172),
    antarctica-PalmerStationAnversIsland(173),
    antarctica-MawsonStationHolmeBay(174),
    antarctica-DavisStationVestfoldHills(175),
    antarctica-CaseyStationBaileyPeninsula(176),
    antarctica-VostokStationSMagneticPole(177),
    antarctica-Dumont-dUrvilleBaseTerreAdelie(178), 
    antarctica-SyowaStationEOngulI(179),
    arcticOcean-Svalbard(180),
    arcticOcean-JanMayen(181),
    asia-Afghanistan(182),
    asia-Armenia(183),
    asia-Azerbaijan(184),
    asia-Bahrain(185),
    asia-Bangladesh(186),
    asia-Bhutan(187),
    asia-Brunei(188),
    asia-Cambodia(189),
    asia-China-EastChinaBeijingGuangdongShanghai(190),
    asia-China-Heilongjiang(191),
    asia-China-CentralChinaGansuGuizhouSichuanYunnan(192),
    asia-China-TibetmostofXinjiangUyghur(193),
    asia-China-SouthwestXinjiangUyghur(194),
    asia-Cyprus(195),
    asia-EastTimor(196), 
    asia-Georgia(197),
    asia-HongKong(198),
    asia-India(199),
    asia-Indonesia-JavaAndSumatra(200),
    asia-Indonesia-WestCentralBorneo(201),
    asia-Indonesia-EastSouthBorneoCelebesBaliNusaTengarraWestTimor(202),
    asia-Indonesia-IrianJayaAndMoluccas(203),
    asia-Iran(204),
    asia-Iraq(205),
    asia-Israel(206),
    asia-Japan(207),
    asia-Jordan(208),
    asia-Kazakhstan-MostLocations(209),
    asia-Kazakhstan-QyzylordaKyzylorda(210),
    asia-Kazakhstan-Aqtobe(211),
    asia-Kazakhstan-AtyrauMangghystau(212),
    asia-Kazakhstan-WestKazakhstan(213),
    asia-Korea-North(214),
    asia-Korea-South(215),
    asia-Kuwait(216),
    asia-Kyrgyzstan(217), 
    asia-Laos(218),
    asia-Lebanon(219),
    asia-Macau(220),
    asia-Malaysia-PeninsularMalaysia(221),
    asia-Malaysia-SabahSarawak(222),
    asia-Mongolia-MostLocations(223),
    asia-Mongolia-BayanOlgiyGoviAltaiHovdUvsZavkhan(224),
    asia-Mongolia-DornodSukhbaatar(225),
    asia-Myanmar(226),
    asia-Nepal(227),
    asia-Oman(228),
    asia-Pakistan(229), 
    asia-Palestine(230),
    asia-Philippines(231),
    asia-Qatar(232),
    asia-Russia-Moscow-01Kaliningrad(233),
    asia-Russia-Moscow00WestRussia(234),
    asia-Russia-Moscow01CaspianSea(235),
    asia-Russia-Moscow02Urals(236),
    asia-Russia-Moscow03WestSiberia(237),
    asia-Russia-Moscow03Novosibirsk(238),
    asia-Russia-Moscow04YeniseiRiver(239),
    asia-Russia-Moscow05LakeBaikal(240),
    asia-Russia-Moscow06LenaRiver(241),
    asia-Russia-Moscow07AmurRiver(242),
    asia-Russia-Moscow07SakhalinIsland(243),
    asia-Russia-Moscow08Magadan(244),
    asia-Russia-Moscow09Kamchatka(245),
    asia-Russia-Moscow10BeringSea(246),
    asia-SaudiArabia(247),
    asia-Singapore(248),
    asia-SriLanka(249),
    asia-Syria(250),
    asia-Taiwan(251),
    asia-Tajikistan(252), 
    asia-Thailand(253),
    asia-Turkmenistan(254), 
    asia-UnitedArabEmirates(255),
    asia-Uzbekistan-WestUzbekistan(256),
    asia-Uzbekistan-EastUzbekistan(257),
    asia-Vietnam(258),
    asia-Yemen(259),
    atlanticOcean-Bermuda(260),
    atlanticOcean-CapeVerde(261),
    atlanticOcean-FaeroeIslands(262),
    atlanticOcean-FalklandIslands(263),
    atlanticOcean-Iceland(264),
    atlanticOcean-Portugal-Mainland(265),
    atlanticOcean-Portugal-MadeiraIslands(266),
    atlanticOcean-Portugal-Azores(267),
    atlanticOcean-SouthGeorgia-SouthSandwichIslands(268),
    atlanticOcean-Spain-Mainland(269),
    atlanticOcean-Spain-CeutaMelilla(270),
    atlanticOcean-Spain-CanaryIslands(271),
    atlanticOcean-StHelena(272),
    atlanticOcean-Svalbard-JanMayen(273),
    australia-LordHoweIsland(274),
    australia-Tasmania(275),
    australia-Victoria(276),
    australia-NewSouthWales-MostLocations(277),
    australia-NewSouthWales-Yancowinna(278),
    australia-Queensland-MostLocations(279),
    australia-Queensland-HolidayIslands(280),
    australia-SouthAustralia(281),
    australia-NorthernTerritory(282),
    australia-WesternAustralia(283),
    europe-Albania(284),
    europe-Andorra(285),
    europe-Austria(286),
    europe-Belarus(287),
    europe-Belgium(288),
    europe-BosniaHerzegovina(289),
    europe-Britain-UKGreatBritain(290),
    europe-Britain-UKNorthernIreland(291),
    europe-Bulgaria(292),
    europe-Croatia(293),
    europe-CzechRepublic(294),
    europe-Denmark(295),
    europe-Estonia(296),
    europe-Finland(297),
    europe-France(298), 
    europe-Germany(299),
    europe-Gibraltar(300),
    europe-Greece(301),
    europe-Hungary(302),
    europe-Ireland(303),
    europe-Italy(304),
    europe-Latvia(305),
    europe-Liechtenstein(306),
    europe-Lithuania(307),
    europe-Luxembourg(308),
    europe-Macedonia(309),
    europe-Malta(310),
    europe-Moldova(311),
    europe-Monaco(312),
    europe-Netherlands(313),
    europe-Norway(314),
    europe-Poland(315),
    europe-Portugal-Mainland(316),
    europe-Portugal-MadeiraIslands(317),
    europe-Portugal-Azores(318),
    europe-Romania(319),
    europe-Russia-Moscow-01Kaliningrad(320),
    europe-Russia-Moscow00WestRussia(321),
    europe-Russia-Moscow01CaspianSea(322),
    europe-Russia-Moscow02Urals(323),
    europe-Russia-Moscow03WestSiberia(324),
    europe-Russia-Moscow03Novosibirsk(325),
    europe-Russia-Moscow04YeniseiRiver(326),
    europe-Russia-Moscow05LakeBaikal(327),
    europe-Russia-Moscow06LenaRiver(328),
    europe-Russia-Moscow07AmurRiver(329),
    europe-Russia-Moscow07SakhalinIsland(330),
    europe-Russia-Moscow08Magadan(331),
    europe-Russia-Moscow09Kamchatka(332),
    europe-Russia-Moscow10BeringSea(333),
    europe-SanMarino(334),
    europe-Slovakia(335),
    europe-Slovenia(336),
    europe-Spain-Mainland(337),
    europe-Spain-CeutaAndMelilla(338),
    europe-Spain-CanaryIslands(339),
    europe-Sweden(340),
    europe-Switzerland(341),
    europe-Turkey(342),
    europe-Ukraine-MostLocations(343),
    europe-Ukraine-Ruthenia(344),
    europe-Ukraine-Zaporozhye-ELugansk(345),
    europe-Ukraine-CentralCrimea(346),
    europe-VaticanCity(347),
    europe-Yugoslavia(348),
    indianOcean-BritishIndianOceanTerritory(349),
    indianOcean-ChristmasIsland(350),
    indianOcean-CocosOrKeelingIslands(351),
    indianOcean-Comoros(352),
    indianOcean-FrenchSouthernAndAntarcticLands(353),
    indianOcean-Madagascar(354),
    indianOcean-Maldives(355),
    indianOcean-Mauritius(356),
    indianOcean-Mayotte(357),
    indianOcean-Reunion(358),
    indianOcean-Seychelles(359),
    pacificOcean-Chile-MostLocations(360),
    pacificOcean-Chile-EasterIslandSalayGomez(361),
    pacificOcean-CookIslands(362),
    pacificOcean-Ecuador(363),
    pacificOcean-Fiji(364),
    pacificOcean-FrenchPolynesia-SocietyIslands(365),
    pacificOcean-FrenchPolynesia-MarquesasIslands(366),
    pacificOcean-FrenchPolynesia-GambierIslands(367),
    pacificOcean-Guam(368),
    pacificOcean-Kiribati-GilbertIslands(369),
    pacificOcean-Kiribati-PhoenixIslands(370),
    pacificOcean-Kiribati-LineIslands(371),
    pacificOcean-MarshallIslands-MostLocations(372),
    pacificOcean-MarshallIslands-Kwajalein(373),
    pacificOcean-Micronesia-Yap(374),
    pacificOcean-Micronesia-TrukOrChuuk(375),
    pacificOcean-Micronesia-PonapeOrPohnpei(376), 
    pacificOcean-Micronesia-Kosrae(377),
    pacificOcean-Nauru(378),
    pacificOcean-NewCaledonia(379),
    pacificOcean-NewZealand-MostLocations(380),
    pacificOcean-NewZealand-ChathamIslands(381),
    pacificOcean-Niue(382),
    pacificOcean-NorfolkIsland(383),
    pacificOcean-NorthernMarianaIslands(384),
    pacificOcean-Palau(385),
    pacificOcean-PapuaNewGuinea(386),
    pacificOcean-Pitcairn(387),
    pacificOcean-SamoaAmerican(388),
    pacificOcean-SamoaWestern(389),
    pacificOcean-SolomonIslands(390),
    pacificOcean-Tokelau(391),
    pacificOcean-Tonga(392),
    pacificOcean-Tuvalu(393),
    pacificOceanUSA-EastTime(394),
    pacificOceanUSA-EastTime-MichiganMostLocations(395),
    pacificOceanUSA-EastTime-KentuckyLouisvilleArea(396),
    pacificOceanUSA-EastTime-KentuckyWayneCounty(397),
    pacificOceanUSA-EastStdTime-IndianaMostLocations(398),
    pacificOceanUSA-EastStdTime-IndianaCrawfordCounty(399),
    pacificOceanUSA-EastStdTime-IndianaStarkeCounty(400),
    pacificOceanUSA-EastStdTime-IndianaSwitzerlandCounty(401),
    pacificOceanUSA-CentTime(402),
    pacificOceanUSA-CentTime-MichiganWisconsinborder(403),
    pacificOceanUSA-CentTime-NorthDakotaOliverCounty(404),
    pacificOceanUSA-MountTime(405),
    pacificOceanUSA-MountTime-SouthIdahoAndEastOregon(406),
    pacificOceanUSA-MountTime-Navajo(407),
    pacificOceanUSA-MountStdTime-Arizona(408),
    pacificOceanUSA-PacificTime(409),
    pacificOceanUSA-AlaskaTime(410),
    pacificOceanUSA-AlaskaTime-AlaskaPanhandle(411),
    pacificOceanUSA-AlaskaTime-AlaskaPanhandleNeck(412),
    pacificOceanUSA-AlaskaTime-WestAlaska(413),
    pacificOceanUSA-AleutianIslands(414),
    pacificOceanUSA-Hawaii(415),
    pacificOcean-USMinorOutlyingIslands-JohnstonAtoll(416),
    pacificOcean-USMinorOutlyingIslands-MidwayIslands(417),
    pacificOcean-USMinorOutlyingIslands-WakeIsland(418),
    pacificOcean-Vanuatu(419),
    pacificOcean-WallisAndFutuna(420)
	}
    MAX-ACCESS read-only 
    STATUS  current 
    DESCRIPTION
        "The daylight savings location."
    ::= { agSystem 55 }

agNewDaylightSavings   OBJECT-TYPE
    SYNTAX  INTEGER  {
    none(0),
    africa-Algeria(1),
    africa-Angola(2),
    africa-Benin(3),
    africa-Botswana(4),
    africa-Burkina-Faso(5),
    africa-Burundi(6),
    africa-Cameroon(7),
    africa-Central-African-Rep(8),
    africa-Chad(9),
    africa-Congo-WestDemRepCongo(10),
    africa-Congo-EastDemRepCongo(11),
    africa-Congo-Rep(12),
    africa-Cote-dIvoire(13),
    africa-Djibouti(14),
    africa-Egypt(15),
    africa-Equatorial-Guinea(16),
    africa-Eritrea(17),
    africa-Ethiopia(18),
    africa-Gabon(19),
    africa-Gambia(20),
    africa-Ghana(21),
    africa-Guinea(22),
    africa-Guinea-Bissau(23),
    africa-Kenya(24),
    africa-Lesotho(25),
    africa-Liberia(26),
    africa-Libya(27),
    africa-Malawi(28),
    africa-Mali-SouthWestMali(29),
    africa-Mali-NorthEastMali(30),
    africa-Mauritania(31),
    africa-Morocco(32),
    africa-Mozambique(33),
    africa-Namibia(34),
    africa-Niger(35),
    africa-Nigeria(36),
    africa-Rwanda(37),
    africa-SaoTome-And-Principe(38),
    africa-Senegal(39),
    africa-SierraLeone(40),
    africa-Somalia(41),
    africa-SouthAfrica(42),
    africa-Spain-Mainland(43),
    africa-Spain-CeutaMelilla(44),
    africa-Spain-CanaryIslands(45),
    africa-Sudan(46), 
    africa-Swaziland(47),
    africa-Tanzania(48),
    africa-Togo(49),
    africa-Tunisia(50),
    africa-Uganda(51),
    africa-Western-Sahara(52),
    africa-Zambia(53),
    africa-Zimbabwe(54),
    americas-Anguilla(55),
    americas-Antigua-Barbuda(56),
    americas-Argentina-EArgentina(57),
    americas-Argentina-MostLocations(58),
    americas-Argentina-Jujuy(59),
    americas-Argentina-Catamarca(60),
    americas-Argentina-Mendoza(61),
    americas-Aruba(62),
    americas-Bahamas(63),
    americas-Barbados(64),
    americas-Belize(65),
    americas-Bolivia(66), 
    americas-Brazil-AtlanticIslands(67),
    americas-Brazil-AmapaEPara(68),
    americas-Brazil-NEBrazil(69),
    americas-Brazil-Pernambuco(70), 
    americas-Brazil-Tocantins(71),
    americas-Brazil-AlagoasSergipe(72),
    americas-Brazil-SSEBrazil(73),
    americas-Brazil-MatoGrossoDoSul(74),
    americas-Brazil-WParaRondonia(75),
    americas-Brazil-Roraima(76),
    americas-Brazil-EAmazonas(77),
    americas-Brazil-WAmazonas(78),
    americas-Brazil-Acre(79),
    americas-Canada-NewfoundlandIsland(80),
    americas-Canada-AtlanTime-NovaScotia(81),
    americas-Canada-AtlanTime-ELabrador(82),
    americas-Canada-EastTime-OntarioMostlocation(83),
    americas-Canada-EastTime-ThunderBay(84),
    americas-Canada-EastStdTime-PangnirtungNunavut(85),
    americas-Canada-EastStdTime-EastNunavut(86),
    americas-Canada-EastStdTime-CenNunavut(87),
    americas-Canada-CenTime-ManitobaWestOntario(88),
    americas-Canada-CenTime-RainyRiver(89),
    americas-Canada-CenTime-WestNunavut(90),
    americas-Canada-CenStdTime-SaskatchewanMostlocation(91),
    americas-Canada-CenStdTime-SaskatchewanMidwest(92),
    americas-Canada-MountTime-AlbertaEastBritishColumbia(93),
    americas-Canada-MountTime-CentralNorthwestTerritories(94),
    americas-Canada-MountTime-WestNorthwestTerritories(95),
    americas-Canada-MountStdTime-DawsonCrkStJohnBritColumbia(96),
    americas-Canada-PacificTime-WestBritishColumbia(97),
    americas-Canada-PacificTime-SouthYukon(98),
    americas-Canada-PacificTime-NorthYukon(99),
    americas-CaymanIslands(100),
    americas-Chile-MostLocation(101),
    americas-Chile-EasterIsland(102),
    americas-Colombia(103),
    americas-CostaRica(104),
    americas-Cuba(105),
    americas-Dominica(106), 
    americas-DominicanRepublic (107),
    americas-Ecuador(108),
    americas-ElSalvado(109),
    americas-FrenchGuiana(110),
    americas-Greenland-MostLocation(111),
    americas-Greenland-EastCoastNorthScoresbysund(112),
    americas-Greenland-ScoresbysundIttoqqortoormiit(113),
    americas-Greenland-ThulePituffik(114),
    americas-Grenada(115),
    americas-Guadeloupe(116),
    americas-Guatemala(117),
    americas-Guyana(118),
    americas-Haiti(119),
    americas-Honduras(120),
    americas-Jamaica(121),
    americas-Martinique(122),
    americas-Mexico-CentTime-Mostlocations(123),
    americas-Mexico-CentTime-QuintanaRoo(124),
    americas-Mexico-CentTime-CampecheYucatan(125),
    americas-Mexico-CentTime-CoahuilaDurangoNuevoLeonTamaulipas(126),
    americas-Mexico-MountTime-SBajaNayaritSinaloa(127),
    americas-Mexico-MountTime-Chihuahua(128),
    americas-Mexico-MountStdTime-Sonora(129),
    americas-Mexico-PacificTime(130),
    americas-Montserrat(131),
    americas-NetherlandsAntilles(132),
    americas-Nicaragua(133),
    americas-Panama(134),
    americas-Paraguay(135),
    americas-Peru(136),
    americas-PuertoRico(137),
    americas-StKittsAndNevis(138), 
    americas-StLucia(139),
    americas-StPierreAndMiquelon(140),
    americas-StVincent(141),
    americas-Suriname(142),
    americas-TrinidadAndTobago(143),
    americas-TurksAndCaicosIs(144),
    americas-USA-EastTime(145),
    americas-USA-EastTime-MichiganMostLocation(146),
    americas-USA-EastTime-KentuckyLouisvilleArea(147),
    americas-USA-EastTime-KentuckyWayneCounty(148),
    americas-USA-EastStdTime-IndianaMostLocations(149),
    americas-USA-EastStdTime-IndianaCrawfordCounty(150),
    americas-USA-EastStdTime-IndianaStarkeCounty(151),
    americas-USA-EastStdTime-IndianaSwitzerlandCounty(152),
    americas-USA-CentTime(153),
    americas-USA-CentTime-MichiganWisconsinborder(154),
    americas-USA-CentTime-NorthDakotaOliverCounty(155),
    americas-USA-MountTime(156),
    americas-USA-MountTime-SouthIdahoAndEastOregon(157),
    americas-USA-MountTime-Navajo(158),
    americas-USA-MountStdTime-Arizona(159),
    americas-USA-PacificTime(160),
    americas-USA-AlaskaTime(161),
    americas-USA-AlaskaTime-AlaskaPanhandle(162),
    americas-USA-AlaskaTime-AlaskaPanhandleNeck(163),
    americas-USA-AlaskaTime-WestAlaska(164),
    americas-USA-AleutianIslands(165),
    americas-USA-Hawaii(166),
    americas-Uruguay(167),
    americas-Venezuela(168),
    americas-VirginIslands-UK(169),
    americas-VirginIslands-US(170),
    antarctica-McMurdoStationRossIsland(171),
    antarctica-Amundsen-ScottStationSouthPole(172),
    antarctica-PalmerStationAnversIsland(173),
    antarctica-MawsonStationHolmeBay(174),
    antarctica-DavisStationVestfoldHills(175),
    antarctica-CaseyStationBaileyPeninsula(176),
    antarctica-VostokStationSMagneticPole(177),
    antarctica-Dumont-dUrvilleBaseTerreAdelie(178), 
    antarctica-SyowaStationEOngulI(179),
    arcticOcean-Svalbard(180),
    arcticOcean-JanMayen(181),
    asia-Afghanistan(182),
    asia-Armenia(183),
    asia-Azerbaijan(184),
    asia-Bahrain(185),
    asia-Bangladesh(186),
    asia-Bhutan(187),
    asia-Brunei(188),
    asia-Cambodia(189),
    asia-China-EastChinaBeijingGuangdongShanghai(190),
    asia-China-Heilongjiang(191),
    asia-China-CentralChinaGansuGuizhouSichuanYunnan(192),
    asia-China-TibetmostofXinjiangUyghur(193),
    asia-China-SouthwestXinjiangUyghur(194),
    asia-Cyprus(195),
    asia-EastTimor(196), 
    asia-Georgia(197),
    asia-HongKong(198),
    asia-India(199),
    asia-Indonesia-JavaAndSumatra(200),
    asia-Indonesia-WestCentralBorneo(201),
    asia-Indonesia-EastSouthBorneoCelebesBaliNusaTengarraWestTimor(202),
    asia-Indonesia-IrianJayaAndMoluccas(203),
    asia-Iran(204),
    asia-Iraq(205),
    asia-Israel(206),
    asia-Japan(207),
    asia-Jordan(208),
    asia-Kazakhstan-MostLocations(209),
    asia-Kazakhstan-QyzylordaKyzylorda(210),
    asia-Kazakhstan-Aqtobe(211),
    asia-Kazakhstan-AtyrauMangghystau(212),
    asia-Kazakhstan-WestKazakhstan(213),
    asia-Korea-North(214),
    asia-Korea-South(215),
    asia-Kuwait(216),
    asia-Kyrgyzstan(217), 
    asia-Laos(218),
    asia-Lebanon(219),
    asia-Macau(220),
    asia-Malaysia-PeninsularMalaysia(221),
    asia-Malaysia-SabahSarawak(222),
    asia-Mongolia-MostLocations(223),
    asia-Mongolia-BayanOlgiyGoviAltaiHovdUvsZavkhan(224),
    asia-Mongolia-DornodSukhbaatar(225),
    asia-Myanmar(226),
    asia-Nepal(227),
    asia-Oman(228),
    asia-Pakistan(229), 
    asia-Palestine(230),
    asia-Philippines(231),
    asia-Qatar(232),
    asia-Russia-Moscow-01Kaliningrad(233),
    asia-Russia-Moscow00WestRussia(234),
    asia-Russia-Moscow01CaspianSea(235),
    asia-Russia-Moscow02Urals(236),
    asia-Russia-Moscow03WestSiberia(237),
    asia-Russia-Moscow03Novosibirsk(238),
    asia-Russia-Moscow04YeniseiRiver(239),
    asia-Russia-Moscow05LakeBaikal(240),
    asia-Russia-Moscow06LenaRiver(241),
    asia-Russia-Moscow07AmurRiver(242),
    asia-Russia-Moscow07SakhalinIsland(243),
    asia-Russia-Moscow08Magadan(244),
    asia-Russia-Moscow09Kamchatka(245),
    asia-Russia-Moscow10BeringSea(246),
    asia-SaudiArabia(247),
    asia-Singapore(248),
    asia-SriLanka(249),
    asia-Syria(250),
    asia-Taiwan(251),
    asia-Tajikistan(252), 
    asia-Thailand(253),
    asia-Turkmenistan(254), 
    asia-UnitedArabEmirates(255),
    asia-Uzbekistan-WestUzbekistan(256),
    asia-Uzbekistan-EastUzbekistan(257),
    asia-Vietnam(258),
    asia-Yemen(259),
    atlanticOcean-Bermuda(260),
    atlanticOcean-CapeVerde(261),
    atlanticOcean-FaeroeIslands(262),
    atlanticOcean-FalklandIslands(263),
    atlanticOcean-Iceland(264),
    atlanticOcean-Portugal-Mainland(265),
    atlanticOcean-Portugal-MadeiraIslands(266),
    atlanticOcean-Portugal-Azores(267),
    atlanticOcean-SouthGeorgia-SouthSandwichIslands(268),
    atlanticOcean-Spain-Mainland(269),
    atlanticOcean-Spain-CeutaMelilla(270),
    atlanticOcean-Spain-CanaryIslands(271),
    atlanticOcean-StHelena(272),
    atlanticOcean-Svalbard-JanMayen(273),
    australia-LordHoweIsland(274),
    australia-Tasmania(275),
    australia-Victoria(276),
    australia-NewSouthWales-MostLocations(277),
    australia-NewSouthWales-Yancowinna(278),
    australia-Queensland-MostLocations(279),
    australia-Queensland-HolidayIslands(280),
    australia-SouthAustralia(281),
    australia-NorthernTerritory(282),
    australia-WesternAustralia(283),
    europe-Albania(284),
    europe-Andorra(285),
    europe-Austria(286),
    europe-Belarus(287),
    europe-Belgium(288),
    europe-BosniaHerzegovina(289),
    europe-Britain-UKGreatBritain(290),
    europe-Britain-UKNorthernIreland(291),
    europe-Bulgaria(292),
    europe-Croatia(293),
    europe-CzechRepublic(294),
    europe-Denmark(295),
    europe-Estonia(296),
    europe-Finland(297),
    europe-France(298), 
    europe-Germany(299),
    europe-Gibraltar(300),
    europe-Greece(301),
    europe-Hungary(302),
    europe-Ireland(303),
    europe-Italy(304),
    europe-Latvia(305),
    europe-Liechtenstein(306),
    europe-Lithuania(307),
    europe-Luxembourg(308),
    europe-Macedonia(309),
    europe-Malta(310),
    europe-Moldova(311),
    europe-Monaco(312),
    europe-Netherlands(313),
    europe-Norway(314),
    europe-Poland(315),
    europe-Portugal-Mainland(316),
    europe-Portugal-MadeiraIslands(317),
    europe-Portugal-Azores(318),
    europe-Romania(319),
    europe-Russia-Moscow-01Kaliningrad(320),
    europe-Russia-Moscow00WestRussia(321),
    europe-Russia-Moscow01CaspianSea(322),
    europe-Russia-Moscow02Urals(323),
    europe-Russia-Moscow03WestSiberia(324),
    europe-Russia-Moscow03Novosibirsk(325),
    europe-Russia-Moscow04YeniseiRiver(326),
    europe-Russia-Moscow05LakeBaikal(327),
    europe-Russia-Moscow06LenaRiver(328),
    europe-Russia-Moscow07AmurRiver(329),
    europe-Russia-Moscow07SakhalinIsland(330),
    europe-Russia-Moscow08Magadan(331),
    europe-Russia-Moscow09Kamchatka(332),
    europe-Russia-Moscow10BeringSea(333),
    europe-SanMarino(334),
    europe-Slovakia(335),
    europe-Slovenia(336),
    europe-Spain-Mainland(337),
    europe-Spain-CeutaAndMelilla(338),
    europe-Spain-CanaryIslands(339),
    europe-Sweden(340),
    europe-Switzerland(341),
    europe-Turkey(342),
    europe-Ukraine-MostLocations(343),
    europe-Ukraine-Ruthenia(344),
    europe-Ukraine-Zaporozhye-ELugansk(345),
    europe-Ukraine-CentralCrimea(346),
    europe-VaticanCity(347),
    europe-Yugoslavia(348),
    indianOcean-BritishIndianOceanTerritory(349),
    indianOcean-ChristmasIsland(350),
    indianOcean-CocosOrKeelingIslands(351),
    indianOcean-Comoros(352),
    indianOcean-FrenchSouthernAndAntarcticLands(353),
    indianOcean-Madagascar(354),
    indianOcean-Maldives(355),
    indianOcean-Mauritius(356),
    indianOcean-Mayotte(357),
    indianOcean-Reunion(358),
    indianOcean-Seychelles(359),
    pacificOcean-Chile-MostLocations(360),
    pacificOcean-Chile-EasterIslandSalayGomez(361),
    pacificOcean-CookIslands(362),
    pacificOcean-Ecuador(363),
    pacificOcean-Fiji(364),
    pacificOcean-FrenchPolynesia-SocietyIslands(365),
    pacificOcean-FrenchPolynesia-MarquesasIslands(366),
    pacificOcean-FrenchPolynesia-GambierIslands(367),
    pacificOcean-Guam(368),
    pacificOcean-Kiribati-GilbertIslands(369),
    pacificOcean-Kiribati-PhoenixIslands(370),
    pacificOcean-Kiribati-LineIslands(371),
    pacificOcean-MarshallIslands-MostLocations(372),
    pacificOcean-MarshallIslands-Kwajalein(373),
    pacificOcean-Micronesia-Yap(374),
    pacificOcean-Micronesia-TrukOrChuuk(375),
    pacificOcean-Micronesia-PonapeOrPohnpei(376), 
    pacificOcean-Micronesia-Kosrae(377),
    pacificOcean-Nauru(378),
    pacificOcean-NewCaledonia(379),
    pacificOcean-NewZealand-MostLocations(380),
    pacificOcean-NewZealand-ChathamIslands(381),
    pacificOcean-Niue(382),
    pacificOcean-NorfolkIsland(383),
    pacificOcean-NorthernMarianaIslands(384),
    pacificOcean-Palau(385),
    pacificOcean-PapuaNewGuinea(386),
    pacificOcean-Pitcairn(387),
    pacificOcean-SamoaAmerican(388),
    pacificOcean-SamoaWestern(389),
    pacificOcean-SolomonIslands(390),
    pacificOcean-Tokelau(391),
    pacificOcean-Tonga(392),
    pacificOcean-Tuvalu(393),
    pacificOceanUSA-EastTime(394),
    pacificOceanUSA-EastTime-MichiganMostLocations(395),
    pacificOceanUSA-EastTime-KentuckyLouisvilleArea(396),
    pacificOceanUSA-EastTime-KentuckyWayneCounty(397),
    pacificOceanUSA-EastStdTime-IndianaMostLocations(398),
    pacificOceanUSA-EastStdTime-IndianaCrawfordCounty(399),
    pacificOceanUSA-EastStdTime-IndianaStarkeCounty(400),
    pacificOceanUSA-EastStdTime-IndianaSwitzerlandCounty(401),
    pacificOceanUSA-CentTime(402),
    pacificOceanUSA-CentTime-MichiganWisconsinborder(403),
    pacificOceanUSA-CentTime-NorthDakotaOliverCounty(404),
    pacificOceanUSA-MountTime(405),
    pacificOceanUSA-MountTime-SouthIdahoAndEastOregon(406),
    pacificOceanUSA-MountTime-Navajo(407),
    pacificOceanUSA-MountStdTime-Arizona(408),
    pacificOceanUSA-PacificTime(409),
    pacificOceanUSA-AlaskaTime(410),
    pacificOceanUSA-AlaskaTime-AlaskaPanhandle(411),
    pacificOceanUSA-AlaskaTime-AlaskaPanhandleNeck(412),
    pacificOceanUSA-AlaskaTime-WestAlaska(413),
    pacificOceanUSA-AleutianIslands(414),
    pacificOceanUSA-Hawaii(415),
    pacificOcean-USMinorOutlyingIslands-JohnstonAtoll(416),
    pacificOcean-USMinorOutlyingIslands-MidwayIslands(417),
    pacificOcean-USMinorOutlyingIslands-WakeIsland(418),
    pacificOcean-Vanuatu(419),
    pacificOceanWallisAndFutuna(420)
	}
    MAX-ACCESS read-write 
    STATUS  current 
    DESCRIPTION
        "The daylight savings location."
    ::= { agSystem 56 }

agCurCfgIdleCLITimeout OBJECT-TYPE
    SYNTAX  INTEGER (1..10080)
    MAX-ACCESS  read-only
    STATUS  current
    DESCRIPTION
        "Set idle CLI sessions timeout."
    ::= { agSystem 57 }

agNewCfgIdleCLITimeout OBJECT-TYPE
    SYNTAX INTEGER (1..10080) 
    MAX-ACCESS  read-write
    STATUS  current
    DESCRIPTION
        "Set idle CLI sessions timeout."
    ::= { agSystem 58 }

agCurCfgXMLCfgServerPort OBJECT-TYPE
    SYNTAX  INTEGER (1..65535)
    MAX-ACCESS  read-only
    STATUS  current
    DESCRIPTION
        "The TCP port number that the XML config server is listening to 
         in the current_configuration block. If HTTPS is also enabled then
         the port numbers should be the same"
    ::= { agSystem 59 }

agNewCfgXMLCfgServerPort OBJECT-TYPE
    SYNTAX  INTEGER (1..65535)
    MAX-ACCESS  read-write
    STATUS  current
    DESCRIPTION
        "The TCP port number that the XML config server is listening to 
         in the new_configuration block. If HTTPS is also enabled then
         the port numbers should be the same"
    ::= { agSystem 60 }

agSymantecGlobalState OBJECT-TYPE
    SYNTAX  INTEGER {
        disabled(1),
        enabled(2)
        }
    MAX-ACCESS  read-write
    STATUS  current
    DESCRIPTION
        "This is an action object to globally enable or disable Symantec feature on the switch."
    ::= { agSystem 61 }



-- Auto-Discovery topology table info


-- Syslog Configuration
agCurCfgSyslogHost OBJECT-TYPE
    SYNTAX  IpAddress
    MAX-ACCESS  read-only
    STATUS  current
    DESCRIPTION
        "The syslog host IP address, as currently configured in
         the current_configuration block."
    ::= { agSyslog 1 }

agNewCfgSyslogHost OBJECT-TYPE
    SYNTAX  IpAddress
    MAX-ACCESS  read-write
    STATUS  current
    DESCRIPTION
        "The syslog host IP address, in the new_configuration block."
    ::= { agSyslog 2 }

agCurCfgSyslog2Host OBJECT-TYPE
    SYNTAX  IpAddress
    MAX-ACCESS  read-only
    STATUS  current
    DESCRIPTION
        "The second syslog host IP address, as currently configured in
         the current_configuration block."
    ::= { agSyslog 3 }

agNewCfgSyslog2Host OBJECT-TYPE
    SYNTAX  IpAddress
    MAX-ACCESS  read-write
    STATUS  current
    DESCRIPTION
        "The second syslog host IP address, in the new_configuration block."
    ::= { agSyslog 4 }

agCurCfgSyslogFac   OBJECT-TYPE
    SYNTAX  INTEGER  {
	local0(1),
	local1(2),
	local2(3),
	local3(4),
	local4(5),
	local5(6),
	local6(7),
	local7(8)
	}
    MAX-ACCESS  read-only
    STATUS  current
    DESCRIPTION
        "The facility of syslog host in the current_configuration block."
    ::= { agSyslog 5 }

agNewCfgSyslogFac   OBJECT-TYPE
    SYNTAX  INTEGER  {
	local0(1), 
	local1(2),
	local2(3),
	local3(4),
	local4(5),
	local5(6),
        local6(7),
	local7(8)
	}
    MAX-ACCESS  read-write
    STATUS  current
    DESCRIPTION
        "The facility of syslog host in the new_configuration block."
    ::= { agSyslog 6 }

agCurCfgSyslog2Fac   OBJECT-TYPE
    SYNTAX  INTEGER  {
	local0(1),
	local1(2),
	local2(3),
	local3(4),
	local4(5),
	local5(6),
	local6(7),
	local7(8)
	}
    MAX-ACCESS  read-only
    STATUS  current
    DESCRIPTION
        "The facility of syslog2 host in the current_configuration block."
    ::= { agSyslog 7 }

agNewCfgSyslog2Fac   OBJECT-TYPE
    SYNTAX  INTEGER  {
	local0(1), 
	local1(2),
	local2(3),
	local3(4),
        local4(5),
	local5(6),
        local6(7),
	local7(8)
	}
    MAX-ACCESS  read-write
    STATUS  current
    DESCRIPTION
        "The facility of syslogs host in the new_configuration block."
    ::= { agSyslog 8 }

agCurCfgSyslogSev   OBJECT-TYPE
    SYNTAX  INTEGER  {
        emerg0(1),
	alert1(2),
	crit2(3),
	err3(4),
	warning4(5),
	notice5(6),
	info6(7),
	debug7(8)
	}
    MAX-ACCESS  read-only
    STATUS  current
    DESCRIPTION
        "The severity of syslog host in the current configuration block."
    ::= { agSyslog 13 }

agNewCfgSyslogSev   OBJECT-TYPE
    SYNTAX  INTEGER  {
        emerg0(1),
	alert1(2),
	crit2(3),
	err3(4),
	warning4(5),
	notice5(6),
	info6(7),
	debug7(8)
	}
    MAX-ACCESS  read-write
    STATUS  current
    DESCRIPTION
        "The severity of syslog host in the new configuration block."
    ::= { agSyslog 14 }

agCurCfgSyslog2Sev   OBJECT-TYPE
    SYNTAX  INTEGER  {
        emerg0(1),
	alert1(2),
	crit2(3),
	err3(4),
	warning4(5),
	notice5(6),
	info6(7),
	debug7(8)
	}
    MAX-ACCESS  read-only
    STATUS  current
    DESCRIPTION
        "The severity of syslog2 host in the current configuration block."
    ::= { agSyslog 15 }

agNewCfgSyslog2Sev   OBJECT-TYPE
    SYNTAX  INTEGER  {
        emerg0(1),
	alert1(2),
	crit2(3),
	err3(4),
	warning4(5),
	notice5(6),
	info6(7),
	debug7(8)
	}
    MAX-ACCESS  read-write
    STATUS  current
    DESCRIPTION
        "The severity of syslogs host in the new configuration block."
    ::= { agSyslog 16 }

agClrSyslogMsgs OBJECT-TYPE
    SYNTAX  INTEGER {
        other(1),
        reset(2)
        }
    MAX-ACCESS  read-write
    STATUS  current
    DESCRIPTION
        "Clears all current Syslog messages."
    ::= { agSyslog 9 }

agSyslogMsgTableMaxSize OBJECT-TYPE
    SYNTAX  Integer32
    MAX-ACCESS  read-only
    STATUS  current
    DESCRIPTION
        "The maximum number of rows in the syslog message table."
    ::= { agSyslog 10 }

agSyslogMsgTable OBJECT-TYPE
    SYNTAX  SEQUENCE OF AgSyslogMsgTableEntry
    MAX-ACCESS  not-accessible
    STATUS  current
    DESCRIPTION
        "The table of syslog messages."
    ::= { agSyslog 11 }

agSyslogMsgTableEntry OBJECT-TYPE
    SYNTAX  AgSyslogMsgTableEntry
    MAX-ACCESS  not-accessible
    STATUS  current
    DESCRIPTION
        "A syslog message stored on the switch."
    INDEX   { agSyslogMsgIndex }
    ::= { agSyslogMsgTable 1 }

AgSyslogMsgTableEntry ::= SEQUENCE {
    agSyslogMsgIndex          Integer32,
    agSyslogMessage           DisplayString
    }

agSyslogMsgIndex OBJECT-TYPE
    SYNTAX  Integer32
    MAX-ACCESS  read-only
    STATUS  current
    DESCRIPTION
        "The syslog message table index."
    ::= { agSyslogMsgTableEntry 1 }

agSyslogMessage OBJECT-TYPE
    SYNTAX  DisplayString (SIZE(0..128))
    MAX-ACCESS  read-only
    STATUS  current
    DESCRIPTION
        "The syslog message."
    ::= { agSyslogMsgTableEntry 2 }

agLog OBJECT IDENTIFIER ::= { agSyslog 12 }

agNewCfgSyslogTrapConsole OBJECT-TYPE
    SYNTAX  INTEGER {
        enabled(1),
        disabled(2)
        }
    MAX-ACCESS  read-write
    STATUS  current
    DESCRIPTION
        "Enable or disable console syslog and SNMP trap, in the 
         new_configuration block."
    ::= { agLog 1 }

agCurCfgSyslogTrapConsole OBJECT-TYPE
    SYNTAX  INTEGER {
        enabled(1),
        disabled(2)
        }
    MAX-ACCESS  read-only
    STATUS  current
    DESCRIPTION
        "Enable or disable console syslog and SNMP trap, as currently 
         configured in the current_configuration block."
    ::= { agLog 2 }

agNewCfgSyslogTrapSystem OBJECT-TYPE
    SYNTAX  INTEGER {
        enabled(1),
        disabled(2)
        }
    MAX-ACCESS  read-write
    STATUS  current
    DESCRIPTION
        "Enable or disable system level syslog and SNMP trap, in the 
         new_configuration block."
    ::= { agLog 3 }

agCurCfgSyslogTrapSystem OBJECT-TYPE
    SYNTAX  INTEGER {
        enabled(1),
        disabled(2)
        }
    MAX-ACCESS  read-only
    STATUS  current
    DESCRIPTION
        "Enable or disable system level syslog and SNMP trap, as currently 
         configured in the current_configuration block."
    ::= { agLog 4 }

agNewCfgSyslogTrapMgmt OBJECT-TYPE
    SYNTAX  INTEGER {
        enabled(1),
        disabled(2)
        }
    MAX-ACCESS  read-write
    STATUS  current
    DESCRIPTION
        "Enable or disable management(flash, config, login) syslog and SNMP 
         trap, in the new_configuration block."
    ::= { agLog 5 }

agCurCfgSyslogTrapMgmt OBJECT-TYPE
    SYNTAX  INTEGER {
        enabled(1),
        disabled(2)
        }
    MAX-ACCESS  read-only
    STATUS  current
    DESCRIPTION
        "Enable or disable management(flash, config, login) syslog and SNMP 
         trap, as currently configured in the current_configuration block."
    ::= { agLog 6 }

agNewCfgSyslogTrapCli OBJECT-TYPE
    SYNTAX  INTEGER {
        enabled(1),
        disabled(2)
        }
    MAX-ACCESS  read-write
    STATUS  current
    DESCRIPTION
        "Enable or disable CLI generated error syslog and SNMP trap, in the 
	 new_configuration block."
    ::= { agLog 7 }

agCurCfgSyslogTrapCli OBJECT-TYPE
    SYNTAX  INTEGER {
        enabled(1),
        disabled(2)
        }
    MAX-ACCESS  read-only
    STATUS  current
    DESCRIPTION
        "Enable or disable CLI generated error syslog and SNMP trap, as 
         currently configured in the current_configuration block." 
    ::= { agLog 8 }

agNewCfgSyslogTrapStp OBJECT-TYPE
    SYNTAX  INTEGER {
        enabled(1),
        disabled(2)
        }
    MAX-ACCESS  read-write
    STATUS  current
    DESCRIPTION
        "Enable or disable spanning tree syslog and SNMP trap, in the 
         new_configuration block."
    ::= { agLog 9 }

agCurCfgSyslogTrapStp OBJECT-TYPE
    SYNTAX  INTEGER {
        enabled(1),
        disabled(2)
        }
    MAX-ACCESS  read-only
    STATUS  current
    DESCRIPTION
        "Enable or disable spanning tree syslog and SNMP trap, as currently 
         configured in the current_configuration block."
    ::= { agLog 10 }

agNewCfgSyslogTrapVlan OBJECT-TYPE
    SYNTAX  INTEGER {
        enabled(1),
        disabled(2)
        }
    MAX-ACCESS  read-write
    STATUS  current
    DESCRIPTION
        "Enable or disable VLAN syslog and SNMP trap, in the new_configuration
         block."
    ::= { agLog 11 }

agCurCfgSyslogTrapVlan OBJECT-TYPE
    SYNTAX  INTEGER {
        enabled(1),
        disabled(2)
        }
    MAX-ACCESS  read-only
    STATUS  current
    DESCRIPTION
        "Enable or disable VLAN syslog and SNMP trap, as currently configured 
         in the current_configuration block."
    ::= { agLog 12 }

agNewCfgSyslogTrapSlb OBJECT-TYPE
    SYNTAX  INTEGER {
        enabled(1),
        disabled(2)
        }
    MAX-ACCESS  read-write
    STATUS  current
    DESCRIPTION
        "Enable or disable SLB syslog and SNMP trap, in the new_configuration 
         block."
    ::= { agLog 13 }

agCurCfgSyslogTrapSlb OBJECT-TYPE
    SYNTAX  INTEGER {
        enabled(1),
        disabled(2)
        }
    MAX-ACCESS  read-only
    STATUS  current
    DESCRIPTION
        "Enable or disable SLB syslog and SNMP trap, as currently configured 
         in the current_configuration block."
    ::= { agLog 14 }

agNewCfgSyslogTrapGslb OBJECT-TYPE
    SYNTAX  INTEGER {
        enabled(1),
        disabled(2)
        }
    MAX-ACCESS  read-write
    STATUS  current
    DESCRIPTION
        "Enable or disable GSLB syslog and SNMP trap, in the new_configuration
         block."
    ::= { agLog 15 }

agCurCfgSyslogTrapGslb OBJECT-TYPE
    SYNTAX  INTEGER {
        enabled(1),
        disabled(2)
        }
    MAX-ACCESS  read-only
    STATUS  current
    DESCRIPTION
        "Enable or disable GSLB syslog and SNMP trap, as currently configured 
         in the current_configuration block."
    ::= { agLog 16 }

agNewCfgSyslogTrapFilter OBJECT-TYPE
    SYNTAX  INTEGER {
        enabled(1),
        disabled(2)
        }
    MAX-ACCESS  read-write
    STATUS  current
    DESCRIPTION
        "Enable or disable filter syslog and SNMP trap, in the 
         new_configuration block."
    ::= { agLog 17 }

agCurCfgSyslogTrapFilter OBJECT-TYPE
    SYNTAX  INTEGER {
        enabled(1),
        disabled(2)
        }
    MAX-ACCESS  read-only
    STATUS  current
    DESCRIPTION
        "Enable or disable filter syslog and SNMP trap, as currently 
         configured in the current_configuration block."
    ::= { agLog 18 }

agNewCfgSyslogTrapSsh OBJECT-TYPE
    SYNTAX  INTEGER {
        enabled(1),
        disabled(2)
        }
    MAX-ACCESS  read-write
    STATUS  current
    DESCRIPTION
        "Enable or disable SSH, RADIUS syslog and SNMP trap, in the 
         new_configuration block."
    ::= { agLog 19 }

agCurCfgSyslogTrapSsh OBJECT-TYPE
    SYNTAX  INTEGER {
        enabled(1),
        disabled(2)
        }
    MAX-ACCESS  read-only
    STATUS  current
    DESCRIPTION
        "Enable or disable SSH, RADIUS syslog and SNMP trap, as currently 
         configured in the current_configuration block."
    ::= { agLog 20 }

agNewCfgSyslogTrapVrrp OBJECT-TYPE
    SYNTAX  INTEGER {
        enabled(1),
        disabled(2)
        }
    MAX-ACCESS  read-write
    STATUS  current
    DESCRIPTION
        "Enable or disable VRRP syslog and SNMP trap, in the new_configuration
         block."
    ::= { agLog 21 }

agCurCfgSyslogTrapVrrp OBJECT-TYPE
    SYNTAX  INTEGER {
        enabled(1),
        disabled(2)
        }
    MAX-ACCESS  read-only
    STATUS  current
    DESCRIPTION
        "Enable or disable VRRP syslog and SNMP trap, as currently configured 
         in the current_configuration block."
    ::= { agLog 22 }

agNewCfgSyslogTrapBgp OBJECT-TYPE
    SYNTAX  INTEGER {
        enabled(1),
        disabled(2)
        }
    MAX-ACCESS  read-write
    STATUS  current
    DESCRIPTION
        "Enable or disable BGP syslog and SNMP trap, in the new_configuration 
         block."
    ::= { agLog 23 }

agCurCfgSyslogTrapBgp OBJECT-TYPE
    SYNTAX  INTEGER {
        enabled(1),
        disabled(2)
        }
    MAX-ACCESS  read-only
    STATUS  current
    DESCRIPTION
        "Enable or disable BGP syslog and SNMP trap, as currently configured 
         in the current_configuration block."
    ::= { agLog 24 }

agNewCfgSyslogTrapNtp OBJECT-TYPE
    SYNTAX  INTEGER {
        enabled(1),
        disabled(2)
        }
    MAX-ACCESS  read-write
    STATUS  current
    DESCRIPTION
        "Enable or disable NTP syslog and SNMP trap, in the new_configuration 
         block."
    ::= { agLog 25 }

agCurCfgSyslogTrapNtp OBJECT-TYPE
    SYNTAX  INTEGER {
        enabled(1),
        disabled(2)
        }
    MAX-ACCESS  read-only
    STATUS  current
    DESCRIPTION
        "Enable or disable NTP syslog and SNMP trap, as currently configured 
         in the current_configuration block."
    ::= { agLog 26 }

agNewCfgSyslogTrapIp OBJECT-TYPE
    SYNTAX  INTEGER {
        enabled(1),
        disabled(2)
        }
    MAX-ACCESS  read-write
    STATUS  current
    DESCRIPTION
        "Enable or disable IP related syslog and SNMP trap, in the 
         new_configuration block."
    ::= { agLog 31 }

agCurCfgSyslogTrapIp OBJECT-TYPE
    SYNTAX  INTEGER {
        enabled(1),
        disabled(2)
        }
    MAX-ACCESS  read-only
    STATUS  current
    DESCRIPTION
        "Enable or disable IP related syslog and SNMP trap, as currently 
         configured in the current_configuration block."
    ::= { agLog 32 }

agNewCfgSyslogTrapWeb OBJECT-TYPE
    SYNTAX  INTEGER {
        enabled(1),
        disabled(2)
        }
    MAX-ACCESS  read-write
    STATUS  current
    DESCRIPTION
        "Enable or disable WEBUI related syslog and SNMP trap, in the 
         new_configuration block."
    ::= { agLog 35 }

agCurCfgSyslogTrapWeb OBJECT-TYPE
    SYNTAX  INTEGER {
        enabled(1),
        disabled(2)
        }
    MAX-ACCESS  read-only
    STATUS  current
    DESCRIPTION
        "Enable or disable WEBUI related syslog and SNMP trap, as currently 
         configured in the current_configuration block."
    ::= { agLog 36 }

agNewCfgSyslogTrapSynAtk OBJECT-TYPE
    SYNTAX  INTEGER {
        enabled(1),
        disabled(2)
        }
    MAX-ACCESS  read-write
    STATUS  current
    DESCRIPTION
        "Enable or disable SYN attack detection related syslog and SNMP trap,
         in the new_configuration block."
    ::= { agLog 37 }

agCurCfgSyslogTrapSynAtk OBJECT-TYPE
    SYNTAX  INTEGER {
        enabled(1),
        disabled(2)
        }
    MAX-ACCESS  read-only
    STATUS  current
    DESCRIPTION
        "Enable or disable SYN attack detection related syslog and SNMP trap,
         as currently configured in the current_configuration block."
    ::= { agLog 38 }

agNewCfgSyslogTrapTcpLim OBJECT-TYPE
    SYNTAX  INTEGER {
        enabled(1),
        disabled(2)
        }
    MAX-ACCESS  read-write
    STATUS  current
    DESCRIPTION
        "Enable or disable TCP rate limiting related syslog and SNMP trap, 
         in the new_configuration block."
    ::= { agLog 39 }

agCurCfgSyslogTrapTcpLim OBJECT-TYPE
    SYNTAX  INTEGER {
        enabled(1),
        disabled(2)
        }
    MAX-ACCESS  read-only
    STATUS  current
    DESCRIPTION
        "Enable or disable TCP rate limiting related syslog and SNMP trap,
         as currently configured in the current_configuration block."
    ::= { agLog 40 }

agNewCfgSyslogTrapOspf OBJECT-TYPE
    SYNTAX  INTEGER {
        enabled(1),
        disabled(2)
        }
    MAX-ACCESS  read-write
    STATUS  current
    DESCRIPTION
        "Enable or disable OSPF related syslog and SNMP trap, 
         in the new_configuration block."
    ::= { agLog 41 }

agCurCfgSyslogTrapOspf OBJECT-TYPE
    SYNTAX  INTEGER {
        enabled(1),
        disabled(2)
        }
    MAX-ACCESS  read-only
    STATUS  current
    DESCRIPTION
        "Enable or disable OSPF related syslog and SNMP trap,
         as currently configured in the current_configuration block."
    ::= { agLog 42 }

agNewCfgSyslogTrapSecurity OBJECT-TYPE
    SYNTAX  INTEGER {
        enabled(1),
        disabled(2)
        }
    MAX-ACCESS  read-write
    STATUS  current
    DESCRIPTION
        "Enable or disable Security pack related syslog and SNMP trap,
         in the new_configuration block."
    ::= { agLog 43 }

agCurCfgSyslogTrapSecurity OBJECT-TYPE
    SYNTAX  INTEGER {
        enabled(1),
        disabled(2)
        }
    MAX-ACCESS  read-only
    STATUS  current
    DESCRIPTION
        "Enable or disable Security pack related syslog and SNMP trap,
         as currently configured in the current_configuration block."
    ::= { agLog 44 }

agNewCfgSyslogTrapRmon OBJECT-TYPE
    SYNTAX  INTEGER {
        enabled(1),
        disabled(2)
        }
    MAX-ACCESS  read-write
    STATUS  current
    DESCRIPTION
        "Enable or disable rmon related syslog and SNMP trap,
         in the new_configuration block."
    ::= { agLog 45 }

agCurCfgSyslogTrapRmon OBJECT-TYPE
    SYNTAX  INTEGER {
        enabled(1),
        disabled(2)
        }
    MAX-ACCESS  read-only
    STATUS  current
    DESCRIPTION
        "Enable or disable rmon related syslog and SNMP trap,
         as currently configured in the current_configuration block."
    ::= { agLog 46 }

agNewCfgSyslogTrapSlbAtk OBJECT-TYPE
    SYNTAX  INTEGER {
        enabled(1),
        disabled(2)
        }
    MAX-ACCESS  read-write
    STATUS  current
    DESCRIPTION
        "Enable or disable SLB ATK related syslog and SNMP trap,
         in the new_configuration block."
    ::= { agLog 47 }

agCurCfgSyslogTrapSlbAtk  OBJECT-TYPE
    SYNTAX  INTEGER {
        enabled(1),
        disabled(2)
        }
    MAX-ACCESS  read-only
    STATUS  current
    DESCRIPTION
        "Enable or disable SLB ATK related syslog and SNMP trap,
         as currently configured in the current_configuration block."
    ::= { agLog 48 }

-- Trap host table
agTrapHostTableMaxEnt OBJECT-TYPE
    SYNTAX  Integer32
    MAX-ACCESS  read-only
    STATUS  current
    DESCRIPTION
        "The maximum number of rows in the trap host table."
    ::= { agTrapHost 1 }

agCurCfgTrapHostTable OBJECT-TYPE
    SYNTAX  SEQUENCE OF AgCurCfgTrapHostEntry
    MAX-ACCESS  not-accessible
    STATUS  current
    DESCRIPTION
        "The table of trap hosts which to send SNMP traps in the 
         current_configuration block."
    ::= { agTrapHost 2 }

agCurCfgTrapHostEntry OBJECT-TYPE
    SYNTAX  AgCurCfgTrapHostEntry
    MAX-ACCESS  not-accessible
    STATUS  current
    DESCRIPTION
        "A row in the trap host table in the current_configuration block."
    INDEX   { agCurCfgTrapHostIndx }
    ::= { agCurCfgTrapHostTable 1 }

AgCurCfgTrapHostEntry ::= SEQUENCE {
    agCurCfgTrapHostIndx            Integer32,
    agCurCfgTrapHostIpAddr          IpAddress,
    agCurCfgTrapHostCommString      DisplayString
    }

agCurCfgTrapHostIndx OBJECT-TYPE
    SYNTAX  Integer32
    MAX-ACCESS  read-only
    STATUS  current
    DESCRIPTION
        "The index of the row in trap host table."
    ::= { agCurCfgTrapHostEntry 1 }

agCurCfgTrapHostIpAddr OBJECT-TYPE
    SYNTAX  IpAddress
    MAX-ACCESS  read-only
    STATUS  current
    DESCRIPTION
        "The IP address of a trap host."
    ::= { agCurCfgTrapHostEntry 2 }

agCurCfgTrapHostCommString OBJECT-TYPE
    SYNTAX  DisplayString (SIZE (0..32))
    MAX-ACCESS  read-only
    STATUS  current
    DESCRIPTION
        "The SNMP community string to use with the trap host"
    ::= { agCurCfgTrapHostEntry 3 }

agNewCfgTrapHostTable OBJECT-TYPE
    SYNTAX  SEQUENCE OF AgNewCfgTrapHostEntry
    MAX-ACCESS  not-accessible
    STATUS  current
    DESCRIPTION
        "The table of trap hosts which to send SNMP traps in the
          new_configuration block."
    ::= { agTrapHost 3 }

agNewCfgTrapHostEntry OBJECT-TYPE
    SYNTAX  AgNewCfgTrapHostEntry
    MAX-ACCESS  not-accessible
    STATUS  current
    DESCRIPTION
        "A row in the trap host table in the new_configuration block."
    INDEX   { agNewCfgTrapHostIndx }
    ::= { agNewCfgTrapHostTable 1 }

AgNewCfgTrapHostEntry ::= SEQUENCE {
    agNewCfgTrapHostIndx            Integer32,
    agNewCfgTrapHostIpAddr          IpAddress,
    agNewCfgTrapHostCommString      DisplayString
    }

agNewCfgTrapHostIndx OBJECT-TYPE
    SYNTAX  Integer32
    MAX-ACCESS  read-only
    STATUS  current
    DESCRIPTION
        "The index of the row in trap host table."
    ::= { agNewCfgTrapHostEntry 1 }

agNewCfgTrapHostIpAddr OBJECT-TYPE
    SYNTAX  IpAddress
    MAX-ACCESS  read-write
    STATUS  current
    DESCRIPTION
        "The IP address of a trap host."
    ::= { agNewCfgTrapHostEntry 2 }

agNewCfgTrapHostCommString OBJECT-TYPE
    SYNTAX  DisplayString (SIZE (0..32))
    MAX-ACCESS  read-write
    STATUS  current
    DESCRIPTION
        "The SNMP community string to use with the trap host"
    ::= { agNewCfgTrapHostEntry 3 }

-- TFTP Config
agTftpServer OBJECT-TYPE
    SYNTAX  DisplayString (SIZE(0..128))
    MAX-ACCESS  read-write
    STATUS  current
    DESCRIPTION
        "The TFTP server IP address or domain name."
    ::= { agTftp 1 }

agTftpImage OBJECT-TYPE
    SYNTAX  INTEGER {
        image1(2),
        image2(3),
        boot(4)
        }
    MAX-ACCESS  read-write
    STATUS  current
    DESCRIPTION
        "Whether the image file should be loaded in image1 or image2 in flash."
    ::= { agTftp 2 }

agTftpImageFileName OBJECT-TYPE
    SYNTAX  DisplayString (SIZE(0..128))
    MAX-ACCESS  read-write
    STATUS  current
    DESCRIPTION
        "The image file name to be downloaded."
    ::= { agTftp 3 }

agTftpCfgFileName OBJECT-TYPE
    SYNTAX  DisplayString (SIZE(0..128))
    MAX-ACCESS  read-write
    STATUS  current
    DESCRIPTION
        "The configuration file name."
    ::= { agTftp 4 }

agTftpDumpFileName OBJECT-TYPE
    SYNTAX  DisplayString (SIZE(0..128))
    MAX-ACCESS  read-write
    STATUS  current
    DESCRIPTION
        "The file name for core dump."
    ::= { agTftp 5 }

agTftpAction OBJECT-TYPE
    SYNTAX  INTEGER {
        other(1),
        img-get(2),
        cfg-get(3),
        cfg-put(4),
        dump-put(5),
        bkpdump-put(6),
        img-put(7),
        tsdump-put(8),
        bogon-get(9)
        }
    MAX-ACCESS  read-write
    STATUS  current
    DESCRIPTION
        "This is an action object to perform various TFTP Get or Put functions.
         The TFTP sever is specified in agTftpServer object.
	 img-get(2)    - Download switch image from a specified image
                         file (agTftpImageFileName) on the TFTP server to
	                 the destinated storage (agTftpImage).
	 cfg-get(3)    - Download switch configuration from a specified
                         file (agTftpCfgFileName) on the TFTP server.
	 cfg-put(4)    - Upload switch configuration to a specified
                         file (agTftpCfgFileName) on the TFTP server.
	 dump-put(5)   - Download switch core dump to a specified
                         file (agTftpDumpFileName) on the TFTP server.
	 bkpdump-put(6)- Download switch backup core dump to a specified
                         file (agTftpDumpFileName) on the TFTP server.
         img-put(7)    - Upload specified switch image to a specified image
                         file (agTftpImageFileName) on the TFTP server.
         tsdump-put(8) - Download switch tech support dump to a specified
                         file (agTftpTSDumpFileName) on the TFTP server.
	 bogon-get(9)  - Download bogon config file from a specified bogon
                         file (uses agTftpImageFileName) on the TFTP server.
         other(1) is returned always when read."
    ::= { agTftp 6 }

agTftpLastActionStatus OBJECT-TYPE
    SYNTAX  DisplayString (SIZE(0..128))
    MAX-ACCESS  read-only
    STATUS  current
    DESCRIPTION
        "The recorded status of the previous TFTP activity."
    ::= { agTftp 7 }

agTftpPort OBJECT-TYPE
    SYNTAX  INTEGER {
        data(1),
        mgmt(2)
        }
    MAX-ACCESS  read-write
    STATUS  current
    DESCRIPTION
        "Specify whether the TFTP operation should nbe performed over the 
         data port or the management port."
    ::= { agTftp 8 }

agTftpUserName OBJECT-TYPE
    SYNTAX  DisplayString (SIZE(0..128))
    MAX-ACCESS  read-write
    STATUS  current
    DESCRIPTION
        "The username for FTP server or blank for TFTP server."
    ::= { agTftp 9 }

agTftpPassword OBJECT-TYPE
    SYNTAX  DisplayString (SIZE(0..128))
    MAX-ACCESS  read-write
    STATUS  current
    DESCRIPTION
        "The password for FTP server."
    ::= { agTftp 10 }

agTftpTSDumpFileName OBJECT-TYPE
    SYNTAX  DisplayString (SIZE(0..128))
    MAX-ACCESS  read-write
    STATUS  current
    DESCRIPTION
        "The file name for TS dump."
    ::= { agTftp 11 }



-- Agent Port Table

agPortTableMaxEnt OBJECT-TYPE
    SYNTAX  Integer32
    MAX-ACCESS  read-only
    STATUS  current
    DESCRIPTION
        "The maximum number of rows in the port configuration host table."
    ::= { agPortConfig 1 }

agPortCurCfgTable OBJECT-TYPE
    SYNTAX  SEQUENCE OF AgPortCurCfgTableEntry
    MAX-ACCESS  not-accessible
    STATUS  current
    DESCRIPTION
        "The table of port configuration in the current_configuration block."
    ::= { agPortConfig 2 }

agPortCurCfgTableEntry OBJECT-TYPE
    SYNTAX  AgPortCurCfgTableEntry
    MAX-ACCESS  not-accessible
    STATUS  current
    DESCRIPTION
        "A row in the port table in the current_configuration block."
    INDEX   { agPortCurCfgIndx }
    ::= { agPortCurCfgTable 1 }

AgPortCurCfgTableEntry ::= SEQUENCE {
    agPortCurCfgIndx             Integer32,
    agPortCurCfgState            INTEGER,
    agPortCurCfgVlanTag          INTEGER,
    agPortCurCfgRmon             INTEGER,
    agPortCurCfgPVID             Integer32,
    agPortCurCfgFastEthAutoNeg   INTEGER,
    agPortCurCfgFastEthSpeed     INTEGER,
    agPortCurCfgFastEthMode      INTEGER,
    agPortCurCfgFastEthFctl      INTEGER,
    agPortCurCfgGigEthAutoNeg    INTEGER,
    agPortCurCfgGigEthFctl       INTEGER,
    agPortCurCfgBwmContract      Integer32,
    agPortCurCfgDiscardNonIPs    INTEGER,
    agPortCurCfgLinkTrap         INTEGER,
    agPortCurCfgPreferred        INTEGER,
    agPortCurCfgBackup           INTEGER,
    agPortCurCfgEgressBW         DisplayString,
    agPortCurCfgNonIPBwmContract Integer32,
    agPortCurCfgGigEthSpeed      INTEGER,
    agPortCurCfgGigEthMode       INTEGER,
    agPortCurCfgPortAlias        DisplayString,
    agPortCurCfgPortName         DisplayString
    }

agPortCurCfgIndx OBJECT-TYPE
    SYNTAX  Integer32
    MAX-ACCESS  read-only
    STATUS  current
    DESCRIPTION
        "The index of the row in port configurations table."
    ::= { agPortCurCfgTableEntry 1 }

agPortCurCfgState OBJECT-TYPE
    SYNTAX  INTEGER {
        enabled(2),
        disabled(3)
	}
    MAX-ACCESS  read-only
    STATUS  current
    DESCRIPTION
        "This is the state of the port."
    ::= { agPortCurCfgTableEntry 2 }

agPortCurCfgVlanTag OBJECT-TYPE
    SYNTAX  INTEGER {
        tagged(2),
        untagged(3)
        }
    MAX-ACCESS  read-only
    STATUS  current
    DESCRIPTION
        "This is VLAN tag state of the port"
    ::= { agPortCurCfgTableEntry 3 }


agPortCurCfgRmon OBJECT-TYPE
    SYNTAX  INTEGER {
        on(2),
        off(3)
        }
    MAX-ACCESS  read-only
    STATUS  current
    DESCRIPTION
        "This object is used to turn RMON on or off on the port."
   ::= { agPortCurCfgTableEntry 5 }

agPortCurCfgPVID OBJECT-TYPE
    SYNTAX  Integer32
    MAX-ACCESS  read-only
    STATUS  current
    DESCRIPTION
        "The default VLAN ID for the port."
    ::= { agPortCurCfgTableEntry 6 }

agPortCurCfgFastEthAutoNeg OBJECT-TYPE
    SYNTAX  INTEGER {
        on(2),
        off(3)
        }
    MAX-ACCESS  read-only
    STATUS  current
    DESCRIPTION
        "This object is used to turn the autonegotiation on or off
         for fast Ethernet connection."
    ::= { agPortCurCfgTableEntry 7 }

agPortCurCfgFastEthSpeed OBJECT-TYPE
    SYNTAX  INTEGER {
        mbs10(2),
        mbs100(3),
        any(4),
        mbs1000(5)
        }
    MAX-ACCESS  read-only
    STATUS  current
    DESCRIPTION
        "Selects the port speed for fast Ethernet connection."
    ::= { agPortCurCfgTableEntry 8 }

agPortCurCfgFastEthMode OBJECT-TYPE
    SYNTAX  INTEGER {
        full-duplex(2),
        half-duplex(3),
        full-or-half-duplex(4)
        }
    MAX-ACCESS  read-only
    STATUS  current
    DESCRIPTION
        "This object is used to select port mode for fast Ethernet connection."
    ::= { agPortCurCfgTableEntry 9 }

agPortCurCfgFastEthFctl OBJECT-TYPE
    SYNTAX  INTEGER {
        transmit(2),
        receive(3),
        both(4),
        none(5)
        }
    MAX-ACCESS  read-only
    STATUS  current
    DESCRIPTION
        "Selects the port flow control for fast Ethernet connection."
    ::= { agPortCurCfgTableEntry 10 }

agPortCurCfgGigEthAutoNeg OBJECT-TYPE
    SYNTAX  INTEGER {
        on(2),
        off(3)
        }
    MAX-ACCESS  read-only
    STATUS  current
    DESCRIPTION
        "This object is used to turn the autonegotiation on or off
         for gigabit Ethernet connection."
    ::= { agPortCurCfgTableEntry 11 }

agPortCurCfgGigEthFctl OBJECT-TYPE
    SYNTAX  INTEGER {
        transmit(2),
        receive(3),
        both(4),
        none(5)
        }
    MAX-ACCESS  read-only
    STATUS  current
    DESCRIPTION
        "This object is used to select port flow control for
         gigabit Ethernet connection."
    ::= { agPortCurCfgTableEntry 12 }

agPortCurCfgPortName	OBJECT-TYPE
    SYNTAX  DisplayString (SIZE(0..63))
    MAX-ACCESS  read-only
    STATUS  current
    DESCRIPTION
        "The switch port name."
    ::= { agPortCurCfgTableEntry 13 }

agPortCurCfgBwmContract OBJECT-TYPE
    SYNTAX  Integer32
    MAX-ACCESS  read-only
    STATUS  current
    DESCRIPTION
        "The switch port Bandwidth Management contract number."
    ::= { agPortCurCfgTableEntry 14 }

agPortCurCfgDiscardNonIPs OBJECT-TYPE
    SYNTAX  INTEGER {
        enabled(2),
        disabled(3)
        }
    MAX-ACCESS  read-only
    STATUS  current
    DESCRIPTION
        "Enable or disable to discard all non-IP traffic on the switch port."
    ::= { agPortCurCfgTableEntry 15 }

agPortCurCfgLinkTrap OBJECT-TYPE
    SYNTAX  INTEGER {
	enabled(1),
	disabled(2)
    }
    MAX-ACCESS  read-only
    STATUS  current
    DESCRIPTION
        "Indicates whether linkUp/linkDown traps should be
        generated for this interface.

        By default, this object should have the value
        enabled(1) for interfaces which do not operate on
        'top' of any other interface (as defined in the
        ifStackTable), and disabled(2) otherwise."
    ::= { agPortCurCfgTableEntry 16 }

agPortCurCfgPreferred OBJECT-TYPE
    SYNTAX  INTEGER {
        copper(1),
        sfp(2)
        }
    MAX-ACCESS  read-only
    STATUS  current
    DESCRIPTION
        "This object is used to set the preferred port. Valid only on dual ports."
   ::= { agPortCurCfgTableEntry 17 }

agPortCurCfgBackup OBJECT-TYPE
    SYNTAX  INTEGER {
	none(2),
        copper(3),
        sfp(4)
        }
    MAX-ACCESS  read-only
    STATUS  current
    DESCRIPTION
        "This object is used to set the backup port. Valid only on dual ports."
   ::= { agPortCurCfgTableEntry 18 }

agPortCurCfgEgressBW OBJECT-TYPE
    SYNTAX DisplayString (SIZE(0..5))
    MAX-ACCESS read-only
    STATUS current
    DESCRIPTION
        "The configured egress bandwidth limit for this port. This is the
         maximum egress bandwidth available to this port if BWM is on."
    ::= { agPortCurCfgTableEntry 19 }

agPortCurCfgNonIPBwmContract OBJECT-TYPE
    SYNTAX  Integer32
    MAX-ACCESS  read-only
    STATUS  current
    DESCRIPTION
        "The BWM contract for non-IP traffic."
    ::= { agPortCurCfgTableEntry 20 }

agPortCurCfgGigEthSpeed OBJECT-TYPE
    SYNTAX  INTEGER {
        mbs10(2),
        mbs100(3),
        any(4),
        mbs1000(5)
        }
    MAX-ACCESS  read-only
    STATUS  current
    DESCRIPTION
        "Selects the port speed for Gigabit Ethernet connection."
    ::= { agPortCurCfgTableEntry 21 }

agPortCurCfgGigEthMode OBJECT-TYPE
    SYNTAX  INTEGER {
        full-duplex(2),
        half-duplex(3),
        full-or-half-duplex(4)
        }
    MAX-ACCESS  read-only
    STATUS  current
    DESCRIPTION
        "This object is used to select port mode for Gigabit Ethernet connection."
    ::= { agPortCurCfgTableEntry 22 }


agPortCurCfgPortAlias    OBJECT-TYPE
    SYNTAX  DisplayString (SIZE(0..15))
    MAX-ACCESS  read-only
    STATUS  current
    DESCRIPTION
        "The switch port alias."
    ::= { agPortCurCfgTableEntry 24 }



agPortNewCfgTable OBJECT-TYPE
    SYNTAX  SEQUENCE OF AgPortNewCfgTableEntry
    MAX-ACCESS  not-accessible
    STATUS  current
    DESCRIPTION
        "The table of port configuration in the new_configuration block."
    ::= { agPortConfig 3 }

agPortNewCfgTableEntry OBJECT-TYPE
    SYNTAX  AgPortNewCfgTableEntry
    MAX-ACCESS  not-accessible
    STATUS  current
    DESCRIPTION
        "A row in the port configuration table in the new_configuration block."
    INDEX   { agPortNewCfgIndx }
    ::= { agPortNewCfgTable 1 }

AgPortNewCfgTableEntry ::= SEQUENCE {
    agPortNewCfgIndx             Integer32,
    agPortNewCfgState            INTEGER,
    agPortNewCfgVlanTag          INTEGER,
    agPortNewCfgRmon             INTEGER,
    agPortNewCfgPVID             Integer32,
    agPortNewCfgFastEthAutoNeg   INTEGER,
    agPortNewCfgFastEthSpeed     INTEGER,
    agPortNewCfgFastEthMode      INTEGER,
    agPortNewCfgFastEthFctl      INTEGER,
    agPortNewCfgGigEthAutoNeg    INTEGER,
    agPortNewCfgGigEthFctl       INTEGER,
    agPortNewCfgPortName         DisplayString,
    agPortNewCfgBwmContract      Integer32,
    agPortNewCfgDiscardNonIPs    INTEGER,
    agPortNewCfgLinkTrap         INTEGER,
    agPortNewCfgPreferred        INTEGER,
    agPortNewCfgBackup           INTEGER,
    agPortNewCfgEgressBW         DisplayString,
    agPortNewCfgNonIPBwmContract Integer32,
    agPortNewCfgGigEthSpeed      INTEGER,
    agPortNewCfgGigEthMode       INTEGER,
    agPortNewCfgPortAlias        DisplayString,
    agPortNewCfgPortName         DisplayString
    }

agPortNewCfgIndx OBJECT-TYPE
    SYNTAX  Integer32
    MAX-ACCESS  read-only
    STATUS  current
    DESCRIPTION
        "The index of the row in port configurations table."
    ::= { agPortNewCfgTableEntry 1 }

agPortNewCfgState OBJECT-TYPE
    SYNTAX  INTEGER {
        enabled(2),
        disabled(3)
        }
    MAX-ACCESS  read-write
    STATUS  current
    DESCRIPTION
        "This is the state of the port."
    ::= { agPortNewCfgTableEntry 2 }

agPortNewCfgVlanTag OBJECT-TYPE
    SYNTAX  INTEGER {
        tagged(2),
        untagged(3)
        }
    MAX-ACCESS  read-write
    STATUS  current
    DESCRIPTION
        "This is VLAN tag state of the port"
    ::= { agPortNewCfgTableEntry 3 }


agPortNewCfgRmon OBJECT-TYPE
    SYNTAX  INTEGER {
        on(2),
        off(3)
        }
    MAX-ACCESS  read-write
    STATUS  current
    DESCRIPTION
        "This object is used to turn RMON on or off on the port."
    ::= { agPortNewCfgTableEntry 5 }

agPortNewCfgPVID OBJECT-TYPE
    SYNTAX  Integer32
    MAX-ACCESS  read-write
    STATUS  current
    DESCRIPTION
        "The default VLAN ID for the port."
    ::= { agPortNewCfgTableEntry 6 }

agPortNewCfgFastEthAutoNeg OBJECT-TYPE
    SYNTAX  INTEGER {
        on(2),
        off(3)
        }
    MAX-ACCESS  read-write
    STATUS  current
    DESCRIPTION
        "This object is used to turn the autonegotiation on or off
         for fast Ethernet connection."
    ::= { agPortNewCfgTableEntry 7 }

agPortNewCfgFastEthSpeed OBJECT-TYPE
    SYNTAX  INTEGER {
        mbs10(2),
        mbs100(3),
        any(4),
        mbs1000(5)
        }
    MAX-ACCESS  read-write
    STATUS  current
    DESCRIPTION
        "Selects the port speed for fast Ethernet connection."
    ::= { agPortNewCfgTableEntry 8 }
 
agPortNewCfgFastEthMode OBJECT-TYPE
    SYNTAX  INTEGER {
        full-duplex(2),
        half-duplex(3),
        full-or-half-duplex(4)
        }
    MAX-ACCESS  read-write
    STATUS  current
    DESCRIPTION
        "This object is used to select port mode for fast Ethernet connection."
    ::= { agPortNewCfgTableEntry 9 }

agPortNewCfgFastEthFctl OBJECT-TYPE
    SYNTAX  INTEGER {
        transmit(2),
        receive(3),
        both(4),
        none(5)
        }
    MAX-ACCESS  read-write
    STATUS  current
    DESCRIPTION
        "Selects the port flow control for fast Ethernet connection."
    ::= { agPortNewCfgTableEntry 10 }

agPortNewCfgGigEthAutoNeg OBJECT-TYPE
    SYNTAX  INTEGER {
        on(2),
        off(3)
        }
    MAX-ACCESS  read-write
    STATUS  current
    DESCRIPTION
        "This object is used to turn the autonegotiation on or off
         for gigabit Ethernet connection."
    ::= { agPortNewCfgTableEntry 11 }

agPortNewCfgGigEthFctl OBJECT-TYPE
    SYNTAX  INTEGER {
        transmit(2),
        receive(3),
        both(4),
        none(5)
       }
    MAX-ACCESS  read-write
    STATUS  current
    DESCRIPTION
        "This object is used to select port flow control for
         gigabit Ethernet connection."
    ::= { agPortNewCfgTableEntry 12 }

agPortNewCfgPortName	OBJECT-TYPE
    SYNTAX  DisplayString (SIZE(0..63))
    MAX-ACCESS  read-write
    STATUS  current
    DESCRIPTION
        "The switch port name."
    ::= { agPortNewCfgTableEntry 13 }

agPortNewCfgBwmContract OBJECT-TYPE
    SYNTAX  Integer32
    MAX-ACCESS  read-write
    STATUS  current
    DESCRIPTION
        "The switch port Bandwidth Management contract number."
    ::= { agPortNewCfgTableEntry 14 }

agPortNewCfgDiscardNonIPs OBJECT-TYPE
    SYNTAX  INTEGER {
        enabled(2),
        disabled(3)
        }
    MAX-ACCESS  read-write
    STATUS  current
    DESCRIPTION
        "Enable or disable to discard all non-IP traffic on the switch port."
    ::= { agPortNewCfgTableEntry 15 }

agPortNewCfgLinkTrap OBJECT-TYPE
    SYNTAX  INTEGER {
	enabled(1),
	disabled(2)
    }
    MAX-ACCESS  read-write
    STATUS  current 
    DESCRIPTION
        "Indicates whether linkUp/linkDown traps should be
        generated for this interface.

        By default, this object should have the value
        enabled(1) for interfaces which do not operate on
        'top' of any other interface (as defined in the
        ifStackTable), and disabled(2) otherwise."
    ::= { agPortNewCfgTableEntry 16 }

agPortNewCfgPreferred OBJECT-TYPE
    SYNTAX  INTEGER {
        copper(1),
        sfp(2)
    }
    MAX-ACCESS  read-write
    STATUS  current
    DESCRIPTION
        "This object is used to set the preferred port. Valid only on dual ports."
   ::= { agPortNewCfgTableEntry 17 }

agPortNewCfgBackup OBJECT-TYPE
    SYNTAX  INTEGER {
	none(1),
        copper(2),
        sfp(3)
    }
    MAX-ACCESS  read-write
    STATUS  current
    DESCRIPTION
        "This object is used to set the backup port. Valid only on dual ports."
   ::= { agPortNewCfgTableEntry 18 }

agPortNewCfgEgressBW OBJECT-TYPE
    SYNTAX DisplayString (SIZE(0..5))
    MAX-ACCESS read-write
    STATUS current
    DESCRIPTION
        "The configured egress bandwidth limit for this port. This is the
         maximum egress bandwidth available to this port if BWM is on."
    ::= { agPortNewCfgTableEntry 19 }

agPortNewCfgNonIPBwmContract OBJECT-TYPE
    SYNTAX  Integer32
    MAX-ACCESS  read-write
    STATUS  current
    DESCRIPTION
        "The BWM contract for non-IP traffic"
    ::= { agPortNewCfgTableEntry 20 }

agPortNewCfgGigEthSpeed OBJECT-TYPE
    SYNTAX  INTEGER {
        mbs10(2),
        mbs100(3),
        any(4),
        mbs1000(5)
        }
    MAX-ACCESS  read-write
    STATUS  current
    DESCRIPTION
        "Selects the port speed for Gigabit Ethernet connection."
    ::= { agPortNewCfgTableEntry 21 }
 
agPortNewCfgGigEthMode OBJECT-TYPE
    SYNTAX  INTEGER {
        full-duplex(2),
        half-duplex(3),
        full-or-half-duplex(4)
        }
    MAX-ACCESS  read-write
    STATUS  current
    DESCRIPTION
        "This object is used to select port mode for Gigabit Ethernet connection."
    ::= { agPortNewCfgTableEntry 22 }


agPortNewCfgPortAlias    OBJECT-TYPE
    SYNTAX  DisplayString (SIZE(0..15))
    MAX-ACCESS  read-write
    STATUS  current
    DESCRIPTION
        "The switch port alias."
    ::= { agPortNewCfgTableEntry 24 }



-- Agent Fast Forwarding Port Table


-- RADIUS Configuration 
 
radCurCfgPrimaryIpAddr OBJECT-TYPE
    SYNTAX  IpAddress
    MAX-ACCESS  read-only
    STATUS  current
    DESCRIPTION
        "The IP address of the Primary RADIUS server."
    ::= { agRadiusConfig 1 }

radNewCfgPrimaryIpAddr OBJECT-TYPE
    SYNTAX  IpAddress
    MAX-ACCESS  read-write
    STATUS  current
    DESCRIPTION
        "The IP address of the Primary RADIUS server."
    ::= { agRadiusConfig 2 }

radCurCfgSecondaryIpAddr OBJECT-TYPE
    SYNTAX  IpAddress
    MAX-ACCESS  read-only
    STATUS  current
    DESCRIPTION
        "The IP address of the Secondary RADIUS server."
    ::= { agRadiusConfig 3 }

radNewCfgSecondaryIpAddr OBJECT-TYPE
    SYNTAX  IpAddress
    MAX-ACCESS  read-write
    STATUS  current
    DESCRIPTION
        "The IP address of the Secondary RADIUS server."
    ::= { agRadiusConfig 4 }

radCurCfgPort OBJECT-TYPE
    SYNTAX  INTEGER  (1500..3000)
    MAX-ACCESS  read-only
    STATUS  current
    DESCRIPTION
        "Specify the RADIUS port number."
    ::= { agRadiusConfig 5 }

radNewCfgPort OBJECT-TYPE
    SYNTAX  INTEGER  (1500..3000)
    MAX-ACCESS  read-write
    STATUS  current
    DESCRIPTION
        "Specify the RADIUS port number."
    ::= { agRadiusConfig 6 }

radCurCfgTimeout OBJECT-TYPE
    SYNTAX  INTEGER  (1..10)
    MAX-ACCESS  read-only
    STATUS  current
    DESCRIPTION
        "The maximum number of seconds before resending authentication
         to RADIUS server."
    ::= { agRadiusConfig 7 }

radNewCfgTimeout OBJECT-TYPE
    SYNTAX  INTEGER  (1..10)
    MAX-ACCESS  read-write
    STATUS  current
    DESCRIPTION
        "The maximum number of seconds before resending authentication
         to RADIUS server."
    ::= { agRadiusConfig 8 }

radCurCfgRetries OBJECT-TYPE
    SYNTAX  INTEGER  (1..3)
    MAX-ACCESS  read-only
    STATUS  current
    DESCRIPTION
        "Number of retries to the RADIUS server."
    ::= { agRadiusConfig 9 }

radNewCfgRetries OBJECT-TYPE
    SYNTAX  INTEGER  (1..3)
    MAX-ACCESS  read-write
    STATUS  current
    DESCRIPTION
        "Number of retries to the RADIUS server."
    ::= { agRadiusConfig 10 }

radCurCfgState OBJECT-TYPE
    SYNTAX  INTEGER {
        enabled(2),
        disabled(3)
        }
    MAX-ACCESS  read-only
    STATUS  current
    DESCRIPTION
        "Enable or disbale RADIUS authentication."
    ::= { agRadiusConfig 11 }

radNewCfgState OBJECT-TYPE
    SYNTAX  INTEGER {
        enabled(2),
        disabled(3)
        }
    MAX-ACCESS  read-write
    STATUS  current
    DESCRIPTION
        "Enable or disable RADIUS authentication."
    ::= { agRadiusConfig 12 }

radCurCfgAuthenString OBJECT-TYPE
    SYNTAX  DisplayString (SIZE(0..32))
    MAX-ACCESS  read-only
    STATUS  current
    DESCRIPTION
        "The RADIUS authentication string."
    ::= { agRadiusConfig 13 }

radNewCfgAuthenString OBJECT-TYPE
    SYNTAX  DisplayString (SIZE(0..32))
    MAX-ACCESS  read-write
    STATUS  current
    DESCRIPTION
        "The RADIUS authentication string."
    ::= { agRadiusConfig 14 }

radCurCfgTelnet OBJECT-TYPE
    SYNTAX  INTEGER {
        enabled(1),
        disabled(2)
        }
    MAX-ACCESS  read-only
    STATUS  current
    DESCRIPTION
        "Enable or disbale RADIUS backdoor for telnet."
    ::= { agRadiusConfig 15 }

radNewCfgTelnet OBJECT-TYPE
    SYNTAX  INTEGER {
        enabled(1),
        disabled(2)
        }
    MAX-ACCESS  read-write
    STATUS  current
    DESCRIPTION
        "Enable or disable RADIUS backdoor for telnet."
    ::= { agRadiusConfig 16 }

radCurCfgAuthenSecondString OBJECT-TYPE
    SYNTAX  DisplayString (SIZE(0..32))
    MAX-ACCESS  read-only
    STATUS  current
    DESCRIPTION
        "The second RADIUS authentication string."
    ::= { agRadiusConfig 17 }

radNewCfgAuthenSecondString OBJECT-TYPE
    SYNTAX  DisplayString (SIZE(0..32))
    MAX-ACCESS  read-write
    STATUS  current
    DESCRIPTION
        "The second RADIUS authentication string."
    ::= { agRadiusConfig 18 }


-- NTP Configuration 
agCurCfgNTPServer OBJECT-TYPE
    SYNTAX  IpAddress
    MAX-ACCESS  read-only
    STATUS  current
    DESCRIPTION
        "The NTP Server Address."
    ::= { agNTP 1 }

agNewCfgNTPServer OBJECT-TYPE
    SYNTAX  IpAddress
    MAX-ACCESS  read-write
    STATUS  current
    DESCRIPTION
        "The NTP Server Address."
    ::= { agNTP 2 }

agCurCfgNTPResyncInterval OBJECT-TYPE
    SYNTAX  INTEGER (1..44640)
    MAX-ACCESS  read-only
    STATUS  current
    DESCRIPTION
        "The NTP Server resync interval in minutes."
    ::= { agNTP 3 }

agNewCfgNTPResyncInterval OBJECT-TYPE
    SYNTAX  INTEGER (1..44640)
    MAX-ACCESS  read-write
    STATUS  current
    DESCRIPTION
        "The NTP Server resync interval in minutes."
    ::= { agNTP 4 }

agCurCfgNTPTzoneHHMM OBJECT-TYPE
    SYNTAX  DisplayString (SIZE(0..6))
    MAX-ACCESS  read-only
    STATUS  current
    DESCRIPTION
        "The NTP Server timezone offset from GMT formatted as (+/-)HH:MM."
    ::= { agNTP 5 }

agNewCfgNTPTzoneHHMM OBJECT-TYPE
    SYNTAX  DisplayString (SIZE(0..6))
    MAX-ACCESS  read-write
    STATUS  current
    DESCRIPTION
        "The NTP Server timezone offset from GMT formatted as (+/-)HH:MM.
         The valid range is from -12:59 to +12:59."
    ::= { agNTP 6 }

agCurCfgNTPDlight OBJECT-TYPE
    SYNTAX  INTEGER {
        enabled(1),
        disabled(2)
        }
    MAX-ACCESS  read-only
    STATUS  current
    DESCRIPTION
        "Enable/disable daylight savings time."
    ::= { agNTP 7 }

agNewCfgNTPDlight OBJECT-TYPE
    SYNTAX  INTEGER {
        enabled(1),
        disabled(2)
        }
    MAX-ACCESS  read-write
    STATUS  current
    DESCRIPTION
        "Enable/disable daylight savings time."
    ::= { agNTP 8 }

agCurCfgNTPService OBJECT-TYPE
    SYNTAX  INTEGER {
        enabled(1),
        disabled(2)
        }
    MAX-ACCESS  read-only
    STATUS  current
    DESCRIPTION
        "Enable/disable NTP Service."
    ::= { agNTP 9 }

agNewCfgNTPService OBJECT-TYPE
    SYNTAX  INTEGER {
        enabled(1),
        disabled(2)
        }
    MAX-ACCESS  read-write
    STATUS  current
    DESCRIPTION
        "Enable/disable NTP Service."
    ::= { agNTP 10 }

agCurCfgNTPSecServer OBJECT-TYPE
    SYNTAX  IpAddress
    MAX-ACCESS  read-only
    STATUS  current
    DESCRIPTION
        "The Secondary NTP Server Address."
    ::= { agNTP 11 }

agNewCfgNTPSecServer OBJECT-TYPE
    SYNTAX  IpAddress
    MAX-ACCESS  read-write
    STATUS  current
    DESCRIPTION
        "The Secondary NTP Server Address."
    ::= { agNTP 12 }

-- APPLY Configuration
agApplyPending OBJECT-TYPE
    SYNTAX  INTEGER {
        applyNeeded(2),
        noApplyNeeded(3)
        }
    MAX-ACCESS  read-only
    STATUS  current
    DESCRIPTION
        "This object, when read, gives the user information
         whether an apply action is needed and that the configuration
         has been chaged by the user actions. The user then can
         apply the changes by setting proper value to the object
         agApplyConfiguration described above."
    ::= { agApply 1 }

agApplyConfig OBJECT-TYPE
    SYNTAX  INTEGER {
        apply(1), 
        idle(2),
        inprogress(3),
        complete(4),
        failed(5)
        }
    MAX-ACCESS  read-write
    STATUS  current
    DESCRIPTION
         "When this object is read the current state is returned.
          idle(2) indicates that there is no apply in progess.
          complete(4) indicates that the last apply operation is completed.
          Setting the value to apply(1), will write all the changes made
          since the last apply to the current configuration block.
	  If the apply is successful this variable will return the state
          'complete' else it will return 'failed'. In case of failure,
          to read the reason for failure use the agApplyTable.
          Once the operation is completed or the agApplyTable is read in case
          of failure, the apply buffer needs to be freed and the agApplyState 
          should be set back to 'idle' state so others can issue the apply 
          command via SNMP."
    ::= { agApply 2 }

agApplyTableSize OBJECT-TYPE
    SYNTAX  Integer32
    MAX-ACCESS  read-only
    STATUS  current
    DESCRIPTION
        "The number of strings in the apply table."
    ::= { agApply 4 }

agApplyTable OBJECT-TYPE
    SYNTAX  SEQUENCE OF AgApplyTableEntry
    MAX-ACCESS  not-accessible
    STATUS  current
    DESCRIPTION
        "The table of URL path for URL load balancing in the current_config."
    ::= { agApply 5 }

agApplyTableEntry OBJECT-TYPE
    SYNTAX  AgApplyTableEntry
    MAX-ACCESS  not-accessible
    STATUS  current
    DESCRIPTION
        "Information about an URL path for URL load balancing."
    INDEX   { agApplyIndex }
    ::= { agApplyTable 1 }

AgApplyTableEntry ::= SEQUENCE {
    agApplyIndex      Integer32,
    agApplyString     OCTET STRING
    }

agApplyIndex OBJECT-TYPE
    SYNTAX  Integer32
    MAX-ACCESS  read-only
    STATUS  current
    DESCRIPTION
        "The table index."
    ::= { agApplyTableEntry 1 }

agApplyString OBJECT-TYPE
    SYNTAX  OCTET STRING
    MAX-ACCESS  read-only
    STATUS  current
    DESCRIPTION
        "A string in the apply table."
    ::= { agApplyTableEntry 2 }

-- Mgmt Port Config

agMgmtCurCfgIpAddr OBJECT-TYPE
    SYNTAX  IpAddress
    MAX-ACCESS  read-only
    STATUS  current
    DESCRIPTION
        "The IP address of the management port."
    ::= { agMgmt 1 }

agMgmtNewCfgIpAddr OBJECT-TYPE
    SYNTAX  IpAddress
    MAX-ACCESS  read-write
    STATUS  current
    DESCRIPTION
        "The IP address of the management port."
    ::= { agMgmt 2 }

agMgmtCurCfgMask OBJECT-TYPE
    SYNTAX  IpAddress
    MAX-ACCESS  read-only
    STATUS  current
    DESCRIPTION
        "The subnet mask of the management port."
    ::= { agMgmt 3 }

agMgmtNewCfgMask OBJECT-TYPE
    SYNTAX  IpAddress
    MAX-ACCESS  read-write
    STATUS  current
    DESCRIPTION
        "The subnet mask of the management port."
    ::= { agMgmt 4 }


agMgmtCurCfgGateway OBJECT-TYPE
    SYNTAX  IpAddress
    MAX-ACCESS  read-only
    STATUS  current
    DESCRIPTION
        "The default gateway for the management port."
    ::= { agMgmt 7 }

agMgmtNewCfgGateway OBJECT-TYPE
    SYNTAX  IpAddress
    MAX-ACCESS  read-write
    STATUS  current
    DESCRIPTION
        "The default gateway for the management port."
    ::= { agMgmt 8 }

agMgmtCurCfgState OBJECT-TYPE
    SYNTAX  INTEGER {
        enabled(1),
        disabled(2)
        }
    MAX-ACCESS  read-only
    STATUS  current
    DESCRIPTION
        "Enable/disable management port."
   ::= { agMgmt 9 } 

agMgmtNewCfgState OBJECT-TYPE
    SYNTAX  INTEGER {
        enabled(1),
        disabled(2)
        }
    MAX-ACCESS  read-write
    STATUS  current
    DESCRIPTION
        "Enable/disable management port."
   ::= { agMgmt 10 } 

agMgmtCurCfgNtp OBJECT-TYPE
    SYNTAX  INTEGER {
        data(1),
        mgmt(2)
        }
    MAX-ACCESS  read-only
    STATUS  current
    DESCRIPTION
        "Specifies NTP access is over management port or data port."
   ::= { agMgmt 11 } 

agMgmtNewCfgNtp OBJECT-TYPE
    SYNTAX  INTEGER {
        data(1),
        mgmt(2)
        }
    MAX-ACCESS  read-write
    STATUS  current
    DESCRIPTION
        "Specifies NTP access is over management port or data port."
   ::= { agMgmt 12 } 

agMgmtCurCfgRadius OBJECT-TYPE
    SYNTAX  INTEGER {
        data(1),
        mgmt(2)
        }
    MAX-ACCESS  read-only
    STATUS  current
    DESCRIPTION
        "Specifies RADIUS server access is over management port or data port."
   ::= { agMgmt 13 } 

agMgmtNewCfgRadius OBJECT-TYPE
    SYNTAX  INTEGER {
        data(1),
        mgmt(2)
        }
    MAX-ACCESS  read-write
    STATUS  current
    DESCRIPTION
        "Specifies RADIUS server access is over management port or data port."
   ::= { agMgmt 14 } 

agMgmtCurCfgSmtp OBJECT-TYPE
    SYNTAX  INTEGER {
        data(1),
        mgmt(2)
        }
    MAX-ACCESS  read-only
    STATUS  current
    DESCRIPTION
        "Specifies SMTP access is over management port or data port."
   ::= { agMgmt 15 } 

agMgmtNewCfgSmtp OBJECT-TYPE
    SYNTAX  INTEGER {
        data(1),
        mgmt(2)
        }
    MAX-ACCESS  read-write
    STATUS  current
    DESCRIPTION
        "Specifies SMTP access is over management port or data port."
   ::= { agMgmt 16 } 

agMgmtCurCfgSnmp OBJECT-TYPE
    SYNTAX  INTEGER {
        data(1),
        mgmt(2)
        }
    MAX-ACCESS  read-only
    STATUS  current
    DESCRIPTION
        "Specifies SNMP trap host access is over management port or data port."
   ::= { agMgmt 17 } 

agMgmtNewCfgSnmp OBJECT-TYPE
    SYNTAX  INTEGER {
        data(1),
        mgmt(2)
        }
    MAX-ACCESS  read-write
    STATUS  current
    DESCRIPTION
        "Specifies SNMP trap host access is over management port or data port."
   ::= { agMgmt 18 } 

agMgmtCurCfgSyslog OBJECT-TYPE
    SYNTAX  INTEGER {
        data(1),
        mgmt(2)
        }
    MAX-ACCESS  read-only
    STATUS  current
    DESCRIPTION
        "Specifies syslog host access is over management port or data port."
   ::= { agMgmt 19 } 

agMgmtNewCfgSyslog OBJECT-TYPE
    SYNTAX  INTEGER {
        data(1),
        mgmt(2)
        }
    MAX-ACCESS  read-write
    STATUS  current
    DESCRIPTION
        "Specifies syslog host access is over management port or data port."
   ::= { agMgmt 20 } 

agMgmtCurCfgTftp OBJECT-TYPE
    SYNTAX  INTEGER {
        data(1),
        mgmt(2)
        }
    MAX-ACCESS  read-only
    STATUS  current
    DESCRIPTION
        "Specifies TFTP access is over management port or data port."
   ::= { agMgmt 21 } 

agMgmtNewCfgTftp OBJECT-TYPE
    SYNTAX  INTEGER {
        data(1),
        mgmt(2)
        }
    MAX-ACCESS  read-write
    STATUS  current
    DESCRIPTION
        "Specifies TFTP access is over management port or data port."
   ::= { agMgmt 22 } 

agMgmtCurCfgDns OBJECT-TYPE
    SYNTAX  INTEGER {
        data(1),
        mgmt(2)
        }
    MAX-ACCESS  read-only
    STATUS  current
    DESCRIPTION
        "Specifies DNS access is over management port or data port."
   ::= { agMgmt 24 } 

agMgmtNewCfgDns OBJECT-TYPE
    SYNTAX  INTEGER {
        data(1),
        mgmt(2)
        }
    MAX-ACCESS  read-write
    STATUS  current
    DESCRIPTION
        "Specifies DNS access is over management port or data port."
   ::= { agMgmt 25 } 

agMgmtCurCfgTacacs OBJECT-TYPE
    SYNTAX  INTEGER {
        data(1),
        mgmt(2)
        }
    MAX-ACCESS  read-only
    STATUS  current
    DESCRIPTION
        "Specifies TACACS+ server access is over management port or data port."
   ::= { agMgmt 26 }

agMgmtNewCfgTacacs OBJECT-TYPE
    SYNTAX  INTEGER {
        data(1),
        mgmt(2)
        }
    MAX-ACCESS  read-write
    STATUS  current
    DESCRIPTION
        "Specifies TACACS+ server access is over management port or data port."
   ::= { agMgmt 27 }

agMgmtCurCfgIntr OBJECT-TYPE
    SYNTAX  INTEGER (0..60)
    MAX-ACCESS  read-only
    STATUS  current
    DESCRIPTION
        "The management port gateway health check interval (in seconds)."
   ::= { agMgmt 28 }

agMgmtNewCfgIntr OBJECT-TYPE
    SYNTAX  INTEGER (0..60)
    MAX-ACCESS  read-write
    STATUS  current
    DESCRIPTION
        "The management port gateway health check interval (in seconds)."
   ::= { agMgmt 29 }

agMgmtCurCfgRetry OBJECT-TYPE
    SYNTAX  INTEGER (1..120)
    MAX-ACCESS  read-only
    STATUS  current
    DESCRIPTION
        "The management port gateway retries before out of service."
   ::= { agMgmt 30 }

agMgmtNewCfgRetry OBJECT-TYPE
    SYNTAX  INTEGER (1..120)
    MAX-ACCESS  read-write
    STATUS  current
    DESCRIPTION
        "The management port gateway retries before out of service."
   ::= { agMgmt 31 }

agMgmtCurCfgSonmp OBJECT-TYPE
    SYNTAX  INTEGER {
        data(1),
        mgmt(2)
        }
    MAX-ACCESS  read-only
    STATUS  current
    DESCRIPTION
        "Specifies whether to use management port IP address or interface IP 
         address in the SONMP Hello packets."
   ::= { agMgmt 32 }

agMgmtNewCfgSonmp OBJECT-TYPE
    SYNTAX  INTEGER {
        data(1),
        mgmt(2)
        }
    MAX-ACCESS  read-write
    STATUS  current
    DESCRIPTION
        "Specifies whether to use management port IP address or interface IP 
         address in the SONMP Hello packets."
   ::= { agMgmt 33 }

agMgmtCurCfgWlm OBJECT-TYPE
    SYNTAX  INTEGER {
        data(1),
        mgmt(2)
        }
    MAX-ACCESS  read-only
    STATUS  current
    DESCRIPTION
        "Specifies WLM SASP is over management port or data port."
   ::= { agMgmt 34 }

agMgmtNewCfgWlm OBJECT-TYPE
    SYNTAX  INTEGER {
        data(1),
        mgmt(2)
        }
    MAX-ACCESS  read-write
    STATUS  current
    DESCRIPTION
        "Specifies WLM SASP is over management port or data port."
   ::= { agMgmt 35 }

agMgmtCurCfgReport OBJECT-TYPE
    SYNTAX  INTEGER {
        data(1),
        mgmt(2)
        }
    MAX-ACCESS  read-only
    STATUS  current
    DESCRIPTION
        "Specifies reporting server is over management port or data port."
   ::= { agMgmt 36 }

agMgmtNewCfgReport OBJECT-TYPE
    SYNTAX  INTEGER {
        data(1),
        mgmt(2)
        }
    MAX-ACCESS  read-write
    STATUS  current
    DESCRIPTION
        "Specifies reporting server is over management port or data port."
   ::= { agMgmt 37 }

agMgmtPort   OBJECT IDENTIFIER ::= { agMgmt 23 }

agMgmtPortCurCfgSpeed OBJECT-TYPE
    SYNTAX  INTEGER {
        mbs10(1),
        mbs100(2),
        any(3)
        }
    MAX-ACCESS  read-only
    STATUS  current
    DESCRIPTION
        "Set Management port link speed."
   ::= { agMgmtPort 1 } 

agMgmtPortNewCfgSpeed OBJECT-TYPE
    SYNTAX  INTEGER {
        mbs10(1),
        mbs100(2),
        any(3)
        }
    MAX-ACCESS  read-write
    STATUS  current
    DESCRIPTION
        "Set Management port link speed."
   ::= { agMgmtPort 2 } 

agMgmtPortCurCfgMode OBJECT-TYPE
    SYNTAX  INTEGER {
        full(1),
        half(2),
        any(3)
        }
    MAX-ACCESS  read-only
    STATUS  current
    DESCRIPTION
        "Set Management port full or half duplex mode."
   ::= { agMgmtPort 3 } 

agMgmtPortNewCfgMode OBJECT-TYPE
    SYNTAX  INTEGER {
        full(1),
        half(2),
        any(3)
        }
    MAX-ACCESS  read-write
    STATUS  current
    DESCRIPTION
        "Set Management port full or half duplex mode."
   ::= { agMgmtPort 4 } 

agMgmtPortCurCfgAuto OBJECT-TYPE
    SYNTAX  INTEGER {
        on(1),
        off(2)
        }
    MAX-ACCESS  read-only
    STATUS  current
    DESCRIPTION
        "Set Management port autonegotiation."
   ::= { agMgmtPort 5 } 

agMgmtPortNewCfgAuto OBJECT-TYPE
    SYNTAX  INTEGER {
        on(1),
        off(2)
        }
    MAX-ACCESS  read-write
    STATUS  current
    DESCRIPTION
        "Set Management port autonegotiation."
   ::= { agMgmtPort 6 } 

-- SSL Processor Config 

agSslprocCurCfgIpAddr OBJECT-TYPE
    SYNTAX  IpAddress
    MAX-ACCESS  read-only
    STATUS  current
    DESCRIPTION
        "The SSL cluster management IP."
    ::= { agSslproc 1 }

agSslprocNewCfgIpAddr OBJECT-TYPE
    SYNTAX  IpAddress
    MAX-ACCESS  read-write
    STATUS  current
    DESCRIPTION
        "The SSL cluster management IP."
    ::= { agSslproc 2 }

agSslprocCurCfgPort OBJECT-TYPE
    SYNTAX  INTEGER (1..65535)
    MAX-ACCESS  read-only
    STATUS  current
    DESCRIPTION
        "The SSL cluster management port."
    ::= { agSslproc 3 }

agSslprocNewCfgPort OBJECT-TYPE
    SYNTAX  INTEGER (1..65535)
    MAX-ACCESS  read-write
    STATUS  current
    DESCRIPTION
        "The SSL cluster management port."
    ::= { agSslproc 4 }

agSslprocCurCfgRts OBJECT-TYPE
    SYNTAX  INTEGER {
        enabled(1),
        disabled(2)
        }
    MAX-ACCESS  read-only
    STATUS  current
    DESCRIPTION
        "Enable/disable RTS processing."
   ::= { agSslproc 5 } 

agSslprocNewCfgRts OBJECT-TYPE
    SYNTAX  INTEGER {
        enabled(1),
        disabled(2)
        }
    MAX-ACCESS  read-write
    STATUS  current
    DESCRIPTION
        "Enabled/disable RTS processing."
   ::= { agSslproc 6 } 

agSslprocCurCfgFilt OBJECT-TYPE
    SYNTAX  INTEGER {
        enabled(1),
        disabled(2)
        }
    MAX-ACCESS  read-only
    STATUS  current
    DESCRIPTION
        "Enable/disable filtering."
   ::= { agSslproc 7 }

agSslprocNewCfgFilt OBJECT-TYPE
    SYNTAX  INTEGER {
        enabled(1),
        disabled(2)
        }
    MAX-ACCESS  read-write
    STATUS  current
    DESCRIPTION
        "Enabled/disable filtering."
   ::= { agSslproc 8 }

agCurCfgSonmpSrcIf OBJECT-TYPE
    SYNTAX  Integer32
    MAX-ACCESS  read-only
    STATUS  current
    DESCRIPTION
        "The IP address used in the SONMP hello packets. The switch should be 
         reachable via SNMP at this IP address."
    ::= { agSonmp 1 }

agNewCfgSonmpSrcIf OBJECT-TYPE
    SYNTAX  Integer32
    MAX-ACCESS  read-write
    STATUS  current
    DESCRIPTION
        "The IP address used in the SONMP hello packets. The switch should be 
         reachable via SNMP at this IP address."
    ::= { agSonmp 2}

-- TACACS+ Configuration

tacCurCfgPrimaryIpAddr OBJECT-TYPE
    SYNTAX  IpAddress
    MAX-ACCESS  read-only
    STATUS  current
    DESCRIPTION
        "The IP address of the Primary TACACS+ server."
    ::= { agTacacsConfig 1 }

tacNewCfgPrimaryIpAddr OBJECT-TYPE
    SYNTAX  IpAddress
    MAX-ACCESS  read-write
    STATUS  current
    DESCRIPTION
        "The IP address of the Primary TACACS+ server."
    ::= { agTacacsConfig 2 }

tacCurCfgSecondaryIpAddr OBJECT-TYPE
    SYNTAX  IpAddress
    MAX-ACCESS  read-only
    STATUS  current
    DESCRIPTION
        "The IP address of the Secondary TACSACS server."
    ::= { agTacacsConfig 3 }
tacNewCfgSecondaryIpAddr OBJECT-TYPE
    SYNTAX  IpAddress
    MAX-ACCESS  read-write
    STATUS  current
    DESCRIPTION
        "The IP address of the Secondary TACACS+ server."
    ::= { agTacacsConfig 4 }


tacCurCfgPort OBJECT-TYPE
    SYNTAX  INTEGER  (1..65000)
    MAX-ACCESS  read-only
    STATUS  current
    DESCRIPTION
        "Specify the TACACS+ port number."
    ::= { agTacacsConfig 5 }

tacNewCfgPort OBJECT-TYPE
    SYNTAX  INTEGER  (1..65000)
    MAX-ACCESS  read-write
    STATUS  current
    DESCRIPTION
        "Specify the TACACS+ port number."
    ::= { agTacacsConfig 6 }

tacCurCfgTimeout OBJECT-TYPE
    SYNTAX  INTEGER  (4..15)
    MAX-ACCESS  read-only
    STATUS  current
    DESCRIPTION
        "The maximum number of seconds before resending authentication
         to TACACS+ server."
    ::= { agTacacsConfig 7 }

tacNewCfgTimeout OBJECT-TYPE
    SYNTAX  INTEGER  (4..15)
    MAX-ACCESS  read-write
    STATUS  current
    DESCRIPTION
        "The maximum number of seconds before resending authentication
         to TACACS+ server."
    ::= { agTacacsConfig 8 }

tacCurCfgRetries OBJECT-TYPE
    SYNTAX  INTEGER  (1..3)
    MAX-ACCESS  read-only
    STATUS  current
    DESCRIPTION
        "Number of retries to the TACACS+ server."
    ::= { agTacacsConfig 9 }

tacNewCfgRetries OBJECT-TYPE
    SYNTAX  INTEGER  (1..3)
    MAX-ACCESS  read-write
    STATUS  current
    DESCRIPTION
        "Number of retries to the TACACS+ server."
    ::= { agTacacsConfig 10 }

tacCurCfgState OBJECT-TYPE
    SYNTAX  INTEGER {
        enabled(2),
        disabled(3)
        }
    MAX-ACCESS  read-only
    STATUS  current
    DESCRIPTION
        "Enable or disbale TACACS+ authentication."
    ::= { agTacacsConfig 11 }

tacNewCfgState OBJECT-TYPE
    SYNTAX  INTEGER {
        enabled(2),
        disabled(3)
        }
    MAX-ACCESS  read-write
    STATUS  current
    DESCRIPTION
        "Enable or disable TACACS+ authentication."
    ::= { agTacacsConfig 12 }

tacCurCfgAuthenString OBJECT-TYPE
    SYNTAX  DisplayString (SIZE(0..32))
    MAX-ACCESS  read-only
    STATUS  current
    DESCRIPTION
        "The TACACS+ authentication string."
    ::= { agTacacsConfig 13 }

tacNewCfgAuthenString OBJECT-TYPE
    SYNTAX  DisplayString (SIZE(0..32))
    MAX-ACCESS  read-write
    STATUS  current
    DESCRIPTION
        "The TACACS+ authentication string."
    ::= { agTacacsConfig 14 }

tacCurCfgTelnet OBJECT-TYPE
    SYNTAX  INTEGER {
        enabled(1),
        disabled(2)
        }
    MAX-ACCESS  read-only
    STATUS  current
    DESCRIPTION
        "Enable or disbale TACACS+ backdoor for telnet."
    ::= { agTacacsConfig 15 }

tacNewCfgTelnet OBJECT-TYPE
    SYNTAX  INTEGER {
        enabled(1),
        disabled(2)
        }
    MAX-ACCESS  read-write
    STATUS  current
    DESCRIPTION
        "Enable or disable TACACS+ backdoor for telnet."
    ::= { agTacacsConfig 16 }

tacCurCfgAuthenSecondString OBJECT-TYPE
    SYNTAX  DisplayString (SIZE(0..32))
    MAX-ACCESS  read-only
    STATUS  current
    DESCRIPTION
        "The second TACACS+ authentication string."
    ::= { agTacacsConfig 17 }

tacNewCfgAuthenSecondString OBJECT-TYPE
    SYNTAX  DisplayString (SIZE(0..32))
    MAX-ACCESS  read-write
    STATUS  current
    DESCRIPTION
        "The second TACACS+ authentication string."
    ::= { agTacacsConfig 18 }



tacCurCfgCmap OBJECT-TYPE
    SYNTAX  INTEGER {
        enabled(1),
        disabled(2)
        }
    MAX-ACCESS  read-only
    STATUS  current
    DESCRIPTION
        "Enable/Disable Tacacs+ new prividlege level maping."
    ::= { agTacacsConfig 25 }

tacNewCfgCmap OBJECT-TYPE
    SYNTAX  INTEGER {
        enabled(1),
        disabled(2)
        }
    MAX-ACCESS  read-write
    STATUS  current
    DESCRIPTION
        "Enable/Disable Tacacs+ new prividlege level maping."
    ::= { agTacacsConfig 26 }

-- Multiple Management network MIB objects
agMgmtNetTableMaxSize OBJECT-TYPE
    SYNTAX  Integer32 
    MAX-ACCESS  read-only 
    STATUS  current 
    DESCRIPTION 
        "The maximum number of entries in the Management 
         Network Table." 
    ::= { agMgmtNetConfig 1 }

agCurCfgMgmtNetTable OBJECT-TYPE
    SYNTAX  SEQUENCE OF AgCurCfgMgmtNetEntry
    MAX-ACCESS  not-accessible
    STATUS  current
    DESCRIPTION
        "The table for Management Network definitions
         in the current configuration block."
    ::= { agMgmtNetConfig 2 }

agCurCfgMgmtNetEntry OBJECT-TYPE
    SYNTAX  AgCurCfgMgmtNetEntry
    MAX-ACCESS  not-accessible
    STATUS  current
    DESCRIPTION
        "A row in the management network definition table." 
    INDEX   {  agCurCfgMgmtNetIndex }
    ::= { agCurCfgMgmtNetTable 1 }

AgCurCfgMgmtNetEntry ::= SEQUENCE {
    agCurCfgMgmtNetIndex  	Integer32,
    agCurCfgMgmtNetSubnet       IpAddress,
    agCurCfgMgmtNetMask         IpAddress
    }

agCurCfgMgmtNetIndex OBJECT-TYPE
    SYNTAX  Integer32
    MAX-ACCESS  read-only
    STATUS  current
    DESCRIPTION
        "The index of the Management Network Definition table." 
    ::= { agCurCfgMgmtNetEntry 1 }

agCurCfgMgmtNetSubnet OBJECT-TYPE
    SYNTAX  IpAddress 
    MAX-ACCESS  read-only
    STATUS  current
    DESCRIPTION
        "The Management Network Address in the current_configuration
         block." 
    ::= { agCurCfgMgmtNetEntry 2 }

agCurCfgMgmtNetMask OBJECT-TYPE
    SYNTAX  IpAddress 
    MAX-ACCESS  read-only
    STATUS  current
    DESCRIPTION
        "The Management Network Mask in the current_configuration
         block." 
    ::= { agCurCfgMgmtNetEntry 3 }

agNewCfgMgmtNetTable OBJECT-TYPE
    SYNTAX  SEQUENCE OF AgNewCfgMgmtNetEntry
    MAX-ACCESS  not-accessible
    STATUS  current
    DESCRIPTION
        "The table for Management Network definitions
         in the new configuration block."
    ::= { agMgmtNetConfig 3 }

agNewCfgMgmtNetEntry OBJECT-TYPE
    SYNTAX  AgNewCfgMgmtNetEntry
    MAX-ACCESS  not-accessible
    STATUS  current
    DESCRIPTION
        "A row in the management network definition table." 
    INDEX   {  agNewCfgMgmtNetIndex }
    ::= { agNewCfgMgmtNetTable 1 }

AgNewCfgMgmtNetEntry ::= SEQUENCE {
    agNewCfgMgmtNetIndex  	Integer32,
    agNewCfgMgmtNetSubnet       IpAddress,
    agNewCfgMgmtNetMask         IpAddress,
    agNewCfgMgmtNetDelete       INTEGER
    }

agNewCfgMgmtNetIndex OBJECT-TYPE
    SYNTAX  Integer32
    MAX-ACCESS  read-only
    STATUS  current
    DESCRIPTION
        "The index of the Management Network Definition table." 
    ::= { agNewCfgMgmtNetEntry 1 }

agNewCfgMgmtNetSubnet OBJECT-TYPE
    SYNTAX  IpAddress 
    MAX-ACCESS  read-create
    STATUS  current
    DESCRIPTION
        "The Management Network Address in the new_configuration
         block." 
    ::= { agNewCfgMgmtNetEntry 2 }

agNewCfgMgmtNetMask OBJECT-TYPE
    SYNTAX  IpAddress 
    MAX-ACCESS  read-create
    STATUS  current
    DESCRIPTION
        "The Management Network Mask in the new_configuration
         block." 
    ::= { agNewCfgMgmtNetEntry 3 }

agNewCfgMgmtNetDelete OBJECT-TYPE
    SYNTAX  INTEGER {
        other(1),
        delete(2)
        }
    MAX-ACCESS  read-create
    STATUS  current
    DESCRIPTION
        "By setting the value to delete(2), the entire row is deleted."
    ::= { agNewCfgMgmtNetEntry 4 }

-- Pattern Matching Group MIB objects
agPgrpMatchTableMaxSize OBJECT-TYPE
    SYNTAX  Integer32
    MAX-ACCESS  read-only 
    STATUS  current 
    DESCRIPTION 
        "The maximum number of entries in the Pattern 
         Match Group Table." 
    ::= { agPgroup 1 }

agCurCfgPgrpMatchTable OBJECT-TYPE
    SYNTAX  SEQUENCE OF AgCurCfgPgrpMatchEntry
    MAX-ACCESS  not-accessible
    STATUS  current
    DESCRIPTION
        "The table for Pattern Match Group definitions
         in the current configuration block."
    ::= { agPgroup 2 }

agCurCfgPgrpMatchEntry OBJECT-TYPE
    SYNTAX  AgCurCfgPgrpMatchEntry
    MAX-ACCESS  not-accessible
    STATUS  current
    DESCRIPTION
        "A row in the Pattern Match Group table." 
    INDEX   {  agCurCfgPgrpMatchIndex }
    ::= { agCurCfgPgrpMatchTable 1 }

AgCurCfgPgrpMatchEntry ::= SEQUENCE {
    agCurCfgPgrpMatchIndex  	Integer32,
    agCurCfgPgrpName		DisplayString,
    agCurCfgPgrpMatchBmap       OCTET STRING 
    }

agCurCfgPgrpMatchIndex OBJECT-TYPE
    SYNTAX  Integer32 
    MAX-ACCESS  read-only
    STATUS  current
    DESCRIPTION
        "The index of the Pattern Match Group Definition table." 
    ::= { agCurCfgPgrpMatchEntry 1 }

agCurCfgPgrpName OBJECT-TYPE
    SYNTAX  DisplayString (SIZE(0..31))
    MAX-ACCESS  read-only
    STATUS  current
    DESCRIPTION
        "The name for the Pattern Match Group."
    ::= { agCurCfgPgrpMatchEntry 2 }

agCurCfgPgrpMatchBmap OBJECT-TYPE
    SYNTAX  OCTET STRING
    MAX-ACCESS  read-only
    STATUS  current
    DESCRIPTION
        "The pattern matching rules applied to the port.  The pattern rules
         are presented in bitmap format.

         in receiving order:

	     OCTET 1  OCTET 2  .....
             xxxxxxxx xxxxxxxx ..... 
             ||    || |_ string 9
             ||    ||  
             ||    ||___ string 8
             ||    |____ string 7
             ||      .    .   .
             ||_________ string 2
             |__________ string 1 (as index to slbCurCfgUrlLbPathTable)

         where x : 1 - The represented string matching rule applied 
		   0 - The represented string matching rule applied"
    ::= { agCurCfgPgrpMatchEntry 3 }

agNewCfgPgrpMatchTable OBJECT-TYPE
    SYNTAX  SEQUENCE OF AgNewCfgPgrpMatchEntry
    MAX-ACCESS  not-accessible
    STATUS  current
    DESCRIPTION
        "The table for Pattern Match Group definitions
         in the new configuration block."
    ::= { agPgroup 3 }

agNewCfgPgrpMatchEntry OBJECT-TYPE
    SYNTAX  AgNewCfgPgrpMatchEntry
    MAX-ACCESS  not-accessible
    STATUS  current
    DESCRIPTION
        "A row in the Pattern Match Group definition table." 
    INDEX   {  agNewCfgPgrpMatchIndex }
    ::= { agNewCfgPgrpMatchTable 1 }

AgNewCfgPgrpMatchEntry ::= SEQUENCE {
    agNewCfgPgrpMatchIndex  	Integer32,
    agNewCfgPgrpName		DisplayString,
    agNewCfgPgrpMatchAdd        Integer32,
    agNewCfgPgrpMatchRem        Integer32,
    agNewCfgPgrpMatchBmap       OCTET STRING,
    agNewCfgPgrpDelete          INTEGER
    }

agNewCfgPgrpMatchIndex OBJECT-TYPE
    SYNTAX  Integer32 
    MAX-ACCESS  read-only
    STATUS  current
    DESCRIPTION
        "The index of the Pattern Match Group Definition table." 
    ::= { agNewCfgPgrpMatchEntry 1 }

agNewCfgPgrpName OBJECT-TYPE
    SYNTAX  DisplayString (SIZE(0..31))
    MAX-ACCESS  read-create
    STATUS  current
    DESCRIPTION
        "The name for the Pattern Match Group."
    ::= { agNewCfgPgrpMatchEntry 2 }

agNewCfgPgrpMatchAdd OBJECT-TYPE
    SYNTAX  Integer32
    MAX-ACCESS  read-create
    STATUS  current
    DESCRIPTION
        "The Pattern Match Group String added in the new_configuration
         block." 
    ::= { agNewCfgPgrpMatchEntry 3 }

agNewCfgPgrpMatchRem OBJECT-TYPE
    SYNTAX  Integer32
    MAX-ACCESS  read-create
    STATUS  current
    DESCRIPTION
        "The Pattern Match Group String removed in the new_configuration
         block." 
    ::= { agNewCfgPgrpMatchEntry 4 }

agNewCfgPgrpMatchBmap OBJECT-TYPE
    SYNTAX  OCTET STRING 
    MAX-ACCESS  read-only
    STATUS  current
    DESCRIPTION
        "The pattern matching rules applied to the port.  The pattern rules
         are presented in bitmap format.

         in receiving order:

	     OCTET 1  OCTET 2  .....
             xxxxxxxx xxxxxxxx ..... 
             ||    || |_ string 9
             ||    ||  
             ||    ||___ string 8
             ||    |____ string 7
             ||      .    .   .
             ||_________ string 2
             |__________ string 1 (as index to slbCurCfgUrlLbPathTable)

         where x : 1 - The represented string matching rule applied 
		   0 - The represented string matching rule applied"
    ::= { agNewCfgPgrpMatchEntry 5 }

agNewCfgPgrpDelete OBJECT-TYPE
    SYNTAX  INTEGER {
        other(1),
        delete(2)
        }
    MAX-ACCESS  read-create
    STATUS  current
    DESCRIPTION
        "By setting the value to delete(2), the entire row is deleted."
    ::= { agNewCfgPgrpMatchEntry 6 }

agCfgSecurityPortTable OBJECT-TYPE
    SYNTAX  SEQUENCE OF AgCfgSecurityPortTableEntry
    MAX-ACCESS  not-accessible
    STATUS  current
    DESCRIPTION
        "The table of Security related features enabled/disabled for this port."
    ::= { agSecurity 2 }

agCfgSecurityPortTableEntry OBJECT-TYPE
    SYNTAX  AgCfgSecurityPortTableEntry
    MAX-ACCESS  not-accessible
    STATUS  current
    DESCRIPTION
        "A row in the Security related in the current configuration block."
    INDEX   { agCfgSecurityPortIndx }
    ::= { agCfgSecurityPortTable 1 }

AgCfgSecurityPortTableEntry ::=
    SEQUENCE {
	agCfgSecurityPortIndx
	    Integer32,
	agCurCfgSecurityDosState
	    INTEGER,
	agNewCfgSecurityDosState
	    INTEGER,
        agCurCfgSecurityIpAclState
            INTEGER,
        agNewCfgSecurityIpAclState
            INTEGER,
        agCurCfgSecurityUbState
            INTEGER,
        agNewCfgSecurityUbState
            INTEGER,
        agCurCfgSecurityBogonState
            INTEGER,
        agCurCfgSecurityAttacksBmap
            OCTET STRING,
        agNewCfgSecurityAttacksBmap
            OCTET STRING,
        agNewCfgSecurityAddAttack
            INTEGER,
        agNewCfgSecurityRemAttack
            INTEGER,
        agNewCfgSecurityDoSAttacks
            INTEGER,
	agCurCfgSecuritySymantecState  
	    INTEGER,
	agNewCfgSecuritySymantecState  
	    INTEGER,
        agNewCfgSecurityBogonState
            INTEGER
    }

agCfgSecurityPortIndx OBJECT-TYPE
    SYNTAX  Integer32
    MAX-ACCESS  read-only
    STATUS  current
    DESCRIPTION
        "The port index."
    ::= { agCfgSecurityPortTableEntry 1 }

agCurCfgSecurityDosState OBJECT-TYPE
    SYNTAX  INTEGER {
        enabled(1),
        disabled(2)
        }
    MAX-ACCESS  read-only
    STATUS  current
    DESCRIPTION
        "Enable/Disable DOS attack per port."
    ::= { agCfgSecurityPortTableEntry 2 }

agNewCfgSecurityDosState OBJECT-TYPE
    SYNTAX  INTEGER {
        enabled(1),
        disabled(2)
        }
    MAX-ACCESS  read-write
    STATUS  current
    DESCRIPTION
        "Enable/Disable DOS attack per port."
    ::= { agCfgSecurityPortTableEntry 3 }

agCurCfgSecurityIpAclState OBJECT-TYPE
    SYNTAX  INTEGER {
        enabled(1),
        disabled(2)
        }
    MAX-ACCESS  read-only
    STATUS  current
    DESCRIPTION
        "Enable/Disable IP ACL per port."
    ::= { agCfgSecurityPortTableEntry 4 }

agNewCfgSecurityIpAclState OBJECT-TYPE
    SYNTAX  INTEGER {
        enabled(1),
        disabled(2)
        }
    MAX-ACCESS  read-write
    STATUS  current
    DESCRIPTION
        "Enable/Disable IP ACL per port."
    ::= { agCfgSecurityPortTableEntry 5 }

agCurCfgSecurityUbState OBJECT-TYPE
    SYNTAX  INTEGER {
        enabled(1),
        disabled(2)
        }
    MAX-ACCESS  read-only
    STATUS  current
    DESCRIPTION
        "Enable/Disable UDP Blast per port."
    ::= { agCfgSecurityPortTableEntry 6 }

agNewCfgSecurityUbState OBJECT-TYPE
    SYNTAX  INTEGER {
        enabled(1),
        disabled(2)
        }
    MAX-ACCESS  read-write
    STATUS  current
    DESCRIPTION
        "Enable/Disable UDP Blast per port."
    ::= { agCfgSecurityPortTableEntry 7 }

agCurCfgSecurityBogonState OBJECT-TYPE
    SYNTAX  INTEGER {
        enabled(1),
        disabled(2)
        }
    MAX-ACCESS  read-only
    STATUS  current
    DESCRIPTION
        "Enable/Disable Bogon IP ACL per port."
    ::= { agCfgSecurityPortTableEntry 8 }

agNewCfgSecurityBogonState OBJECT-TYPE
    SYNTAX  INTEGER {
        enabled(1),
        disabled(2)
        }
    MAX-ACCESS  read-write
    STATUS  current
    DESCRIPTION
        "Enable/Disable Bogon IP ACL per port."
    ::= { agCfgSecurityPortTableEntry 9 }

-- MIBs for perPort DoS Attacks add/rem

agCurCfgSecurityAttacksBmap OBJECT-TYPE
    SYNTAX  OCTET STRING
    MAX-ACCESS  read-only
    STATUS  current
    DESCRIPTION
        "The DoS Attacks added/removed for this port.
        The selected DoS Attacks are presented in a bitmap format.

         in receiving order:

             OCTET 1  OCTET 2  .....
             xxxxxxxx xxxxxxxx .....
             ||    || |_______  9
             ||    ||
             ||    ||_________  8
             ||    |__________  7
             ||      .    .   .
             ||________________ 2
             |________________  1

        1  - IPLen
        2  - IPVersion
        3  - Broadcast
        4  - Loopback
        5  - Land
        6  - IPReserved
        7  - IPTTL
        8  - IPProt
        9  - IPOptLen
        10 - FragMoreDont
        11 - FragData
        12 - FragBoundary
        13 - FragLast
        14 - FragDontOff
        15 - FragOpt
        16 - FragOff
        17 - FragOversize
        18 - TCPLen
        19 - TCPPortZero
        20 - BlatAttack
        21 - TCPReserved
        22 - NullScanAttack
        23 - FullXmasScan
        24 - FinScan
        25 - VecnaScan
        26 - XmasScanAttack
        27 - SynFinScan
        28 - FlagAbnormal
        29 - SYNData
        30 - SYNFrag
        31 - FTPPort
        32 - DNSPort
        33 - SeqZero
        34 - AckZero
        35 - TCPOptLen
        36 - UDPLen
        37 - UDPPortZero
        38 - FraggleAttack
        39 - Pepsi
        40 - Rc8
        41 - SNMPNull
        42 - ICMPLen
        43 - SmurfAttack
        44 - ICMPData
        45 - ICMPOff
        46 - ICMPType
        47 - IGMPLen
        48 - IGMPFrag
        49 - IGMPType
        50 - ARPLen
        51 - ARPNbCast
        52 - ARPNuCast
        53 - ARPSpoof
        54 - GARP
        55 - IP6Len
        56 - IP6Version

        where x :      1 - The represented DoS Attack is enabled
                       0 - The represented DoS Attack is disabled"
    ::= { agCfgSecurityPortTableEntry 10 }

agNewCfgSecurityAttacksBmap OBJECT-TYPE
    SYNTAX  OCTET STRING
    MAX-ACCESS  read-only
    STATUS  current
    DESCRIPTION
        "The DoS Attacks added/removed for this port.
        The selected DoS Attacks are presented in a bitmap format.

         in receiving order:

             OCTET 1  OCTET 2  .....
             xxxxxxxx xxxxxxxx .....
             ||    || |______  9
             ||    ||
             ||    ||________  8
             ||    |_________  7
             ||      .    .   .
             ||_______________ 2
             |________________ 1

        1  - IPLen
        2  - IPVersion
        3  - Broadcast
        4  - Loopback
        5  - Land
        6  - IPReserved
        7  - IPTTL
        8  - IPProt
        9  - IPOptLen
        10 - FragMoreDont
        11 - FragData
        12 - FragBoundary
        13 - FragLast
        14 - FragDontOff
        15 - FragOpt
        16 - FragOff
        17 - FragOversize
        18 - TCPLen
        19 - TCPPortZero
        20 - BlatAttack
        21 - TCPReserved
        22 - NullScanAttack
        23 - FullXmasScan
        24 - FinScan
        25 - VecnaScan
        26 - XmasScanAttack
        27 - SynFinScan
        28 - FlagAbnormal
        29 - SYNData
        30 - SYNFrag
        31 - FTPPort
        32 - DNSPort
        33 - SeqZero
        34 - AckZero
        35 - TCPOptLen
        36 - UDPLen
        37 - UDPPortZero
        38 - FraggleAttack
        39 - Pepsi
        40 - Rc8
        41 - SNMPNull
        42 - ICMPLen
        43 - SmurfAttack
        44 - ICMPData
        45 - ICMPOff
        46 - ICMPType
        47 - IGMPLen
        48 - IGMPFrag
        49 - IGMPType
        50 - ARPLen
        51 - ARPNbCast
        52 - ARPNuCast
        53 - ARPSpoof
        54 - GARP
        55 - IP6Len
        56 - IP6Version

        where x :      1 - The represented DoS Attack is enabled
                       0 - The represented DoS Attack is disabled"
    ::= { agCfgSecurityPortTableEntry 11 }

agNewCfgSecurityAddAttack OBJECT-TYPE
    SYNTAX  INTEGER {
        iplen(1),
        ipversion(2),
        broadcast(3),
        loopback(4),
        land(5),
        ipreserved(6),
        ipttl(7),
        ipprot(8),
        ipoptlen(9),
        fragmoredont(10),
        fragdata(11),
        fragboundary(12),
        fraglast(13),
        fragdontoff(14),
        fragopt(15),
        fragoff(16),
        fragoversize(17),
        tcplen(18),
        tcpportzero(19),
        blat(20),
        tcpreserved(21),
        nullscan(22),
        fullxmasscan(23),
        finscan(24),
        vecnascan(25),
        xmassscan(26),
        synfinscan(27),
        flagabnormal(28),
        syndata(29),
        synfrag(30),
        ftpport(31),
        dnsport(32),
        seqzero(33),
        ackzero(34),
        tcpoptlen(35),
        udplen(36),
        udpportzero(37),
        fraggle(38),
        pepsi(39),
        rc8(40),
        snmpnull(41),
        icmplen(42),
        smurf(43),
        icmpdata(44),
        icmpoff(45),
        icmptype(46),
        igmplen(47),
        igmpfrag(48),
        igmptype(49),
        arplen(50),
        arpnbcast(51),
        arpnucast(52),
        arpspoof(53),
        garp(54),
        ip6len(55),
        ip6version(56)
        }
    MAX-ACCESS  read-write
    STATUS  current
    DESCRIPTION
        "This is an action object to add a DoS Attack to a port. The value
         specified with this object is number given in this description.

        1  - IPLen
        2  - IPVersion
        3  - Broadcast
        4  - Loopback
        5  - Land
        6  - IPReserved
        7  - IPTTL
        8  - IPProt
        9  - IPOptLen
        10 - FragMoreDont
        11 - FragData
        12 - FragBoundary
        13 - FragLast
        14 - FragDontOff
        15 - FragOpt
        16 - FragOff
        17 - FragOversize
        18 - TCPLen
        19 - TCPPortZero
        20 - BlatAttack
        21 - TCPReserved
        22 - NullScanAttack
        23 - FullXmasScan
        24 - FinScan
        25 - VecnaScan
        26 - XmasScanAttack
        27 - SynFinScan
        28 - FlagAbnormal
        29 - SYNData
        30 - SYNFrag
        31 - FTPPort
        32 - DNSPort
        33 - SeqZero
        34 - AckZero
        35 - TCPOptLen
        36 - UDPLen
        37 - UDPPortZero
        38 - FraggleAttack
        39 - Pepsi
        40 - Rc8
        41 - SNMPNull
        42 - ICMPLen
        43 - SmurfAttack
        44 - ICMPData
        45 - ICMPOff
        46 - ICMPType
        47 - IGMPLen
        48 - IGMPFrag
        49 - IGMPType
        50 - ARPLen
        51 - ARPNbCast
        52 - ARPNuCast
        53 - ARPSpoof
        54 - GARP
        55 - IP6Len
        56 - IP6Version

            When read, the value '0' is returned always."
    ::= { agCfgSecurityPortTableEntry 12 }

agNewCfgSecurityRemAttack  OBJECT-TYPE
    SYNTAX  INTEGER {
        iplen(1),
        ipversion(2),
        broadcast(3),
        loopback(4),
        land(5),
        ipreserved(6),
        ipttl(7),
        ipprot(8),
        ipoptlen(9),
        fragmoredont(10),
        fragdata(11),
        fragboundary(12),
        fraglast(13),
        fragdontoff(14),
        fragopt(15),
        fragoff(16),
        fragoversize(17),
        tcplen(18),
        tcpportzero(19),
        blat(20),
        tcpreserved(21),
        nullscan(22),
        fullxmasscan(23),
        finscan(24),
        vecnascan(25),
        xmassscan(26),
        synfinscan(27),
        flagabnormal(28),
        syndata(29),
        synfrag(30),
        ftpport(31),
        dnsport(32),
        seqzero(33),
        ackzero(34),
        tcpoptlen(35),
        udplen(36),
        udpportzero(37),
        fraggle(38),
        pepsi(39),
        rc8(40),
        snmpnull(41),
        icmplen(42),
        smurf(43),
        icmpdata(44),
        icmpoff(45),
        icmptype(46),
        igmplen(47),
        igmpfrag(48),
        igmptype(49),
        arplen(50),
        arpnbcast(51),
        arpnucast(52),
        arpspoof(53),
        garp(54),
        ip6len(55),
        ip6version(56)
        }
    MAX-ACCESS  read-write
    STATUS  current
    DESCRIPTION
        "This is an action object to remove a DoS attack for a port. The
         value specified with this object is number given in this description.

        1  - IPLen
        2  - IPVersion
        3  - Broadcast
        4  - Loopback
        5  - Land
        6  - IPReserved
        7  - IPTTL
        8  - IPProt
        9  - IPOptLen
        10 - FragMoreDont
        11 - FragData
        12 - FragBoundary
        13 - FragLast
        14 - FragDontOff
        15 - FragOpt
        16 - FragOff
        17 - FragOversize
        18 - TCPLen
        19 - TCPPortZero
        20 - BlatAttack
        21 - TCPReserved
        22 - NullScanAttack
        23 - FullXmasScan
        24 - FinScan
        25 - VecnaScan
        26 - XmasScanAttack
        27 - SynFinScan
        28 - FlagAbnormal
        29 - SYNData
        30 - SYNFrag
        31 - FTPPort
        32 - DNSPort
        33 - SeqZero
        34 - AckZero
        35 - TCPOptLen
        36 - UDPLen
        37 - UDPPortZero
        38 - FraggleAttack
        39 - Pepsi
        40 - Rc8
        41 - SNMPNull
        42 - ICMPLen
        43 - SmurfAttack
        44 - ICMPData
        45 - ICMPOff
        46 - ICMPType
        47 - IGMPLen
        48 - IGMPFrag
        49 - IGMPType
        50 - ARPLen
        51 - ARPNbCast
        52 - ARPNuCast
        53 - ARPSpoof
        54 - GARP
        55 - IP6Len
        56 - IP6Version

            When read, the value '0' is returned always."
    ::= { agCfgSecurityPortTableEntry 13 }

agNewCfgSecurityDoSAttacks OBJECT-TYPE
    SYNTAX  INTEGER {
	ok(1),
	addall(2),
	remall(3)
    }
    MAX-ACCESS  read-write
    STATUS  current
    DESCRIPTION
	"Add all DoS attacks to the port by setting the value to '2'.
	 Remove all DoS attacks from the port by setting the value to '3'.
	 Do nothing by setting the value to '1'.
 	 When read, the value '0' is returned always."
    ::= { agCfgSecurityPortTableEntry 14 }

agCurCfgSecuritySymantecState OBJECT-TYPE
    SYNTAX  INTEGER {
        enabled(1),
        disabled(2)
        }
    MAX-ACCESS  read-only
    STATUS  current
    DESCRIPTION
        "Enable/Disable Symantec IPS Processing per port."
    ::= { agCfgSecurityPortTableEntry 15 }

agNewCfgSecuritySymantecState OBJECT-TYPE
    SYNTAX  INTEGER {
        enabled(1),
        disabled(2)
        }
    MAX-ACCESS  read-write
    STATUS  current
    DESCRIPTION
        "Enable/Disable Symantec IPS Processing per port."
    ::= { agCfgSecurityPortTableEntry 16 }

-- IP_ACL: IP Address ACL Configuration

ipAclTableMaxSize OBJECT-TYPE
    SYNTAX  Integer32
    MAX-ACCESS  read-only
    STATUS  current
    DESCRIPTION
        "The maximum number of rows in the IP ACL table."
    ::= { ipAclCfg 1 }

ipAclCurCfgTable OBJECT-TYPE
    SYNTAX  SEQUENCE OF IpAclCurCfgEntry
    MAX-ACCESS  not-accessible
    STATUS  current
    DESCRIPTION
        "The table of IP ACL in the current configuration block."
    ::= { ipAclCfg 2 }

ipAclCurCfgEntry OBJECT-TYPE
    SYNTAX  IpAclCurCfgEntry
    MAX-ACCESS  not-accessible
    STATUS  current
    DESCRIPTION
        "A row in the IP ACL table"
    INDEX   { ipAclCurCfgIndx }
    ::= { ipAclCurCfgTable 1 }

IpAclCurCfgEntry ::= SEQUENCE {
    ipAclCurCfgIndx             Integer32,
    ipAclCurCfgIp               IpAddress,
    ipAclCurCfgMask             IpAddress
    }

ipAclCurCfgIndx OBJECT-TYPE
    SYNTAX  Integer32
    MAX-ACCESS  read-only
    STATUS  current
    DESCRIPTION
        "The index of the IP ACL table."
    ::= { ipAclCurCfgEntry 1}

ipAclCurCfgIp OBJECT-TYPE
    SYNTAX  IpAddress
    MAX-ACCESS  read-only
    STATUS  current
    DESCRIPTION
        "The IP address of the entry."
    ::= { ipAclCurCfgEntry 2}

ipAclCurCfgMask OBJECT-TYPE 
    SYNTAX  IpAddress
    MAX-ACCESS  read-only 
    STATUS  current 
    DESCRIPTION 
        "The IP address Mask of the entry."
    ::= { ipAclCurCfgEntry 3}

ipAclNewCfgTable OBJECT-TYPE
    SYNTAX  SEQUENCE OF IpAclNewCfgEntry
    MAX-ACCESS  not-accessible
    STATUS  current
    DESCRIPTION
        "The table of IP ACL in the new configuration block."
    ::= { ipAclCfg 3 }

ipAclNewCfgEntry OBJECT-TYPE
    SYNTAX  IpAclNewCfgEntry
    MAX-ACCESS  not-accessible
    STATUS  current
    DESCRIPTION
        "A row in the IP ACL table"
    INDEX   { ipAclNewCfgIndx }
    ::= { ipAclNewCfgTable 1 }

IpAclNewCfgEntry ::= SEQUENCE {
    ipAclNewCfgIndx             Integer32,
    ipAclNewCfgIp               IpAddress,
    ipAclNewCfgAction           INTEGER,
    ipAclNewCfgMask             IpAddress
    }

ipAclNewCfgIndx OBJECT-TYPE
    SYNTAX  Integer32
    MAX-ACCESS  read-only
    STATUS  current
    DESCRIPTION
        "The index of the IP ACL table."
    ::= { ipAclNewCfgEntry 1}

ipAclNewCfgIp OBJECT-TYPE
    SYNTAX  IpAddress
    MAX-ACCESS  read-create
    STATUS  current
    DESCRIPTION
        "The IP address of the entry."
    ::= { ipAclNewCfgEntry 2}

ipAclNewCfgAction OBJECT-TYPE
    SYNTAX  INTEGER {
        other(1),
        delete(2)
       }  
    MAX-ACCESS  read-create
    STATUS  current
    DESCRIPTION
        "When set to the value of 2 (delete), the entire row is deleted. 
         When read, other is returned. Setting the value to anything other 
         than 2(delete) has no effect on the state of the row."
    ::= { ipAclNewCfgEntry 3 }

ipAclNewCfgMask OBJECT-TYPE 
    SYNTAX  IpAddress
    MAX-ACCESS  read-create
    STATUS  current 
    DESCRIPTION 
        "The IP address Mask of the entry."
    ::= { ipAclNewCfgEntry 4}


-- UDP_BLAST: UDP Blast Protection 

udpBlastudpPortTableMaxSize OBJECT-TYPE
    SYNTAX  Integer32
    MAX-ACCESS  read-only
    STATUS  current
    DESCRIPTION
        "The maximum number of rows in the UDP Blast Port table."
    ::= { udpBlastCfg 1 }

udpBlastCurCfgudpPortPacketLimit OBJECT-TYPE
    SYNTAX  INTEGER(1..20000000) 
    MAX-ACCESS  read-only
    STATUS  current
    DESCRIPTION
        "The default packet limit in the current configuration block."
    ::= { udpBlastCfg 2 }

udpBlastCurCfgudpPortTable OBJECT-TYPE
    SYNTAX  SEQUENCE OF UdpBlastCurCfgudpPortEntry
    MAX-ACCESS  not-accessible
    STATUS  current
    DESCRIPTION
        "The UDP Blast port table in the current configuration block."
    ::= { udpBlastCfg 3 }

udpBlastCurCfgudpPortEntry OBJECT-TYPE
    SYNTAX  UdpBlastCurCfgudpPortEntry
    MAX-ACCESS  not-accessible
    STATUS  current
    DESCRIPTION
        "A row in the UDP Blast UDP Port table"
    INDEX   { udpBlastCurCfgudpPortLowIndx, udpBlastCurCfgudpPortHighIndx}
    ::= { udpBlastCurCfgudpPortTable 1 }

UdpBlastCurCfgudpPortEntry ::= SEQUENCE {
    udpBlastCurCfgudpPortLowIndx              INTEGER,
    udpBlastCurCfgudpPortHighIndx             INTEGER,
    udpBlastCurCfgudpPortEntryPacketLimit     INTEGER
    }

udpBlastCurCfgudpPortLowIndx OBJECT-TYPE
    SYNTAX  INTEGER(1..65535)
    MAX-ACCESS  read-only
    STATUS  current
    DESCRIPTION
        "The low UDP port number of UDP port range in the UDP Port table."
    ::= { udpBlastCurCfgudpPortEntry 1}

udpBlastCurCfgudpPortHighIndx OBJECT-TYPE
    SYNTAX  INTEGER(1..65535)
    MAX-ACCESS  read-only
    STATUS  current
    DESCRIPTION
        "The high UDP port number of UDP port range in the UDP Port table.
         If highIndx and lowIndx are set to the same, it is considered a
         single port instead of range"
    ::= { udpBlastCurCfgudpPortEntry 2}

udpBlastCurCfgudpPortEntryPacketLimit OBJECT-TYPE
    SYNTAX  INTEGER(1..20000000)
    MAX-ACCESS  read-only
    STATUS  current
    DESCRIPTION
        "The Packet Limit of the UDP Port Entry."
    ::= { udpBlastCurCfgudpPortEntry 3}

udpBlastNewCfgudpPortPacketLimit OBJECT-TYPE
    SYNTAX  INTEGER(1..20000000)
    MAX-ACCESS  read-write
    STATUS  current
    DESCRIPTION
        "The default packet limit in the new configuration block."
    ::= { udpBlastCfg 4 }

udpBlastNewCfgudpPortTable OBJECT-TYPE
    SYNTAX  SEQUENCE OF UdpBlastNewCfgudpPortEntry
    MAX-ACCESS  not-accessible
    STATUS  current
    DESCRIPTION
        "The UDP Blast table in the new configuration block."
    ::= { udpBlastCfg 5 }

udpBlastNewCfgudpPortEntry OBJECT-TYPE
    SYNTAX  UdpBlastNewCfgudpPortEntry
    MAX-ACCESS  not-accessible
    STATUS  current
    DESCRIPTION
        "A row in the UDP Blast UDP Port table"
    INDEX   { udpBlastNewCfgudpPortLowIndx, udpBlastNewCfgudpPortHighIndx}
    ::= { udpBlastNewCfgudpPortTable 1 }

UdpBlastNewCfgudpPortEntry ::= SEQUENCE {
    udpBlastNewCfgudpPortLowIndx              INTEGER,
    udpBlastNewCfgudpPortHighIndx             INTEGER,
    udpBlastNewCfgudpPortEntryDelete          INTEGER,
    udpBlastNewCfgudpPortEntryPacketLimit     INTEGER
    }

udpBlastNewCfgudpPortLowIndx OBJECT-TYPE
    SYNTAX  INTEGER(1..65535)
    MAX-ACCESS  read-only
    STATUS  current
    DESCRIPTION
        "The low UDP port number of UDP port range in the UDP Port table.
         The difference between the minimum of all the  low UDP port 
         number specified and the maximum of all the high UDP port number 
         specified can't exceed 5000."
    ::= { udpBlastNewCfgudpPortEntry 1}

udpBlastNewCfgudpPortHighIndx OBJECT-TYPE
    SYNTAX  INTEGER(1..65535)
    MAX-ACCESS  read-only
    STATUS  current
    DESCRIPTION
        "The high UDP port number of UDP port range in the UDP Port table.
         The difference between the minimum of all the  low UDP port 
         number specified and the maximum of all the high UDP port number 
         specified can't exceed 5000. 
         If highIndx and lowIndx are set to the same, it is considered a 
         single port instead of range."
    ::= { udpBlastNewCfgudpPortEntry 2}

udpBlastNewCfgudpPortEntryDelete OBJECT-TYPE
    SYNTAX  INTEGER {
        other(1),
        delete(2)
       }  
    MAX-ACCESS  read-create
    STATUS  current
    DESCRIPTION
        "This deletes the UDP port entry from lowIndx to highIndx."
    ::= { udpBlastNewCfgudpPortEntry 3}

udpBlastNewCfgudpPortEntryPacketLimit OBJECT-TYPE
    SYNTAX  INTEGER(1..20000000) 
    MAX-ACCESS  read-create
    STATUS  current
    DESCRIPTION
        "The Packet Limit of the UDP Port Entry."
    ::= { udpBlastNewCfgudpPortEntry 4}

-- General Security MIB objects

secCurCfgSecurityLogThreshold OBJECT-TYPE
    SYNTAX  INTEGER(0..1048576)
    MAX-ACCESS  read-only
    STATUS  current
    DESCRIPTION
        "The rate threshold for security logging in packets/sec. Rate zero indicates no rate threshold."
    ::= { secGeneralCfg 1 }

secNewCfgSecurityLogThreshold OBJECT-TYPE
    SYNTAX  INTEGER(0..1048576)
    MAX-ACCESS  read-write
    STATUS  current
    DESCRIPTION
        "The rate threshold for security logging in packets/sec. Rate zero indicates no rate threshold."
    ::= { secGeneralCfg 2 }


secCurCfgPacketDepth OBJECT-TYPE
    SYNTAX  INTEGER(0..255)
    MAX-ACCESS  read-only
    STATUS  current
    DESCRIPTION
        "Depth of match for pattern matching, in units of packets.
	 A value of 0 means match all packets in the stream."
    ::= { secGeneralCfg 5 }

secNewCfgPacketDepth OBJECT-TYPE
    SYNTAX  INTEGER(0..255)
    MAX-ACCESS  read-write
    STATUS  current
    DESCRIPTION
        "Depth of match for pattern matching, in units of packets.
	 A value of 0 means match all packets in the stream."
    ::= { secGeneralCfg 6 }

secCurCfgIpAclSyslogThreshold OBJECT-TYPE
    SYNTAX  Integer32
    MAX-ACCESS read-only
    STATUS  current
    DESCRIPTION
        "Display syslog when threshold number of ACL's have been hit."
    ::= {secGeneralCfg 7 }

secNewCfgIpAclSyslogThreshold OBJECT-TYPE
    SYNTAX  Integer32
    MAX-ACCESS  read-write
    STATUS  current
    DESCRIPTION
        "Display syslog when threshold number of ACL's have been hit."
    ::= {secGeneralCfg 8 }

secCurCfgIpAclSyslogTime OBJECT-TYPE
    SYNTAX  Integer32
    MAX-ACCESS read-only
    STATUS  current
    DESCRIPTION
        "Display syslog after specified number of minutes have passed."
    ::= { secGeneralCfg 9}

secNewCfgIpAclSyslogTime OBJECT-TYPE
    SYNTAX  Integer32
    MAX-ACCESS  read-write
    STATUS  current
    DESCRIPTION
        "Display syslog after specified number of minutes have passed."
    ::= { secGeneralCfg 10}


-- DoS Attack Prevention MIB objects

dosCurCfgIPTTL OBJECT-TYPE
    SYNTAX  INTEGER(0..255)
    MAX-ACCESS  read-only
    STATUS  current
    DESCRIPTION
        "The smallest allowable IP ttl."
    ::= { dosAttackPrevCfg 1 }

dosNewCfgIPTTL OBJECT-TYPE
    SYNTAX  INTEGER(0..255)
    MAX-ACCESS  read-write
    STATUS  current
    DESCRIPTION
        "The smallest allowable IP ttl."
    ::= { dosAttackPrevCfg 2 }

dosCurCfgIPProt OBJECT-TYPE
    SYNTAX  INTEGER(0..255)
    MAX-ACCESS  read-only
    STATUS  current
    DESCRIPTION
        "The highest allowable IP protocol."
    ::= { dosAttackPrevCfg 3 }

dosNewCfgIPProt OBJECT-TYPE
    SYNTAX  INTEGER(0..255)
    MAX-ACCESS  read-write
    STATUS  current
    DESCRIPTION
        "The highest allowable IP protocol."
    ::= { dosAttackPrevCfg 4 }
    
dosCurCfgFragdata OBJECT-TYPE
    SYNTAX  INTEGER(16..248)
    MAX-ACCESS  read-only
    STATUS  current
    DESCRIPTION
        "The smallest allowable IP fragment payload."
    ::= { dosAttackPrevCfg 5 }

dosNewCfgFragdata OBJECT-TYPE
    SYNTAX  INTEGER(16..248)
    MAX-ACCESS  read-write
    STATUS  current
    DESCRIPTION
        "The smallest allowable IP fragment payload."
    ::= { dosAttackPrevCfg 6 }
    
dosCurCfgFragoff OBJECT-TYPE
    SYNTAX  INTEGER(16..248)
    MAX-ACCESS  read-only
    STATUS  current
    DESCRIPTION
        "The smallest allowable IP fragment offset."
    ::= { dosAttackPrevCfg 7 }

dosNewCfgFragoff OBJECT-TYPE
    SYNTAX  INTEGER(16..248)
    MAX-ACCESS  read-write
    STATUS  current
    DESCRIPTION
        "The smallest allowable IP fragment offset."
    ::= { dosAttackPrevCfg 8 }
    
dosCurCfgSYNdata OBJECT-TYPE
    SYNTAX  INTEGER(0..255)
    MAX-ACCESS  read-only
    STATUS  current
    DESCRIPTION
        "The largest allowable TCP SYN payload."
    ::= { dosAttackPrevCfg 9 }

dosNewCfgSYNdata OBJECT-TYPE
    SYNTAX  INTEGER(0..255)
    MAX-ACCESS  read-write
    STATUS  current
    DESCRIPTION
        "The largest allowable TCP SYN payload."
    ::= { dosAttackPrevCfg 10 }
    
dosCurCfgICMPdata OBJECT-TYPE
    SYNTAX  INTEGER(1..9026)
    MAX-ACCESS  read-only
    STATUS  current
    DESCRIPTION
        "The largest allowable ICMP payload."
    ::= { dosAttackPrevCfg 11 }

dosNewCfgICMPdata OBJECT-TYPE
    SYNTAX  INTEGER(1..9026)
    MAX-ACCESS  read-write
    STATUS  current
    DESCRIPTION
        "The largest allowable ICMP payload."
    ::= { dosAttackPrevCfg 12 }

dosCurCfgICMPoff OBJECT-TYPE
    SYNTAX  INTEGER(1..8190)
    MAX-ACCESS  read-only
    STATUS  current
    DESCRIPTION
        "The largest allowable ICMP fragment offset."
    ::= { dosAttackPrevCfg 13 }

dosNewCfgICMPoff OBJECT-TYPE
    SYNTAX  INTEGER(1..8190)
    MAX-ACCESS  read-write
    STATUS  current
    DESCRIPTION
        "The largest allowable ICMP fragment offset."
    ::= { dosAttackPrevCfg 14 }


-- DST_IP_ACL: IP DST Address ACL Configuration

ipDstAclTableMaxSize OBJECT-TYPE
    SYNTAX  Integer32
    MAX-ACCESS  read-only
    STATUS  current
    DESCRIPTION
        "The maximum number of rows in the DST IP ACL table."
    ::= { ipDstAclCfg 1 }

ipDstAclCurCfgTable OBJECT-TYPE
    SYNTAX  SEQUENCE OF IpDstAclCurCfgEntry
    MAX-ACCESS  not-accessible
    STATUS  current
    DESCRIPTION
        "The table of DST IP ACL in the current configuration block."
    ::= { ipDstAclCfg 2 }

ipDstAclCurCfgEntry OBJECT-TYPE
    SYNTAX  IpDstAclCurCfgEntry
    MAX-ACCESS  not-accessible
    STATUS  current
    DESCRIPTION
        "A row in the DST IP ACL table"
    INDEX   { ipDstAclCurCfgIndx }
    ::= { ipDstAclCurCfgTable 1 }

IpDstAclCurCfgEntry ::= SEQUENCE {
    ipDstAclCurCfgIndx             Integer32,
    ipDstAclCurCfgIp               IpAddress,
    ipDstAclCurCfgMask             IpAddress
    }

ipDstAclCurCfgIndx OBJECT-TYPE
    SYNTAX  Integer32
    MAX-ACCESS  read-only
    STATUS  current
    DESCRIPTION
        "The index of the DST IP ACL table."
    ::= { ipDstAclCurCfgEntry 1}

ipDstAclCurCfgIp OBJECT-TYPE
    SYNTAX  IpAddress
    MAX-ACCESS  read-only
    STATUS  current
    DESCRIPTION
        "The IP address of the entry."
    ::= { ipDstAclCurCfgEntry 2}

ipDstAclCurCfgMask OBJECT-TYPE 
    SYNTAX  IpAddress
    MAX-ACCESS  read-only 
    STATUS  current 
    DESCRIPTION 
        "The IP address Mask of the entry."
    ::= { ipDstAclCurCfgEntry 3}

ipDstAclNewCfgTable OBJECT-TYPE
    SYNTAX  SEQUENCE OF IpDstAclNewCfgEntry
    MAX-ACCESS  not-accessible
    STATUS  current
    DESCRIPTION
        "The table of DST IP ACL in the new configuration block."
    ::= { ipDstAclCfg 3 }

ipDstAclNewCfgEntry OBJECT-TYPE
    SYNTAX  IpDstAclNewCfgEntry
    MAX-ACCESS  not-accessible
    STATUS  current
    DESCRIPTION
        "A row in the DST IP ACL table"
    INDEX   { ipDstAclNewCfgIndx }
    ::= { ipDstAclNewCfgTable 1 }

IpDstAclNewCfgEntry ::= SEQUENCE {
    ipDstAclNewCfgIndx             Integer32,
    ipDstAclNewCfgIp               IpAddress,
    ipDstAclNewCfgAction           INTEGER,
    ipDstAclNewCfgMask             IpAddress
    }

ipDstAclNewCfgIndx OBJECT-TYPE
    SYNTAX  Integer32
    MAX-ACCESS  read-only
    STATUS  current
    DESCRIPTION
        "The index of the DST IP ACL table."
    ::= { ipDstAclNewCfgEntry 1}

ipDstAclNewCfgIp OBJECT-TYPE
    SYNTAX  IpAddress
    MAX-ACCESS  read-create
    STATUS  current
    DESCRIPTION
        "The IP address of the entry."
    ::= { ipDstAclNewCfgEntry 2}

ipDstAclNewCfgAction OBJECT-TYPE
    SYNTAX  INTEGER {
        other(1),
        delete(2)
       }  
    MAX-ACCESS  read-create
    STATUS  current
    DESCRIPTION
        "When set to the value of 2 (delete), the entire row is deleted. 
         When read, other is returned. Setting the value to anything other 
         than 2(delete) has no effect on the state of the row."
    ::= { ipDstAclNewCfgEntry 3 }

ipDstAclNewCfgMask OBJECT-TYPE 
    SYNTAX  IpAddress
    MAX-ACCESS  read-create
    STATUS  current 
    DESCRIPTION 
        "The IP address Mask of the entry."
    ::= { ipDstAclNewCfgEntry 4}

--
-- Symantec Signature ID - BWM Contract - Policy Action Association Table.
--
symSigBwmMappingTableMaxSize OBJECT-TYPE
    SYNTAX Integer32
    MAX-ACCESS read-only
    STATUS current
    DESCRIPTION
        "The maximum number of entries in the Symantec Signature ID- 
         BWM contract-Policy Mapping Table."
    ::= { symantecCfg 1 }

symCurCfgSigBwmMappingTable OBJECT-TYPE
    SYNTAX  SEQUENCE OF SymCurCfgSigBwmMappingTableEntry
    MAX-ACCESS  not-accessible
    STATUS  current
    DESCRIPTION
        "The Symantec Signature ID-BWM Contract-Policy Mapping table."
    ::= { symantecCfg 2 }

symCurCfgSigBwmMappingTableEntry OBJECT-TYPE
    SYNTAX  SymCurCfgSigBwmMappingTableEntry
    MAX-ACCESS  not-accessible
    STATUS  current
    DESCRIPTION
        "A row in the Symantec Signature ID-BWM Contract-Policy Mapping 
	 table."
    INDEX   { symCurCfgTblIndex }
    ::= { symCurCfgSigBwmMappingTable 1 }

SymCurCfgSigBwmMappingTableEntry ::= SEQUENCE {
    symCurCfgTblIndex		    Integer32,
    symCurCfgSignatureID            Integer32,
    symCurCfgInContractID           Integer32,
    symCurCfgOutContractID          Integer32
    }

symCurCfgTblIndex  OBJECT-TYPE
    SYNTAX  Integer32
    MAX-ACCESS  read-only
    STATUS  current
    DESCRIPTION
        "The Table Index."
    ::= { symCurCfgSigBwmMappingTableEntry 1 }

symCurCfgSignatureID  OBJECT-TYPE
    SYNTAX  Integer32
    MAX-ACCESS  read-only
    STATUS  current
    DESCRIPTION
        "The Symantec Signature ID."
    ::= { symCurCfgSigBwmMappingTableEntry 2 }

symCurCfgInContractID  OBJECT-TYPE
    SYNTAX  Integer32
    MAX-ACCESS  read-only
    STATUS  current
    DESCRIPTION
        "The BWM In-Contrat ID associated with the Signature ID."
    ::= { symCurCfgSigBwmMappingTableEntry 3 }

symCurCfgOutContractID  OBJECT-TYPE
    SYNTAX  Integer32
    MAX-ACCESS  read-only
    STATUS  current
    DESCRIPTION
        "The BWM Out-Contrat ID associated with the Signature ID."
    ::= { symCurCfgSigBwmMappingTableEntry 4 }

symNewCfgSigBwmMappingTable OBJECT-TYPE
    SYNTAX  SEQUENCE OF SymNewCfgSigBwmMappingTableEntry
    MAX-ACCESS  not-accessible
    STATUS  current
    DESCRIPTION
        "The Symantec Signature ID-BWM Contract-Policy Mapping table."
    ::= { symantecCfg 3 }

symNewCfgSigBwmMappingTableEntry OBJECT-TYPE
    SYNTAX  SymNewCfgSigBwmMappingTableEntry
    MAX-ACCESS  not-accessible
    STATUS  current
    DESCRIPTION
        "A row in the Symantec Signature ID-BWM Contract-Policy Mapping
	 table."
    INDEX   { symNewCfgTblIndex }
    ::= { symNewCfgSigBwmMappingTable 1 }

SymNewCfgSigBwmMappingTableEntry ::= SEQUENCE {
    symNewCfgTblIndex		    Integer32,
    symNewCfgSignatureID            Integer32,
    symNewCfgInContractID           Integer32,
    symNewCfgOutContractID          Integer32,
    symNewCfgDeleteEntry	    INTEGER
    }

symNewCfgTblIndex  OBJECT-TYPE
    SYNTAX  Integer32
    MAX-ACCESS  read-only
    STATUS  current
    DESCRIPTION
        "The Table Index."
    ::= { symNewCfgSigBwmMappingTableEntry 1 }

symNewCfgSignatureID  OBJECT-TYPE
    SYNTAX  Integer32
    MAX-ACCESS  read-create
    STATUS  current
    DESCRIPTION
        "The Symantec Signature ID."
    ::= { symNewCfgSigBwmMappingTableEntry 2 }

symNewCfgInContractID  OBJECT-TYPE
    SYNTAX  Integer32
    MAX-ACCESS  read-create
    STATUS  current
    DESCRIPTION
        "The BWM In-Contrat ID associated with the Signature ID."
    ::= { symNewCfgSigBwmMappingTableEntry 3 }

symNewCfgOutContractID  OBJECT-TYPE
    SYNTAX  Integer32
    MAX-ACCESS  read-create
    STATUS  current
    DESCRIPTION
        "The BWM Out-Contrat ID associated with the Signature ID."
    ::= { symNewCfgSigBwmMappingTableEntry 4 }

symNewCfgDeleteEntry  OBJECT-TYPE
    SYNTAX  INTEGER {
        others(1),
        delete(2)
        }
    MAX-ACCESS  read-create
    STATUS  current
    DESCRIPTION
        "Delete an table entry."
    ::= { symNewCfgSigBwmMappingTableEntry 5 }

symNewCfgDefaultAction OBJECT-TYPE
    SYNTAX INTEGER { 
	allow(1),
	deny(2)
        }
    MAX-ACCESS read-create 
    STATUS  current
    DESCRIPTION
        "The default action to be taken during LiveUpdate." 
    ::= { symantecCfg 4 }

symCurCfgDefaultAction OBJECT-TYPE
    SYNTAX INTEGER { 
	allow(1),
	deny(2)
        }
    MAX-ACCESS read-only 
    STATUS  current
    DESCRIPTION
        "The default action to be taken during LiveUpdate." 
    ::= { symantecCfg 5 }

symSigFileVersionSeqNumber OBJECT-TYPE
    SYNTAX  Integer32 
    MAX-ACCESS  read-create
    STATUS  current
    DESCRIPTION
        "Symantec Signature File version sequence."
    ::= { symantecCfg 6 }

--
-- Security Port statistics table
--
agDosPortStatsTable OBJECT-TYPE
    SYNTAX  SEQUENCE OF AgDosPortStatsTableEntry
    MAX-ACCESS  not-accessible
    STATUS  current
    DESCRIPTION
        "The table of DOS port statistics."
    ::= { securityStats 1 }

agDosPortStatsTableEntry OBJECT-TYPE
    SYNTAX  AgDosPortStatsTableEntry
    MAX-ACCESS  not-accessible
    STATUS  current
    DESCRIPTION
        "A row in the port stats table."
    INDEX   { agDosPortStatsIndx }
    ::= { agDosPortStatsTable 1 }

AgDosPortStatsTableEntry ::=
    SEQUENCE {
	agDosPortStatsIndx
	    Integer32,
        agDosPortStatsIPLen
            Counter32,
        agDosPortStatsIPVersion
            Counter32,
        agDosPortStatsBroadcast
            Counter32,
        agDosPortStatsLoopback
            Counter32,
	agDosPortStatsLand
	    Counter32,
        agDosPortStatsIPReserved
            Counter32,
        agDosPortStatsIPTTL
            Counter32,
        agDosPortStatsIPProt
            Counter32,
        agDosPortStatsIPOptLen
            Counter32,
        agDosPortStatsFragMoreDont
            Counter32,
        agDosPortStatsFragData
            Counter32,
        agDosPortStatsFragBoundary
            Counter32,
        agDosPortStatsFragLast
            Counter32,
        agDosPortStatsFragDontOff
            Counter32,
        agDosPortStatsFragOpt
            Counter32,
        agDosPortStatsFragOff
            Counter32,
        agDosPortStatsFragOversize
            Counter32,
        agDosPortStatsTCPLen
            Counter32,
        agDosPortStatsTCPPortZero
            Counter32,
	agDosPortStatsBlatAttack
	    Counter32,
        agDosPortStatsTCPReserved
            Counter32,
	agDosPortStatsNullScanAttack
	    Counter32,
        agDosPortStatsFullXmasScan
            Counter32,
        agDosPortStatsFinScan
            Counter32,
        agDosPortStatsVecnaScan
            Counter32,
	agDosPortStatsXmasScanAttack
	    Counter32,
	agDosPortStatsSynFinScan
	    Counter32,
        agDosPortStatsFlagAbnormal
            Counter32,
        agDosPortStatsSYNData
            Counter32,
        agDosPortStatsSYNFrag
            Counter32,
        agDosPortStatsFTPPort
            Counter32,
        agDosPortStatsDNSPort
            Counter32,
        agDosPortStatsSeqZero
            Counter32,
        agDosPortStatsAckZero
            Counter32,
        agDosPortStatsTCPOptLen
            Counter32,
        agDosPortStatsUDPLen
            Counter32,
        agDosPortStatsUDPPortZero
            Counter32,
	agDosPortStatsFraggleAttack
	    Counter32,
        agDosPortStatsPepsi
            Counter32,
        agDosPortStatsRc8
            Counter32,
        agDosPortStatsSNMPNull
            Counter32,
        agDosPortStatsICMPLen
            Counter32,
	agDosPortStatsSmurfAttack
	    Counter32,
        agDosPortStatsICMPData
            Counter32,
        agDosPortStatsICMPOff
            Counter32,
        agDosPortStatsICMPType
            Counter32,
        agDosPortStatsIGMPLen
            Counter32,
        agDosPortStatsIGMPFrag
            Counter32,
        agDosPortStatsIGMPType
            Counter32,
        agDosPortStatsARPLen
            Counter32,
        agDosPortStatsARPNbCast
            Counter32,
        agDosPortStatsARPNuCast
            Counter32,
        agDosPortStatsARPSpoof
            Counter32,
        agDosPortStatsGARP
            Counter32,
        agDosPortStatsIP6Len
            Counter32,
        agDosPortStatsIP6Version
            Counter32
    }

agDosPortStatsIndx OBJECT-TYPE
    SYNTAX  Integer32
    MAX-ACCESS  read-only
    STATUS  current
    DESCRIPTION
        "The port index."
    ::= { agDosPortStatsTableEntry 1 }


agDosPortStatsIPLen OBJECT-TYPE
    SYNTAX  Counter32
    MAX-ACCESS  read-only
    STATUS  current
    DESCRIPTION
	"IPv4 packets with bad IP header or payload length."
    ::= { agDosPortStatsTableEntry 10 }

agDosPortStatsIPVersion OBJECT-TYPE
    SYNTAX  Counter32
    MAX-ACCESS  read-only
    STATUS  current
    DESCRIPTION
	"IPv4 packets with IP version not 4."
    ::= { agDosPortStatsTableEntry 11 }

agDosPortStatsBroadcast OBJECT-TYPE
    SYNTAX  Counter32
    MAX-ACCESS  read-only
    STATUS  current
    DESCRIPTION
	"IPv4 packets with broadcast source or destination 
	IP [0.0.0.0,255.255.255.255]."
    ::= { agDosPortStatsTableEntry 12 }

agDosPortStatsLoopback OBJECT-TYPE
    SYNTAX  Counter32
    MAX-ACCESS  read-only
    STATUS  current
    DESCRIPTION
	"IPv4 packets with loopback source or destination 
	IP [127.0.0.0/8]."
    ::= { agDosPortStatsTableEntry 13 }

agDosPortStatsLand OBJECT-TYPE
    SYNTAX  Counter32
    MAX-ACCESS  read-only
    STATUS  current
    DESCRIPTION
	"IPv4 Packets with source IP equal to destination IP."
    ::= { agDosPortStatsTableEntry 14 }

agDosPortStatsIPReserved OBJECT-TYPE
    SYNTAX  Counter32
    MAX-ACCESS  read-only
    STATUS  current
    DESCRIPTION
	"IPv4 packets with IP reserved bit is set."
    ::= { agDosPortStatsTableEntry 15 }

agDosPortStatsIPTTL OBJECT-TYPE
    SYNTAX  Counter32
    MAX-ACCESS  read-only
    STATUS  current
    DESCRIPTION
	"IPv4 packets with small IP TTL."
    ::= { agDosPortStatsTableEntry 16 }

agDosPortStatsIPProt OBJECT-TYPE
    SYNTAX  Counter32
    MAX-ACCESS  read-only
    STATUS  current
    DESCRIPTION
	"IPv4 packets with IP protocol is unassigned or reserved."
    ::= { agDosPortStatsTableEntry 17 }

agDosPortStatsIPOptLen OBJECT-TYPE
    SYNTAX  Counter32
    MAX-ACCESS  read-only
    STATUS  current
    DESCRIPTION
	"IPv4 packets with bad IP options length."
    ::= { agDosPortStatsTableEntry 18 }

agDosPortStatsFragMoreDont OBJECT-TYPE
    SYNTAX  Counter32
    MAX-ACCESS  read-only
    STATUS  current
    DESCRIPTION
	"IPv4 packets with more fragments and don't fragment bits are set."
    ::= { agDosPortStatsTableEntry 19 }

agDosPortStatsFragData OBJECT-TYPE
    SYNTAX  Counter32
    MAX-ACCESS  read-only
    STATUS  current
    DESCRIPTION
	"IPv4 packets with more fragments bit is set and small payload."
    ::= { agDosPortStatsTableEntry 20 }

agDosPortStatsFragBoundary OBJECT-TYPE
    SYNTAX  Counter32
    MAX-ACCESS  read-only
    STATUS  current
    DESCRIPTION
	"IPv4 packets with more fragments bit is set and
         payload not at 8-byte boundary."
    ::= { agDosPortStatsTableEntry 21 }

agDosPortStatsFragLast OBJECT-TYPE
    SYNTAX  Counter32
    MAX-ACCESS  read-only
    STATUS  current
    DESCRIPTION
	"IPv4 packets last fragment without payload."
    ::= { agDosPortStatsTableEntry 22 }

agDosPortStatsFragDontOff OBJECT-TYPE
    SYNTAX  Counter32
    MAX-ACCESS  read-only
    STATUS  current
    DESCRIPTION
	"IPv4 packets with non-zero fragment offset and don't 
	fragment bits are set."
    ::= { agDosPortStatsTableEntry 23 }

agDosPortStatsFragOpt OBJECT-TYPE
    SYNTAX  Counter32
    MAX-ACCESS  read-only
    STATUS  current
    DESCRIPTION
	"IPv4 packets with non-zero fragment offset and IP options."
    ::= { agDosPortStatsTableEntry 24 }

agDosPortStatsFragOff OBJECT-TYPE
    SYNTAX  Counter32
    MAX-ACCESS  read-only
    STATUS  current
    DESCRIPTION
	"IPv4 packets with small non-zero fragment offset."
    ::= { agDosPortStatsTableEntry 25 }

agDosPortStatsFragOversize OBJECT-TYPE
    SYNTAX  Counter32
    MAX-ACCESS  read-only
    STATUS  current
    DESCRIPTION
	"IPv4 packets with non-zero fragment offset and oversize payload."
    ::= { agDosPortStatsTableEntry 26 }

agDosPortStatsTCPLen OBJECT-TYPE
    SYNTAX  Counter32
    MAX-ACCESS  read-only
    STATUS  current
    DESCRIPTION
	"TCP packets with bad TCP header length."
    ::= { agDosPortStatsTableEntry 27 }

agDosPortStatsTCPPortZero OBJECT-TYPE
    SYNTAX  Counter32
    MAX-ACCESS  read-only
    STATUS  current
    DESCRIPTION
	"TCP packets with source or destination port is zero."
    ::= { agDosPortStatsTableEntry 28 }

agDosPortStatsBlatAttack OBJECT-TYPE
    SYNTAX  Counter32
    MAX-ACCESS  read-only
    STATUS  current
    DESCRIPTION
	"TCP packets source IP not equal to destination IP and source port 
	equal to destination port."
    ::= { agDosPortStatsTableEntry 29 }

agDosPortStatsTCPReserved OBJECT-TYPE
    SYNTAX  Counter32
    MAX-ACCESS  read-only
    STATUS  current
    DESCRIPTION
	"TCP packets with TCP reserved bit is set."
    ::= { agDosPortStatsTableEntry 30 }

agDosPortStatsNullScanAttack OBJECT-TYPE
    SYNTAX  Counter32
    MAX-ACCESS  read-only
    STATUS  current
    DESCRIPTION
	"TCP packets were the TCP sequence number is zero and all control 
	bits are zeroes."
    ::= { agDosPortStatsTableEntry 31 }

agDosPortStatsFullXmasScan OBJECT-TYPE
    SYNTAX  Counter32
    MAX-ACCESS  read-only
    STATUS  current
    DESCRIPTION
	"TCP packets with all control bits are set."
    ::= { agDosPortStatsTableEntry 32 }

agDosPortStatsFinScan OBJECT-TYPE
    SYNTAX  Counter32
    MAX-ACCESS  read-only
    STATUS  current
    DESCRIPTION
	"TCP packets with only FIN bit is set."
    ::= { agDosPortStatsTableEntry 33 }

agDosPortStatsVecnaScan OBJECT-TYPE
    SYNTAX  Counter32
    MAX-ACCESS  read-only
    STATUS  current
    DESCRIPTION
	"TCP packets with only URG or PUSH or URG|FIN or
         PSH|FIN or URG|PSH bits are set."
    ::= { agDosPortStatsTableEntry 34 }

agDosPortStatsXmasScanAttack OBJECT-TYPE
    SYNTAX  Counter32
    MAX-ACCESS  read-only
    STATUS  current
    DESCRIPTION
	"TCP packets were the TCP sequence number is zero and FIN, 
	URG and PSH bits are set."
    ::= { agDosPortStatsTableEntry 35 }

agDosPortStatsSynFinScan OBJECT-TYPE
    SYNTAX  Counter32
    MAX-ACCESS  read-only
    STATUS  current
    DESCRIPTION
	"TCP packets were SYN and FIN bits are set."
    ::= { agDosPortStatsTableEntry 36 }

agDosPortStatsFlagAbnormal OBJECT-TYPE
    SYNTAX  Counter32
    MAX-ACCESS  read-only
    STATUS  current
    DESCRIPTION
	"TCP packets with abnormal control bits combination."
    ::= { agDosPortStatsTableEntry 37 }

agDosPortStatsSYNData OBJECT-TYPE
    SYNTAX  Counter32
    MAX-ACCESS  read-only
    STATUS  current
    DESCRIPTION
	"TCP packets with SYN bit is set and with payload."
    ::= { agDosPortStatsTableEntry 38 }

agDosPortStatsSYNFrag OBJECT-TYPE
    SYNTAX  Counter32
    MAX-ACCESS  read-only
    STATUS  current
    DESCRIPTION
	"TCP packets with SYN bit is set and more fragments bit is set."
    ::= { agDosPortStatsTableEntry 39 }

agDosPortStatsFTPPort OBJECT-TYPE
    SYNTAX  Counter32
    MAX-ACCESS  read-only
    STATUS  current
    DESCRIPTION
	"TCP packets with SPORT=20, DPORT<1024 and SYN bit is set."
    ::= { agDosPortStatsTableEntry 40 }

agDosPortStatsDNSPort OBJECT-TYPE
    SYNTAX  Counter32
    MAX-ACCESS  read-only
    STATUS  current
    DESCRIPTION
	"TCP packets with SPORT=53, DPORT<1024 and SYN bit is set."
    ::= { agDosPortStatsTableEntry 41 }

agDosPortStatsSeqZero OBJECT-TYPE
    SYNTAX  Counter32
    MAX-ACCESS  read-only
    STATUS  current
    DESCRIPTION
	"TCP packets with sequence number is zero."
    ::= { agDosPortStatsTableEntry 42 }

agDosPortStatsAckZero OBJECT-TYPE
    SYNTAX  Counter32
    MAX-ACCESS  read-only
    STATUS  current
    DESCRIPTION
	"TCP packets with acknowledgement number is zero and 
	ACK bit is set."
    ::= { agDosPortStatsTableEntry 43 }

agDosPortStatsTCPOptLen OBJECT-TYPE
    SYNTAX  Counter32
    MAX-ACCESS  read-only
    STATUS  current
    DESCRIPTION
	"TCP packets with bad TCP options length."
    ::= { agDosPortStatsTableEntry 44 }

agDosPortStatsUDPLen OBJECT-TYPE
    SYNTAX  Counter32
    MAX-ACCESS  read-only
    STATUS  current
    DESCRIPTION
	"UDP packets with bad UDP header length."
    ::= { agDosPortStatsTableEntry 45 }

agDosPortStatsUDPPortZero OBJECT-TYPE
    SYNTAX  Counter32
    MAX-ACCESS  read-only
    STATUS  current
    DESCRIPTION
	"UDP packets with source or destination port is zero."
    ::= { agDosPortStatsTableEntry 46 }

agDosPortStatsFraggleAttack OBJECT-TYPE
    SYNTAX  Counter32
    MAX-ACCESS  read-only
    STATUS  current
    DESCRIPTION
	"UDP packets sent to a broadcast destination IP (x.x.x.255)."
    ::= { agDosPortStatsTableEntry 47 }

agDosPortStatsPepsi OBJECT-TYPE
    SYNTAX  Counter32
    MAX-ACCESS  read-only
    STATUS  current
    DESCRIPTION
	"UDP packets with SPORT=19, DPORT=7 or SPORT=7, DPORT=19."
    ::= { agDosPortStatsTableEntry 48 }

agDosPortStatsRc8 OBJECT-TYPE
    SYNTAX  Counter32
    MAX-ACCESS  read-only
    STATUS  current
    DESCRIPTION
        "UDP packets with SPORT=7 and DPORT=7."
    ::= { agDosPortStatsTableEntry 49 }

agDosPortStatsSNMPNull OBJECT-TYPE
    SYNTAX  Counter32
    MAX-ACCESS  read-only
    STATUS  current
    DESCRIPTION
	"UDP packets with DPORT=161 and without payload."
    ::= { agDosPortStatsTableEntry 50 }

agDosPortStatsICMPLen OBJECT-TYPE
    SYNTAX  Counter32
    MAX-ACCESS  read-only
    STATUS  current
    DESCRIPTION
	"ICMP packets with bad ICMP header length."
    ::= { agDosPortStatsTableEntry 51 }

agDosPortStatsSmurfAttack OBJECT-TYPE
    SYNTAX  Counter32
    MAX-ACCESS  read-only
    STATUS  current
    DESCRIPTION
	"ICMP ping request to a broadcast destination IP x.x.x.255."
    ::= { agDosPortStatsTableEntry 52 }

agDosPortStatsICMPData OBJECT-TYPE
    SYNTAX  Counter32
    MAX-ACCESS  read-only
    STATUS  current
    DESCRIPTION
	"ICMP packets with non-zero fragment offset and large payload."
    ::= { agDosPortStatsTableEntry 53 }

agDosPortStatsICMPOff OBJECT-TYPE
    SYNTAX  Counter32
    MAX-ACCESS  read-only
    STATUS  current
    DESCRIPTION
        "ICMP packets with large fragment offset."
    ::= { agDosPortStatsTableEntry 54 }

agDosPortStatsICMPType OBJECT-TYPE
    SYNTAX  Counter32
    MAX-ACCESS  read-only
    STATUS  current
    DESCRIPTION
        "ICMP packets with type is reserved."
    ::= { agDosPortStatsTableEntry 55 }

agDosPortStatsIGMPLen OBJECT-TYPE
    SYNTAX  Counter32
    MAX-ACCESS  read-only
    STATUS  current
    DESCRIPTION
	"IGMP packets with bad IGMP header length."
    ::= { agDosPortStatsTableEntry 56 }

agDosPortStatsIGMPFrag OBJECT-TYPE
    SYNTAX  Counter32
    MAX-ACCESS  read-only
    STATUS  current
    DESCRIPTION
	"IGMP packets with more fragments bit is set."
    ::= { agDosPortStatsTableEntry 57 }

agDosPortStatsIGMPType OBJECT-TYPE
    SYNTAX  Counter32
    MAX-ACCESS  read-only
    STATUS  current
    DESCRIPTION
        "IGMP packets with type is reserved."
    ::= { agDosPortStatsTableEntry 58 }

agDosPortStatsARPLen OBJECT-TYPE
    SYNTAX  Counter32
    MAX-ACCESS  read-only
    STATUS  current
    DESCRIPTION
	"ARP request or reply packets with bad length."
    ::= { agDosPortStatsTableEntry 59 }

agDosPortStatsARPNbCast OBJECT-TYPE
    SYNTAX  Counter32
    MAX-ACCESS  read-only
    STATUS  current
    DESCRIPTION
	"ARP request packets with non broadcast destination MAC."
    ::= { agDosPortStatsTableEntry 60 }

agDosPortStatsARPNuCast OBJECT-TYPE
    SYNTAX  Counter32
    MAX-ACCESS  read-only
    STATUS  current
    DESCRIPTION
        "ARP reply packets with non unicast destination MAC."
    ::= { agDosPortStatsTableEntry 61 }

agDosPortStatsARPSpoof OBJECT-TYPE
    SYNTAX  Counter32
    MAX-ACCESS  read-only
    STATUS  current
    DESCRIPTION
	"ARP request or reply packets with mismatch source with
	 sender MACs or destination with target MACs."
    ::= { agDosPortStatsTableEntry 62 }

agDosPortStatsGARP OBJECT-TYPE
    SYNTAX  Counter32
    MAX-ACCESS  read-only
    STATUS  current
    DESCRIPTION
        "ARP request or reply packets with same
         source and destination IP."
    ::= { agDosPortStatsTableEntry 63 }

agDosPortStatsIP6Len OBJECT-TYPE
    SYNTAX  Counter32
    MAX-ACCESS  read-only
    STATUS  current
    DESCRIPTION
	"IPv6 packets with bad header length."
    ::= { agDosPortStatsTableEntry 64 }

agDosPortStatsIP6Version OBJECT-TYPE
    SYNTAX  Counter32
    MAX-ACCESS  read-only
    STATUS  current
    DESCRIPTION
	"IPv6 packets with IP version not 6."
    ::= { agDosPortStatsTableEntry 65 }

agSecurityPgrpStatsTable OBJECT-TYPE
    SYNTAX  SEQUENCE OF AgSecurityPgrpStatsTableEntry
    MAX-ACCESS  not-accessible
    STATUS  current
    DESCRIPTION
        "The table of pattern group statistics."
    ::= { securityStats 2 }

agSecurityPgrpStatsTableEntry OBJECT-TYPE
    SYNTAX  AgSecurityPgrpStatsTableEntry
    MAX-ACCESS  not-accessible
    STATUS  current
    DESCRIPTION
        "A row in the port stats table."
    INDEX   { agSecurityPgrpStatsIndx }
    ::= { agSecurityPgrpStatsTable 1 }

AgSecurityPgrpStatsTableEntry ::=
    SEQUENCE {
	agSecurityPgrpStatsIndx
	    Integer32,
	agSecurityPgrpStatsName
	    DisplayString,
	agSecurityPgrpStatsHits
	    Counter32
}

agSecurityPgrpStatsIndx OBJECT-TYPE
    SYNTAX  Integer32  
    MAX-ACCESS  read-only
    STATUS  current
    DESCRIPTION
        "The Pattern Group index."
    ::= { agSecurityPgrpStatsTableEntry 1 }

agSecurityPgrpStatsName OBJECT-TYPE
    SYNTAX  DisplayString
    MAX-ACCESS  read-only
    STATUS  current
    DESCRIPTION
	    "The name of the Pattern Group."
    ::= { agSecurityPgrpStatsTableEntry 2 }

agSecurityPgrpStatsHits OBJECT-TYPE
    SYNTAX  Counter32
    MAX-ACCESS  read-only
    STATUS  current
    DESCRIPTION
	    "The total hits for this Pattern Group."
    ::= { agSecurityPgrpStatsTableEntry 3 }

-- UDP_BLAST statistics
agSecurityUbStatsTable OBJECT-TYPE
    SYNTAX  SEQUENCE OF AgSecurityUbStatsTableEntry
    MAX-ACCESS  not-accessible
    STATUS  current
    DESCRIPTION
        "The table of UDP Blast statistics."
    ::= { securityStats 3 }

agSecurityUbStatsTableEntry OBJECT-TYPE
    SYNTAX  AgSecurityUbStatsTableEntry
    MAX-ACCESS  not-accessible
    STATUS  current
    DESCRIPTION
        "A row in the UDP Blast stats table."
    INDEX   { agSecurityUbStatsIndx }
    ::= { agSecurityUbStatsTable 1 }

AgSecurityUbStatsTableEntry ::=
    SEQUENCE {
        agSecurityUbStatsIndx
            Integer32,
        agSecurityUbStatsPort
            Integer32,
        agSecurityUbStatsBlockedPacket
            Counter32,
        agSecurityUbStatsPacketRate
            Counter32
}

agSecurityUbStatsIndx OBJECT-TYPE
    SYNTAX  Integer32 
    MAX-ACCESS  read-only
    STATUS  current
    DESCRIPTION
        "The UDP Blast Statistics Group index."
    ::= { agSecurityUbStatsTableEntry 1 }

agSecurityUbStatsPort OBJECT-TYPE
    SYNTAX  Integer32 
    MAX-ACCESS  read-only
    STATUS  current
    DESCRIPTION
            "UDP Port Number."
    ::= { agSecurityUbStatsTableEntry 2 }

agSecurityUbStatsBlockedPacket OBJECT-TYPE
    SYNTAX  Counter32 
    MAX-ACCESS  read-only
    STATUS  current
    DESCRIPTION
            "Total blocked packet."
    ::= { agSecurityUbStatsTableEntry 3 }

agSecurityUbStatsPacketRate OBJECT-TYPE
    SYNTAX  Counter32
    MAX-ACCESS  read-only
    STATUS  current
    DESCRIPTION
            "Current Packet rate per second."
    ::= { agSecurityUbStatsTableEntry 4 }


-- IP_ACL statistics
agSecurityIpAclStatsTable OBJECT-TYPE
    SYNTAX  SEQUENCE OF AgSecurityIpAclStatsTableEntry
    MAX-ACCESS  not-accessible
    STATUS  current
    DESCRIPTION
        "The table of IP ACL statistics."
    ::= { securityStats 4 }

agSecurityIpAclStatsTableEntry OBJECT-TYPE
    SYNTAX  AgSecurityIpAclStatsTableEntry
    MAX-ACCESS  not-accessible
    STATUS  current
    DESCRIPTION
        "A row in the IP ACL stats table."
    INDEX   { agSecurityIpAclStatsIndx }
    ::= { agSecurityIpAclStatsTable 1 }

AgSecurityIpAclStatsTableEntry ::=
    SEQUENCE {
        agSecurityIpAclStatsIndx
            Integer32,
        agSecurityIpAclStatsAddress
            IpAddress,
        agSecurityIpAclStatsBlockedPacket
            Counter32
}

agSecurityIpAclStatsIndx OBJECT-TYPE
    SYNTAX  Integer32  
    MAX-ACCESS  read-only
    STATUS  current
    DESCRIPTION
        "The IP ACL Statistics Group index."
    ::= { agSecurityIpAclStatsTableEntry 1 }

agSecurityIpAclStatsAddress OBJECT-TYPE
    SYNTAX  IpAddress 
    MAX-ACCESS  read-only
    STATUS  current
    DESCRIPTION
            "IP ACL IP Address."
    ::= { agSecurityIpAclStatsTableEntry 2 }

agSecurityIpAclStatsBlockedPacket OBJECT-TYPE
    SYNTAX  Counter32 
    MAX-ACCESS  read-only
    STATUS  current
    DESCRIPTION
            "Total blocked packet."
    ::= { agSecurityIpAclStatsTableEntry 3 }

-- DST_IP_ACL statistics
agSecurityIpDstAclStatsTable OBJECT-TYPE
    SYNTAX  SEQUENCE OF AgSecurityIpDstAclStatsTableEntry
    MAX-ACCESS  not-accessible
    STATUS  current
    DESCRIPTION
        "The table of DST IP ACL statistics."
    ::= { securityStats 5 }

agSecurityIpDstAclStatsTableEntry OBJECT-TYPE
    SYNTAX  AgSecurityIpDstAclStatsTableEntry
    MAX-ACCESS  not-accessible
    STATUS  current
    DESCRIPTION
        "A row in the DST IP ACL stats table."
    INDEX   { agSecurityIpDstAclStatsIndx }
    ::= { agSecurityIpDstAclStatsTable 1 }

AgSecurityIpDstAclStatsTableEntry ::=
    SEQUENCE {
        agSecurityIpDstAclStatsIndx
            Integer32,
        agSecurityIpDstAclStatsAddress
            IpAddress,
        agSecurityIpDstAclStatsBlockedPacket
            Counter32
}

agSecurityIpDstAclStatsIndx OBJECT-TYPE
    SYNTAX  Integer32  
    MAX-ACCESS  read-only
    STATUS  current
    DESCRIPTION
        "The DST IP ACL Statistics Group index."
    ::= { agSecurityIpDstAclStatsTableEntry 1 }

agSecurityIpDstAclStatsAddress OBJECT-TYPE
    SYNTAX  IpAddress 
    MAX-ACCESS  read-only
    STATUS  current
    DESCRIPTION
            "DST IP ACL IP Address."
    ::= { agSecurityIpDstAclStatsTableEntry 2 }

agSecurityIpDstAclStatsBlockedPacket OBJECT-TYPE
    SYNTAX  Counter32 
    MAX-ACCESS  read-only
    STATUS  current
    DESCRIPTION
            "Total blocked packet."
    ::= { agSecurityIpDstAclStatsTableEntry 3 }

-- Symantec Stats Symhits
symantecStats OBJECT IDENTIFIER ::= { securityStats 6 }

symStatsTotalHits OBJECT-TYPE
    SYNTAX Counter32
    MAX-ACCESS  read-only
    STATUS  current
    DESCRIPTION
        "Total number of Symantec Hits."
    ::= { symantecStats 1 }

symStatsClear OBJECT-TYPE
    SYNTAX INTEGER  {
	ok(1),
	clear(2)
	}
    MAX-ACCESS  read-write
    STATUS  current
    DESCRIPTION
        "Clear Symantec hit stats."
    ::= { symantecStats 2 }

symStatsSourceIp OBJECT-TYPE
    SYNTAX IpAddress 
    MAX-ACCESS  read-only
    STATUS  current
    DESCRIPTION
        "Source IP Address of the last hit."
    ::= { symantecStats 3 }

symStatsSourcePort OBJECT-TYPE
    SYNTAX Integer32 
    MAX-ACCESS  read-only
    STATUS  current
    DESCRIPTION
        "Source Port of the last hit."
    ::= { symantecStats 4 }

symStatsDestIp OBJECT-TYPE
    SYNTAX IpAddress 
    MAX-ACCESS  read-only
    STATUS  current
    DESCRIPTION
        "Destination IP Address of the lsat hit."
    ::= { symantecStats 5 }

symStatsDestPort OBJECT-TYPE
    SYNTAX Integer32 
    MAX-ACCESS  read-only
    STATUS  current
    DESCRIPTION
        "Destination Port of the last hit."
    ::= { symantecStats 6 }

symStatsProtocol OBJECT-TYPE
    SYNTAX  DisplayString (SIZE(0..16))
    MAX-ACCESS  read-only
    STATUS  current
    DESCRIPTION
        "Protocol of the last hit."
    ::= { symantecStats 7 }

symStatsLastHitId OBJECT-TYPE
    SYNTAX Integer32 
    MAX-ACCESS  read-only
    STATUS  current
    DESCRIPTION
        "Last Hit Id."
    ::= { symantecStats 8 }

symStatsConfiguredHitsMax OBJECT-TYPE
    SYNTAX Integer32
    MAX-ACCESS  read-only
    STATUS  current
    DESCRIPTION
        "Max number of entries in configured hits table and
	 configured hits count on sp table."
    ::= { symantecStats 9 }

symStatsConfiguredHitsTable OBJECT-TYPE
    SYNTAX  SEQUENCE OF SymStatsConfiguredHitsTableEntry
    MAX-ACCESS  not-accessible
    STATUS  current
    DESCRIPTION
        "Symantec configured hits stats table."
    ::= { symantecStats 10 }

symStatsConfiguredHitsTableEntry OBJECT-TYPE
    SYNTAX  SymStatsConfiguredHitsTableEntry
    MAX-ACCESS  not-accessible
    STATUS  current
    DESCRIPTION
        "A Symantec configured hits stats table entry."
    INDEX   { symStatsConfiguredHitsTblIndex }
    ::= { symStatsConfiguredHitsTable 1 }

SymStatsConfiguredHitsTableEntry ::= SEQUENCE {
   symStatsConfiguredHitsTblIndex	Integer32,
   symStatsConfiguredHitsSigId		Integer32,
   symStatsConfiguredHitsTotalSpHCount	Counter32,
   symStatsConfiguredHitsInCont		Counter32,
   symStatsConfiguredHitsOutCont	Counter32,
   symStatsConfiguredHitsLastHitTime	DisplayString
   }

symStatsConfiguredHitsTblIndex OBJECT-TYPE
    SYNTAX  Integer32
    MAX-ACCESS  read-only
    STATUS  current
    DESCRIPTION
        "The Symantec configured hits stats table index."
    ::= { symStatsConfiguredHitsTableEntry 1 }

symStatsConfiguredHitsSigId OBJECT-TYPE
    SYNTAX  Integer32
    MAX-ACCESS  read-only
    STATUS  current
    DESCRIPTION
        "Signature Id hit."
    ::= { symStatsConfiguredHitsTableEntry 2 }

symStatsConfiguredHitsTotalSpHCount OBJECT-TYPE
    SYNTAX  Counter32
    MAX-ACCESS  read-only
    STATUS  current
    DESCRIPTION
        "Total Hit Count on all SPs."
    ::= { symStatsConfiguredHitsTableEntry 3 }

symStatsConfiguredHitsInCont OBJECT-TYPE
    SYNTAX  Counter32 
    MAX-ACCESS  read-only
    STATUS  current
    DESCRIPTION
        "In-Contract used."
    ::= { symStatsConfiguredHitsTableEntry 4 }

symStatsConfiguredHitsOutCont OBJECT-TYPE
    SYNTAX  Counter32 
    MAX-ACCESS  read-only
    STATUS  current
    DESCRIPTION
        "Out-Contract used."
    ::= { symStatsConfiguredHitsTableEntry 5 }

symStatsConfiguredHitsLastHitTime OBJECT-TYPE
    SYNTAX  DisplayString (SIZE(0..128))
    MAX-ACCESS  read-only
    STATUS  current
    DESCRIPTION
        "Last hit Time."
    ::= { symStatsConfiguredHitsTableEntry 6 }

symStatsConfiguredHitsCountOnSpTable OBJECT-TYPE
    SYNTAX  SEQUENCE OF SymStatsConfiguredHitsCountOnSpTableEntry
    MAX-ACCESS  not-accessible
    STATUS  current
    DESCRIPTION
        "Symantec configured hit count Sp stats table."
    ::= { symantecStats 11 }

symStatsConfiguredHitsCountOnSpTableEntry OBJECT-TYPE
    SYNTAX  SymStatsConfiguredHitsCountOnSpTableEntry
    MAX-ACCESS  not-accessible
    STATUS  current
    DESCRIPTION
        "A Symantec configured hits stats table entry."
    INDEX   { symStatsConfiguredHitsCountOnSpTblIndex,
	      symStatsConfiguredHitsCountOnSpTblSpIndex }
    ::= { symStatsConfiguredHitsCountOnSpTable 1 }

SymStatsConfiguredHitsCountOnSpTableEntry ::= SEQUENCE {
   symStatsConfiguredHitsCountOnSpTblIndex	Integer32,
   symStatsConfiguredHitsCountOnSpTblSpIndex	Integer32,
   symStatsConfiguredHitsCountOnSpTblHitCount	Counter32
   }

symStatsConfiguredHitsCountOnSpTblIndex OBJECT-TYPE
    SYNTAX  Integer32
    MAX-ACCESS  read-only
    STATUS  current
    DESCRIPTION
        "The Symantec configured hit count SP table index."
    ::= { symStatsConfiguredHitsCountOnSpTableEntry 1 }

symStatsConfiguredHitsCountOnSpTblSpIndex OBJECT-TYPE
    SYNTAX  Integer32
    MAX-ACCESS  read-only
    STATUS  current
    DESCRIPTION
        "The Symantec configured hit count SP table SP index."
    ::= { symStatsConfiguredHitsCountOnSpTableEntry 2 }

symStatsConfiguredHitsCountOnSpTblHitCount OBJECT-TYPE
    SYNTAX  Counter32
    MAX-ACCESS  read-only
    STATUS  current
    DESCRIPTION
        "Hit Count on SP."
    ::= { symStatsConfiguredHitsCountOnSpTableEntry 3 }

symStatsUnconfiguredHitsMax OBJECT-TYPE
    SYNTAX Integer32
    MAX-ACCESS  read-only
    STATUS  current
    DESCRIPTION
        "Max number of entries in unconfigured hits table and
	 unconfigured hits count on sp table."
    ::= { symantecStats 12 }

symStatsUnconfiguredHitsTable OBJECT-TYPE
    SYNTAX  SEQUENCE OF SymStatsUnconfiguredHitsTableEntry
    MAX-ACCESS  not-accessible
    STATUS  current
    DESCRIPTION
        "Symantec unconfigured hits stats table."
    ::= { symantecStats 13 }

symStatsUnconfiguredHitsTableEntry OBJECT-TYPE
    SYNTAX  SymStatsUnconfiguredHitsTableEntry
    MAX-ACCESS  not-accessible
    STATUS  current
    DESCRIPTION
        "A Symantec unconfigured hits stats table entry."
    INDEX   { symStatsUnconfiguredHitsTblIndex }
    ::= { symStatsUnconfiguredHitsTable 1 }

SymStatsUnconfiguredHitsTableEntry ::= SEQUENCE {
   symStatsUnconfiguredHitsTblIndex		Integer32,
   symStatsUnconfiguredHitsSigId		Integer32,
   symStatsUnconfiguredHitsTotalSpHCount	Counter32,
   symStatsUnconfiguredHitsLastHitTime		DisplayString
   }

symStatsUnconfiguredHitsTblIndex OBJECT-TYPE
    SYNTAX  Integer32
    MAX-ACCESS  read-only
    STATUS  current
    DESCRIPTION
        "The Symantec unconfigured hits stats table index."
    ::= { symStatsUnconfiguredHitsTableEntry 1 }

symStatsUnconfiguredHitsSigId OBJECT-TYPE
    SYNTAX  Integer32
    MAX-ACCESS  read-only
    STATUS  current
    DESCRIPTION
        "Signature Id hit."
    ::= { symStatsUnconfiguredHitsTableEntry 2 }

symStatsUnconfiguredHitsTotalSpHCount OBJECT-TYPE
    SYNTAX  Counter32
    MAX-ACCESS  read-only
    STATUS  current
    DESCRIPTION
        "Total Hit Count on all SPs."
    ::= { symStatsUnconfiguredHitsTableEntry 3 }

symStatsUnconfiguredHitsLastHitTime OBJECT-TYPE
    SYNTAX  DisplayString (SIZE(0..128))
    MAX-ACCESS  read-only
    STATUS  current
    DESCRIPTION
        "Last hit Time."
    ::= { symStatsUnconfiguredHitsTableEntry 4 }

symStatsUnconfiguredHitsCountOnSpTable OBJECT-TYPE
    SYNTAX  SEQUENCE OF SymStatsUnconfiguredHitsCountOnSpTableEntry
    MAX-ACCESS  not-accessible
    STATUS  current
    DESCRIPTION
        "Symantec unconfigured hit count Sp stats table."
    ::= { symantecStats 14 }

symStatsUnconfiguredHitsCountOnSpTableEntry OBJECT-TYPE
    SYNTAX  SymStatsUnconfiguredHitsCountOnSpTableEntry
    MAX-ACCESS  not-accessible
    STATUS  current
    DESCRIPTION
        "A Symantec unconfigured hits stats table entry."
    INDEX   { symStatsUnconfiguredHitsCountOnSpTblIndex, 
	      symStatsUnconfiguredHitsCountOnSpTblSpIndex }
    ::= { symStatsUnconfiguredHitsCountOnSpTable 1 }

SymStatsUnconfiguredHitsCountOnSpTableEntry ::= SEQUENCE {
   symStatsUnconfiguredHitsCountOnSpTblIndex	Integer32,
   symStatsUnconfiguredHitsCountOnSpTblSpIndex	Integer32,
   symStatsUnconfiguredHitsCountOnSpTblHitCount	Counter32
   }

symStatsUnconfiguredHitsCountOnSpTblIndex OBJECT-TYPE
    SYNTAX  Integer32
    MAX-ACCESS  read-only
    STATUS  current
    DESCRIPTION
        "The Symantec unconfigured hit count SP table index."
    ::= { symStatsUnconfiguredHitsCountOnSpTableEntry 1 }

symStatsUnconfiguredHitsCountOnSpTblSpIndex OBJECT-TYPE
    SYNTAX  Integer32
    MAX-ACCESS  read-only
    STATUS  current
    DESCRIPTION
        "The Symantec unconfigured hit count SP table SP index."
    ::= { symStatsUnconfiguredHitsCountOnSpTableEntry 2 }

symStatsUnconfiguredHitsCountOnSpTblHitCount OBJECT-TYPE
    SYNTAX  Counter32
    MAX-ACCESS  read-only
    STATUS  current
    DESCRIPTION
        "Hit Count on SP."
    ::= { symStatsUnconfiguredHitsCountOnSpTableEntry 3 }

-- Scheduled Reboot Group
agCfgBootWeekday OBJECT-TYPE
    SYNTAX  INTEGER {
        sunday(1),
        monday(2),
        tuesday(3),
        wednesday(4),
        thursday(5),
        friday(6),
        saturday(7),
	none(8)
        }
    MAX-ACCESS  read-write
    STATUS  current
    DESCRIPTION
        "The day of the week for reboot." 
    ::= { agBoot 1 }

agCfgBootHour OBJECT-TYPE
    SYNTAX  INTEGER (0..23)
    MAX-ACCESS  read-write
    STATUS  current
    DESCRIPTION
        "The hour in 24-hour format for reboot." 
    ::= { agBoot 2 }

agCfgBootMin OBJECT-TYPE
    SYNTAX  INTEGER (0..59) 
    MAX-ACCESS  read-write
    STATUS  current
    DESCRIPTION
        "The minutes [00] for reboot." 
    ::= { agBoot 3 }

agCfgBootReset OBJECT-TYPE
    SYNTAX  INTEGER {
        none(1),
        cancel(2)
        }
    MAX-ACCESS  read-write
    STATUS  current
    DESCRIPTION
        "Cancel pending switch reset."
    ::= { agBoot 4 }

agCfgBootNxtResetTime OBJECT-TYPE
    SYNTAX  DisplayString (SIZE(0..255))
    MAX-ACCESS  read-only
    STATUS  current
    DESCRIPTION
        "Display the next scheduled reboot time."
     ::= { agBoot 5 }

-- Port access

agPortAccessTableMaxSize OBJECT-TYPE
    SYNTAX  Integer32
    MAX-ACCESS  read-only
    STATUS  current
    DESCRIPTION
        "The maximum number of entries in Port Access Table."
    ::= { agPortAccessCfg 1 }

agCurCfgPortAccessTable OBJECT-TYPE
    SYNTAX  SEQUENCE OF AgCurCfgPortAccessEntry
    MAX-ACCESS  not-accessible
    STATUS  current
    DESCRIPTION
       "The table of ports and their access states"
    ::= { agPortAccessCfg 2 }

agCurCfgPortAccessEntry OBJECT-TYPE
    SYNTAX  AgCurCfgPortAccessEntry
    MAX-ACCESS  not-accessible
    STATUS  current
    DESCRIPTION
        "A row in the port access table"
    INDEX   { agCurCfgPortAccessIndex }
    ::= { agCurCfgPortAccessTable 1 }

AgCurCfgPortAccessEntry ::= SEQUENCE {
    agCurCfgPortAccessIndex           Integer32,
    agCurCfgPortAccessState           INTEGER
    }

agCurCfgPortAccessIndex OBJECT-TYPE
    SYNTAX  Integer32
    MAX-ACCESS  read-only
    STATUS  current
    DESCRIPTION
        "The port number in the table."
    ::= { agCurCfgPortAccessEntry 1 }

agCurCfgPortAccessState OBJECT-TYPE
    SYNTAX  INTEGER {
        deny(0),
        allow(1)
        }
    MAX-ACCESS  read-only
    STATUS  current
    DESCRIPTION
        "The port access state of the port.
         deny(0)            - port does not have management access
         allow(1)           - port has management access"
    ::= { agCurCfgPortAccessEntry 2 }

agNewCfgPortAccessTable OBJECT-TYPE
    SYNTAX  SEQUENCE OF AgNewCfgPortAccessEntry
    MAX-ACCESS  not-accessible
    STATUS  current
    DESCRIPTION
        "The table of ports and their access states"
    ::= { agPortAccessCfg 3 }

agNewCfgPortAccessEntry OBJECT-TYPE
    SYNTAX  AgNewCfgPortAccessEntry
    MAX-ACCESS  not-accessible
    STATUS  current
    DESCRIPTION
        "A row in the port access table."
    INDEX   { agNewCfgPortAccessIndex }
    ::= { agNewCfgPortAccessTable 1 }

AgNewCfgPortAccessEntry ::= SEQUENCE {
    agNewCfgPortAccessIndex           Integer32,
    agNewCfgPortAccessState           INTEGER
    }

agNewCfgPortAccessIndex OBJECT-TYPE
    SYNTAX  Integer32
    MAX-ACCESS  read-only
    STATUS  current
    DESCRIPTION
        "The port number in the table."
    ::= { agNewCfgPortAccessEntry 1 }

agNewCfgPortAccessState OBJECT-TYPE
    SYNTAX  INTEGER {
        deny(0),
        allow(1)
        }
    MAX-ACCESS  read-write
    STATUS  current
    DESCRIPTION
        "The port access state of the port.
         deny(0)            - port does not have management access
         allow(1)           - port has management access"
    ::= { agNewCfgPortAccessEntry 2 }

-- SAVE Configuration

agSaveConfig OBJECT-TYPE
    SYNTAX  INTEGER {
        save(1),
        idle(2),
        inprogress(3),
        complete(4),
        failed(5),
	saveNoBackup(6)
        }
    MAX-ACCESS  read-write
    STATUS  current
    DESCRIPTION
        "When this object is read the current state is returned.
        idle(2) indicates that there is no save in progess.
        complete(4) indicates that the last save operation is completed.
        Setting the value to save(1), will write the current config block
        since the last save to the flash memory with backup, for saving 
	without backup saveNoBackup(6) can be used.
	If the save is successful this variable will return the state
        'complete' else it will return 'failed'. In case of failure,
        to read the reason for failure use the agSaveTable.
        Once the operation is completed or the agSaveTable is read ,
        the save buffer needs to be freed and the agSaveState
        should be set back to 'idle' state so others can issue the save
        command via SNMP."
    ::= { agSave 1 }

agSaveTableSize OBJECT-TYPE
    SYNTAX  Integer32
    MAX-ACCESS  read-only
    STATUS  current
    DESCRIPTION
        "The number of strings in the save table."
    ::= { agSave 2 }

agSaveTable OBJECT-TYPE
    SYNTAX  SEQUENCE OF AgSaveTableEntry
    MAX-ACCESS  not-accessible
    STATUS  current
    DESCRIPTION
        "The table of error messages for asynchrnous save operation."
    ::= { agSave 3 }

agSaveTableEntry OBJECT-TYPE
    SYNTAX  AgSaveTableEntry
    MAX-ACCESS  not-accessible
    STATUS  current
    DESCRIPTION
        "Error Strings generated while asynchronous save operation."
    INDEX   { agSaveIndex }
    ::= { agSaveTable 1 }

AgSaveTableEntry ::= SEQUENCE {
    agSaveIndex      Integer32,
    agSaveString     OCTET STRING
    }

agSaveIndex OBJECT-TYPE
    SYNTAX  Integer32
    MAX-ACCESS  read-only
    STATUS  current
    DESCRIPTION
        "The table index for save."
    ::= { agSaveTableEntry 1 }

agSaveString OBJECT-TYPE
    SYNTAX  OCTET STRING
    MAX-ACCESS  read-only
    STATUS  current
    DESCRIPTION
        "A string in the Save table."
    ::= { agSaveTableEntry 2 }

-- SNMP File Transfer
agFileSize OBJECT-TYPE
    SYNTAX  Integer32 
    MAX-ACCESS  read-write
    STATUS  current
    DESCRIPTION
        "This is the number of octets in the file. This is set to indicate
        the total size of the file that is being transfered. The value is 
	set in bytes. File size range for Bogon File Transfer 1 - 2097152 
        and for Symantec Signature 1 - 178176"
    ::= { agFileTransfer 1 }

agFileTransferState OBJECT-TYPE
    SYNTAX  INTEGER {
        idle(1),
        transfer(2),
        inprogress(3),
	missingrows(4),
        complete(5),
	error(6),
	endoftransfer(7)
        }
    MAX-ACCESS  read-write
    STATUS  current
    DESCRIPTION
        "When this object is read the current state is returned.
        idle(1) indicates that there is no transfer in progess.
        Any user must verify the state machine is in state idle before
        setting the state to transfer(2).Before setting transfer(2) state 
        agFileSize and agFileType should be set and then transition
        changes to inprogress(3). While in this state, the agFileTable
        should be populated with all the rows needed to transfer the files
        entire contents. endoftransfer(7) should be set inorder to notify
	the agent that contents are transfered. If all the contents are 
	received, then the state transitions to complete(5). If there are 
        any missing rows, the agent will transition to the state
        missingrows(4). The user must either populate the missing rows,
        and give a endoftransfer(7) state, or give up the transfer by
        setting the state to idle(1). When the idle(1) state is set,
        the string with missing rows is cleared and the buffer is written
        to the file, state goes complete(5) to upon successful completion.
	Any transition to idle(1) will free any resources associated with
	the file transfer, that are no longer needed. The agFileTable will 
	contain 0 rows. While in state missingrows(4), agFileTableMissingRows
	will contain a parseable string of missing row indexes seperated
	by a comma."
    ::= { agFileTransfer 2 }

agFileTableMissingRows OBJECT-TYPE
    SYNTAX OCTET STRING (SIZE(0..1024)) 
    MAX-ACCESS  read-only
    STATUS  current
    DESCRIPTION
        "A string representing the missing rows of data for the file
        transfer. This is only valid while agFileTransferState is
        in the missingrows(4) state. The string will be numbers 
	representing the missing row indexes seperated by
        commas e.g.  13,25,99"
    ::= { agFileTransfer 3 }

agFileType OBJECT-TYPE
    SYNTAX  INTEGER {
        bogon(1),
        symantecSignature(2)
        }
    MAX-ACCESS  read-write
    STATUS  current
    DESCRIPTION
        "This identifies the file type that is being transfered."
    ::= { agFileTransfer 4 }


agFileTableSize OBJECT-TYPE
    SYNTAX  Integer32
    MAX-ACCESS  read-only
    STATUS  current
    DESCRIPTION
        "The number of rows in the file table."
    ::= { agFileTransfer 5 }

agFileTable OBJECT-TYPE
    SYNTAX  SEQUENCE OF AgFileTableEntry
    MAX-ACCESS  not-accessible
    STATUS  current
    DESCRIPTION
        "The table of octets that when combined create a file."
    ::= { agFileTransfer 6 }

agFileTableEntry OBJECT-TYPE
    SYNTAX  AgFileTableEntry
    MAX-ACCESS  not-accessible
    STATUS  current
    DESCRIPTION
        "An entry in the file table."
    INDEX   { agFileIndex }
    ::= { agFileTable 1 }

AgFileTableEntry ::= SEQUENCE {
    agFileIndex      Integer32,
    agFileString     OCTET STRING
    }

agFileIndex OBJECT-TYPE
    SYNTAX  Integer32
    MAX-ACCESS  read-only
    STATUS  current
    DESCRIPTION
        "The table index."
    ::= { agFileTableEntry 1 }

agFileString OBJECT-TYPE
    SYNTAX  OCTET STRING (SIZE(0..1024))
    MAX-ACCESS  read-write
    STATUS  current
    DESCRIPTION
        "A string with bogon ip/mask pair."
    ::= { agFileTableEntry 2 }
-- End of SNMP FT

agFileErrorTableSize OBJECT-TYPE
    SYNTAX  Integer32
    MAX-ACCESS  read-only
    STATUS  current
    DESCRIPTION
        "The number of strings in the snmp file transfer error table."
    ::= { agFileTransfer 7 }

agFileErrorTable OBJECT-TYPE
    SYNTAX  SEQUENCE OF AgFileErrorTableEntry
    MAX-ACCESS  not-accessible
    STATUS  current
    DESCRIPTION
        "The table of error messages for asynchrnous snmp file transfer
       operation."
    ::= { agFileTransfer 8 }

agFileErrorTableEntry OBJECT-TYPE
    SYNTAX  AgFileErrorTableEntry
    MAX-ACCESS  not-accessible
    STATUS  current
    DESCRIPTION
        "Error Strings generated while asynchronous snmp file transfer
       operation."
    INDEX   { agFileErrorIndex }
    ::= { agFileErrorTable 1 }

AgFileErrorTableEntry ::= SEQUENCE {
    agFileErrorIndex      Integer32,
    agFileErrorString     DisplayString 
    }

agFileErrorIndex OBJECT-TYPE
    SYNTAX  Integer32
    MAX-ACCESS  read-only
    STATUS  current
    DESCRIPTION
        "The table index for snmp file transfer error table."
    ::= { agFileErrorTableEntry 1 }

agFileErrorString OBJECT-TYPE
    SYNTAX  DisplayString  
    MAX-ACCESS  read-only
    STATUS  current
    DESCRIPTION
        "A string in the snmp file transfer error table."
    ::= { agFileErrorTableEntry 2 }




-- Statistics Group

-- Packet Statistics Group
-- This group represents Packet Statistics information

pktStatsAllocs OBJECT-TYPE
    SYNTAX  Counter32
    MAX-ACCESS  read-only
    STATUS  current
    DESCRIPTION
        "Total number of packet allocations from the packet buffer pool by 
         the TCP/IP protocol stack."
    ::= { pktStats 1 }
 
pktStatsFrees OBJECT-TYPE
    SYNTAX  Counter32
    MAX-ACCESS  read-only
    STATUS  current
    DESCRIPTION
        "Total number of times the packet buffers are freed(released) to the
         packet buffer pool by the TCP/IP protocol stack."
    ::= { pktStats 2 }
 
pktStatsAllocFails OBJECT-TYPE
    SYNTAX  Counter32
    MAX-ACCESS  read-only
    STATUS  current
    DESCRIPTION
        "Total number of packet allocation failures from the packet buffer 
         pool by the TCP/IP protocol stack."
    ::= { pktStats 3}
 
pktStatsMediums OBJECT-TYPE
    SYNTAX  Gauge32
    MAX-ACCESS  read-only
    STATUS  current
    DESCRIPTION
        "Total number of packet allocations with size greater than 128 bytes
         and less than or equal to 1536 bytes from the packet buffer pool by 
         the TCP/IP protocol stack."
    ::= { pktStats 4}

pktStatsJumbos OBJECT-TYPE
    SYNTAX  Gauge32
    MAX-ACCESS  read-only
    STATUS  current
    DESCRIPTION
        "Total number of packet allocations with size larger than 1536 bytes 
         from the packet buffer pool by the TCP/IP protocol stack."
    ::= { pktStats 5}
 
pktStatsSmalls OBJECT-TYPE
    SYNTAX  Gauge32
    MAX-ACCESS  read-only
    STATUS  current
    DESCRIPTION
        "Total number of packet allocations with size less than or eqaul to 
         128 bytes from the packet buffer pool by the TCP/IP protocol stack."
    ::= { pktStats 6}

pktStatsMediumsHiWatermark OBJECT-TYPE
    SYNTAX  Counter32
    MAX-ACCESS  read-only
    STATUS  current
    DESCRIPTION
        "The highest number of packet allocations with size greater than 
         128 bytes and less than or equal to 1536 bytes from the packet 
         buffer pool by the TCP/IP protocol stack."
    ::= { pktStats 7}

pktStatsJumbosHiWatermark OBJECT-TYPE
    SYNTAX  Counter32
    MAX-ACCESS  read-only
    STATUS  current
    DESCRIPTION
        "The highest number of packet allocations with size larger than 
         1536 bytes from the packet buffer pool by the TCP/IP protocol stack."
    ::= { pktStats 8}

pktStatsSmallsHiWatermark OBJECT-TYPE
    SYNTAX  Counter32
    MAX-ACCESS  read-only
    STATUS  current
    DESCRIPTION
        "The highest number of packet allocations with size less than or 
         eqaul to 128 bytes from the packet buffer pool by the TCP/IP 
         protocol stack."
    ::= { pktStats 9}

pktStatsDiscards OBJECT-TYPE
    SYNTAX  Counter32
    MAX-ACCESS  read-only
    STATUS  current
    DESCRIPTION
        "The total number of packets which were chosen to be discarded because 
         the number of buffers available in the packet buffer pool is low."
    ::= { pktStats 10}
 
-- MP CPU Statisitics Group
 
mpCpuStatsUtil1Second OBJECT-TYPE
    SYNTAX  Integer32 
    MAX-ACCESS  read-only
    STATUS  current
    DESCRIPTION
        "The utilization of MP CPU over 1 second. It shows the percentage."
    ::= { mpCpuStats 1}
 
mpCpuStatsUtil4Seconds OBJECT-TYPE
    SYNTAX  Integer32 
    MAX-ACCESS  read-only
    STATUS  current
    DESCRIPTION
        "The utilization of MP CPU  over 4 seconds. 
	 It shows the percentage."
    ::= { mpCpuStats 2}
 
mpCpuStatsUtil64Seconds OBJECT-TYPE
    SYNTAX  Integer32 
    MAX-ACCESS  read-only
    STATUS  current
    DESCRIPTION
        "The utilization of MP CPU over 64 seconds. 
	 It shows the percentage."
    ::= { mpCpuStats 3}
 
--
-- Port statistics table
--
portStatsTable OBJECT-TYPE
    SYNTAX  SEQUENCE OF PortStatsTableEntry
    MAX-ACCESS  not-accessible
    STATUS  current
    DESCRIPTION
        "The table of port statistics."
    ::= { portStats 1 }

portStatsTableEntry OBJECT-TYPE
    SYNTAX  PortStatsTableEntry
    MAX-ACCESS  not-accessible
    STATUS  current
    DESCRIPTION
        "A row in the port stats table."
    INDEX   { portStatsIndx }
    ::= { portStatsTable 1 }

PortStatsTableEntry ::=
    SEQUENCE {
	portStatsIndx
	    Integer32,
	portStatsPhyIfInOctets
	    Counter32,
	portStatsPhyIfInUcastPkts
	    Counter32,
	portStatsPhyIfInNUcastPkts
	    Counter32,
	portStatsPhyIfInDiscards
	    Counter32,
	portStatsPhyIfInErrors
	    Counter32,
	portStatsPhyIfInUnknownProtos
	    Counter32,
	portStatsPhyIfOutOctets
	    Counter32,
	portStatsPhyIfOutUcastPkts
	    Counter32,
	portStatsPhyIfOutNUcastPkts
	    Counter32,
	portStatsPhyIfOutDiscards
	    Counter32,
	portStatsPhyIfOutErrors
	    Counter32,
	portStatsPhyIfOutQLen
	    Gauge32,
        portStatsPhyIfInBroadcastPkts
            Counter32,
        portStatsPhyIfOutBroadcastPkts
            Counter32,
	portStatsClear
            INTEGER,
        portStatsPhyIfInMcastPkts
            Counter32,
        portStatsPhyIfOutMcastPkts
            Counter32
    }

portStatsIndx OBJECT-TYPE
    SYNTAX  Integer32
    MAX-ACCESS  read-only
    STATUS  current
    DESCRIPTION
        "The port index."
    ::= { portStatsTableEntry 1 }

portStatsPhyIfInOctets OBJECT-TYPE
    SYNTAX  Counter32
    MAX-ACCESS  read-only
    STATUS  current
    DESCRIPTION
	    "The total number of octets received on the
	    interface, including framing characters."
    ::= { portStatsTableEntry 2 }

portStatsPhyIfInUcastPkts OBJECT-TYPE
    SYNTAX  Counter32
    MAX-ACCESS  read-only
    STATUS  current
    DESCRIPTION
	    "The number of subnetwork-unicast packets
	    delivered to a higher-layer protocol."
    ::= { portStatsTableEntry 3 }

portStatsPhyIfInNUcastPkts OBJECT-TYPE
    SYNTAX  Counter32
    MAX-ACCESS  read-only
    STATUS  current
    DESCRIPTION
	    "The number of non-unicast (i.e., subnetwork-
	    broadcast or subnetwork-multicast) packets
	    delivered to a higher-layer protocol."
    ::= { portStatsTableEntry 4 }

portStatsPhyIfInDiscards OBJECT-TYPE
    SYNTAX  Counter32
    MAX-ACCESS  read-only
    STATUS  current
    DESCRIPTION
	    "The number of inbound packets which were chosen
	    to be discarded even though no errors had been
	    detected to prevent their being deliverable to a
	    higher-layer protocol.  One possible reason for
	    discarding such a packet could be to free up
	    buffer space."
    ::= { portStatsTableEntry 5 }

portStatsPhyIfInErrors OBJECT-TYPE
    SYNTAX  Counter32
    MAX-ACCESS  read-only
    STATUS  current
    DESCRIPTION
	    "The number of inbound packets that contained
	    errors preventing them from being deliverable to a
	    higher-layer protocol."
    ::= { portStatsTableEntry 6 }

portStatsPhyIfInUnknownProtos OBJECT-TYPE
    SYNTAX  Counter32
    MAX-ACCESS  read-only
    STATUS  current
    DESCRIPTION
	    "The number of packets received via the interface
	    which were discarded because of an unknown or
	    unsupported protocol."
    ::= { portStatsTableEntry 7 }

portStatsPhyIfOutOctets OBJECT-TYPE
    SYNTAX  Counter32
    MAX-ACCESS  read-only
    STATUS  current
    DESCRIPTION
	    "The total number of octets transmitted out of the
	    interface, including framing characters."
    ::= { portStatsTableEntry 8 }

portStatsPhyIfOutUcastPkts OBJECT-TYPE
    SYNTAX  Counter32
    MAX-ACCESS  read-only
    STATUS  current
    DESCRIPTION
	    "The total number of packets that higher-level
	    protocols requested be transmitted to a
	    subnetwork-unicast address, including those that
	    were discarded or not sent."
    ::= { portStatsTableEntry 9 }

portStatsPhyIfOutNUcastPkts OBJECT-TYPE
    SYNTAX  Counter32
    MAX-ACCESS  read-only
    STATUS  current
    DESCRIPTION
	    "The total number of packets that higher-level
	    protocols requested be transmitted to a non-
	    unicast (i.e., a subnetwork-broadcast or
	    subnetwork-multicast) address, including those
	    that were discarded or not sent."
    ::= { portStatsTableEntry 10 }

portStatsPhyIfOutDiscards OBJECT-TYPE
    SYNTAX  Counter32
    MAX-ACCESS  read-only
    STATUS  current
    DESCRIPTION
	    "The number of outbound packets which were chosen
	    to be discarded even though no errors had been
	    detected to prevent their being transmitted.  One
	    possible reason for discarding such a packet could
	    be to free up buffer space."
    ::= { portStatsTableEntry 11 }

portStatsPhyIfOutErrors OBJECT-TYPE
    SYNTAX  Counter32
    MAX-ACCESS  read-only
    STATUS  current
    DESCRIPTION
	    "The number of outbound packets that could not be
	    transmitted because of errors."
    ::= { portStatsTableEntry 12 }

portStatsPhyIfOutQLen OBJECT-TYPE
    SYNTAX  Gauge32
    MAX-ACCESS  read-only
    STATUS  current
    DESCRIPTION
	    "The length of the output packet queue (in
	    packets)."
    ::= { portStatsTableEntry 13 }

portStatsPhyIfInBroadcastPkts OBJECT-TYPE
    SYNTAX  Counter32
    MAX-ACCESS  read-only
    STATUS  current 
    DESCRIPTION
            "The number of packets, delivered by this sub-layer to
            a higher (sub-)layer, which were addressed to a
            broadcast address at this sub-layer."
    ::= { portStatsTableEntry 14 }

portStatsPhyIfOutBroadcastPkts OBJECT-TYPE
    SYNTAX  Counter32
    MAX-ACCESS  read-only
    STATUS  current 
    DESCRIPTION
	    "The total number of packets that higher-level
            protocols requested be transmitted, and which were
            addressed to a broadcast address at this sub-layer,
            including those that were discarded or not sent."
    ::= { portStatsTableEntry 15 }

portStatsClear OBJECT-TYPE
    SYNTAX  INTEGER {
        ok(1),
        clear(2)
        }
    MAX-ACCESS  read-write
    STATUS  current 
    DESCRIPTION
	    "Setting this value to clear(2) clears the stats for this port."
    ::= { portStatsTableEntry 16 }

portStatsPhyIfInMcastPkts OBJECT-TYPE
    SYNTAX  Counter32
    MAX-ACCESS  read-only
    STATUS  current
    DESCRIPTION
        "The number of packets, delivered by this sub-layer to
         a higher (sub-)layer, which were addressed to a
         multicast address at this sub-layer.
        ."
    ::= { portStatsTableEntry 17 }

portStatsPhyIfOutMcastPkts OBJECT-TYPE
    SYNTAX  Counter32
    MAX-ACCESS  read-only
    STATUS  current
    DESCRIPTION
        "The total number of packets that higher-level protocols 
         requested be transmitted, and which were addressed to 
         a multicast address at this sub-layer, including those 
         that were discarded or not sent."
    ::= { portStatsTableEntry 18 }

portMirrorStatsTable OBJECT-TYPE
    SYNTAX  SEQUENCE OF PortMirrorStatsTableEntry
    MAX-ACCESS  not-accessible
    STATUS  current
    DESCRIPTION
        "The table of port mirror statistics."
    ::= { portMirrorStats 1 }

portMirrorStatsTableEntry OBJECT-TYPE
    SYNTAX  PortMirrorStatsTableEntry
    MAX-ACCESS  not-accessible
    STATUS  current
    DESCRIPTION
        "A row in the port mirror stats table."
    INDEX   { portMirrorStatsIndx }
    ::= { portMirrorStatsTable 1 }

PortMirrorStatsTableEntry ::= SEQUENCE {
    portMirrorStatsIndx          Integer32,
    portMirrorStatsIngress       Counter32,
    portMirrorStatsEgress        Counter32
    }

portMirrorStatsIndx OBJECT-TYPE
    SYNTAX  Integer32
    MAX-ACCESS  read-only
    STATUS  current
    DESCRIPTION
        "The port index."
    ::= { portMirrorStatsTableEntry 1 }

portMirrorStatsIngress OBJECT-TYPE
    SYNTAX Counter32
    MAX-ACCESS  read-only
    STATUS  current
    DESCRIPTION
        "Specifies number of bytes mirrored in ingress port."
    ::= { portMirrorStatsTableEntry 2 }

portMirrorStatsEgress  OBJECT-TYPE
    SYNTAX Counter32
    MAX-ACCESS  read-only
    STATUS  current
    DESCRIPTION
        "Specifies number of bytes mirrored in egress port."
    ::= { portMirrorStatsTableEntry 3 }

portMirrorClear  OBJECT IDENTIFIER ::= { portMirrorStats 2 }

portMirrorStatsClear OBJECT-TYPE
    SYNTAX  INTEGER {
        ok(1),
        clear(2)
        }
    MAX-ACCESS  read-write
    STATUS  current
    DESCRIPTION
        "Setting this value to clear(2) clears the mirror stats."
    ::= { portMirrorClear 1 }

-- MP Memory Statisitics

mpMemStatsTotal OBJECT-TYPE
    SYNTAX Integer32
    MAX-ACCESS read-only
    STATUS current
    DESCRIPTION
        "The total memory of MP."
    ::= { mpMemStats 1 }

mpMemStatsUsed OBJECT-TYPE
    SYNTAX Integer32
    MAX-ACCESS read-only
    STATUS current
    DESCRIPTION
        "The used memory of MP."
    ::= { mpMemStats 2 }

mpMemStatsFree OBJECT-TYPE
    SYNTAX Integer32
    MAX-ACCESS read-only
    STATUS current
    DESCRIPTION
        "The free memory of MP."
    ::= { mpMemStats 3 }

mpMemStatsLowFree OBJECT-TYPE
    SYNTAX Integer32
    MAX-ACCESS read-only
    STATUS current
    DESCRIPTION
        "The lowest free memory of MP."
    ::= { mpMemStats 4 }

-- NTP Statisitics

ntpPrimaryServerReqSent OBJECT-TYPE
    SYNTAX Integer32
    MAX-ACCESS read-only
    STATUS current
    DESCRIPTION
        "The total number of NTP requests sent to Primary NTP Server."
    ::= { ntpStats 1 }

ntpPrimaryServerRespRcvd OBJECT-TYPE
    SYNTAX Integer32
    MAX-ACCESS read-only
    STATUS current
    DESCRIPTION
        "The total number of NTP responces received from Primary NTP Server."
    ::= { ntpStats 2 }

ntpPrimaryServerUpdates OBJECT-TYPE
    SYNTAX Integer32
    MAX-ACCESS read-only
    STATUS current
    DESCRIPTION
        "The total number of NTP Updates by Primary NTP Server."
    ::= { ntpStats 3 }

ntpSecondaryServerReqSent OBJECT-TYPE
    SYNTAX Integer32
    MAX-ACCESS read-only
    STATUS current
    DESCRIPTION
        "The total number of NTP requests sent to Secondary NTP Server."
    ::= { ntpStats 4 }

ntpSecondaryServerRespRcvd OBJECT-TYPE
    SYNTAX Integer32
    MAX-ACCESS read-only
    STATUS current
    DESCRIPTION
        "The total number of NTP responces received from Secondary NTP Server."
    ::= { ntpStats 5 }

ntpSecondaryServerUpdates OBJECT-TYPE
    SYNTAX Integer32
    MAX-ACCESS read-only
    STATUS current
    DESCRIPTION
        "The total number of NTP Updates by Secondary NTP Server."
    ::= { ntpStats 6 }

ntpLastUpdateServer OBJECT-TYPE
    SYNTAX  INTEGER {
        none(0),
        primary(1),
        secondary(2)
        }
    MAX-ACCESS read-only
    STATUS current
    DESCRIPTION
        "The type of ntp server updated last time."
    ::= { ntpStats 7 }

ntpLastUpdateTime OBJECT-TYPE
    SYNTAX  DisplayString (SIZE(0..127))
    MAX-ACCESS  read-only
    STATUS  current
    DESCRIPTION
        "The last time updated by ntp server."
    ::= { ntpStats 8 }

ntpClearStats OBJECT-TYPE
    SYNTAX  INTEGER {
        ok(1),
        clear(2)
        }
    MAX-ACCESS read-write
    STATUS current
    DESCRIPTION
        "Setting this value to clear(2) clears the stats for ntp."
    ::= { ntpStats 9 }

ntpSystemCurrentTime OBJECT-TYPE
    SYNTAX  DisplayString (SIZE(0..127))
    MAX-ACCESS  read-only
    STATUS  current
    DESCRIPTION
        "The current system time."
    ::= { ntpStats 10 }


-- Clear Statistics
snmpClearStats OBJECT-TYPE
    SYNTAX  INTEGER { 
	ok(1),
	clear(2)
	}
    MAX-ACCESS  read-write
    STATUS  current  
    DESCRIPTION
        "Setting this to clear(2) results in clearing the SNMP statistics." 
    ::= { agClearStats 1 }

agDiffState OBJECT-TYPE
    SYNTAX  INTEGER {
        diff(1), 
        flashdiff(2),
        idle(3),
        inprogress(4),
        complete(5)
        }
    MAX-ACCESS  read-write
    STATUS  current
    DESCRIPTION
         "When this object is read the current state is returned.
          idle(3) indicates that there is no diff in progess.
          complete(5) indicates that the last diff operation is completed.
          Setting the value to diff(1), will start a new diff operation
          Diff compares the new configuration with the current configuration
          and shows the pending configuration changes. 
          Setting the value to flashdiff(1), will start a new diff operation.
          flashdiff compares new configuration with the flash configuration.
          To read the configuration changes use the agDiffTable once the
          state of this variable returns complete.
          Once the agDiffTable is read the state should be set back to 'idle'
          which frees the diff buffer and others can issue a diff command via
          SNMP."
    ::= { agDiff 2 }

agDiffTableSize OBJECT-TYPE
    SYNTAX  Integer32
    MAX-ACCESS  read-only
    STATUS  current
    DESCRIPTION
        "The number of strings in the diff table."
    ::= { agDiff 3 }

agDiffTable OBJECT-TYPE
    SYNTAX  SEQUENCE OF AgDiffTableEntry
    MAX-ACCESS  not-accessible
    STATUS  current
    DESCRIPTION
        "The table of diff strings."
    ::= { agDiff 4 }

agDiffTableEntry OBJECT-TYPE
    SYNTAX  AgDiffTableEntry
    MAX-ACCESS  not-accessible
    STATUS  current
    DESCRIPTION
        "An entry in the diff table."
    INDEX   { agDiffIndex }
    ::= { agDiffTable 1 }

AgDiffTableEntry ::= SEQUENCE {
    agDiffIndex      Integer32,
    agDiffString     OCTET STRING
    }

agDiffIndex OBJECT-TYPE
    SYNTAX  Integer32
    MAX-ACCESS  read-only
    STATUS  current
    DESCRIPTION
        "The table index."
    ::= { agDiffTableEntry 1 }

agDiffString OBJECT-TYPE
    SYNTAX  OCTET STRING
    MAX-ACCESS  read-only
    STATUS  current
    DESCRIPTION
        "A string in the diff table."
    ::= { agDiffTableEntry 2 }

-- Config Dump 
agCfgDumpState OBJECT-TYPE
    SYNTAX  INTEGER {
        dump(1), 
        idle(2),
        inprogress(3),
        complete(4)
        }
    MAX-ACCESS  read-write
    STATUS  current
    DESCRIPTION
         "When this object is read the current state is returned.
          idle(2) indicates that there is no dump in progess.
          complete(4) indicates that the last dump operation is completed.
          Setting the value to dump(1), will start a new dump operation
          Dump will show the current configuration.
          To read the configuration dump use the agCfgDumpTable once the
          state of this variable returns complete.
          Once the agCfgDumpTable is read the state should be set back to 
          'idle' which frees the dump buffer and others can issue a dump 
          command via SNMP."
    ::= { agCfgDump 2 }

agCfgDumpTableSize OBJECT-TYPE
    SYNTAX  Integer32
    MAX-ACCESS  read-only
    STATUS  current
    DESCRIPTION
        "The number of strings in the dump table."
    ::= { agCfgDump 3 }

agCfgDumpTable OBJECT-TYPE
    SYNTAX  SEQUENCE OF AgCfgDumpTableEntry
    MAX-ACCESS  not-accessible
    STATUS  current
    DESCRIPTION
        "The table of dump strings."
    ::= { agCfgDump 4 }

agCfgDumpTableEntry OBJECT-TYPE
    SYNTAX  AgCfgDumpTableEntry
    MAX-ACCESS  not-accessible
    STATUS  current
    DESCRIPTION
        "An entry in the dump table."
    INDEX   { agCfgDumpIndex }
    ::= { agCfgDumpTable 1 }

AgCfgDumpTableEntry ::= SEQUENCE {
    agCfgDumpIndex      Integer32,
    agCfgDumpString     OCTET STRING
    }

agCfgDumpIndex OBJECT-TYPE
    SYNTAX  Integer32
    MAX-ACCESS  read-only
    STATUS  current
    DESCRIPTION
        "The table index."
    ::= { agCfgDumpTableEntry 1 }

agCfgDumpString OBJECT-TYPE
    SYNTAX  OCTET STRING
    MAX-ACCESS  read-only
    STATUS  current
    DESCRIPTION
        "A string in the dump table."
    ::= { agCfgDumpTableEntry 2 }

-- SP Statistics 

-- SP CPU utilization table

spStatsCpuUtilTable OBJECT-TYPE
    SYNTAX  SEQUENCE OF SpStatsCpuUtilTableEntry 
    MAX-ACCESS  not-accessible
    STATUS  current
    DESCRIPTION
        "The table of SP CPU utilization."
    ::= { spStats 1 }

spStatsCpuUtilTableEntry OBJECT-TYPE
    SYNTAX  SpStatsCpuUtilTableEntry
    MAX-ACCESS  not-accessible
    STATUS  current
    DESCRIPTION
        "A row in the SP CPU utilization table."
    INDEX   { spStatsCpuUtilSpIndex }
    ::= { spStatsCpuUtilTable 1 }

SpStatsCpuUtilTableEntry ::= SEQUENCE {
    spStatsCpuUtilSpIndex    Integer32,
    spStatsCpuUtil1Second    Integer32,
    spStatsCpuUtil4Seconds   Integer32,
    spStatsCpuUtil64Seconds  Integer32
    }

spStatsCpuUtilSpIndex OBJECT-TYPE
    SYNTAX  Integer32
    MAX-ACCESS  read-only
    STATUS  current
    DESCRIPTION
        "The SP index."
    ::= { spStatsCpuUtilTableEntry 1 }

spStatsCpuUtil1Second OBJECT-TYPE
    SYNTAX  Integer32 
    MAX-ACCESS  read-only
    STATUS  current
    DESCRIPTION
        "The utilization of this SP over 1 second. It shows the percentage."
    ::= { spStatsCpuUtilTableEntry 2 }
 
spStatsCpuUtil4Seconds OBJECT-TYPE
    SYNTAX  Integer32 
    MAX-ACCESS  read-only
    STATUS  current
    DESCRIPTION
        "The utilization of this SP over 4 seconds. It shows the percentage."
    ::= { spStatsCpuUtilTableEntry 3 }
 
spStatsCpuUtil64Seconds OBJECT-TYPE
    SYNTAX  Integer32 
    MAX-ACCESS  read-only
    STATUS  current
    DESCRIPTION
        "The utilization of this SP over 64 seconds. It shows the percentage."
    ::= { spStatsCpuUtilTableEntry 4 }

-- SP Maintenance Statistics

spMaintStatsTable OBJECT-TYPE
    SYNTAX  SEQUENCE OF SpMaintStatsTableEntry 
    MAX-ACCESS  not-accessible
    STATUS  current
    DESCRIPTION
        "The table of SP maintenance statistics."
    ::= { spStats 2 }

spMaintStatsTableEntry OBJECT-TYPE
    SYNTAX  SpMaintStatsTableEntry
    MAX-ACCESS  not-accessible
    STATUS  current
    DESCRIPTION
        "A row in the SP maintenance statistics table."
    INDEX   { spMaintStatsSpIndex }
    ::= { spMaintStatsTable 1 }

SpMaintStatsTableEntry ::= SEQUENCE {
    spMaintStatsSpIndex           Integer32,
    spMaintStatsResolveErrNoddw   Counter32,
    spMaintStatsLearnErrNoddw     Counter32,
    spMaintStatsAgeMPNoddw        Counter32,
    spMaintStatsDeleteMiss        Counter32,
    spMaintStatsRecvLetErrorsMP   Counter32,
    spMaintStatsRecvLetErrorsSP1  Counter32,
    spMaintStatsRecvLetErrorsSP2  Counter32,
    spMaintStatsRecvLetErrorsSP3  Counter32,
    spMaintStatsRecvLetErrorsSP4  Counter32,
    spMaintStatsSendLetFailsMP    Counter32,
    spMaintStatsSendLetFailsSP1   Counter32,
    spMaintStatsSendLetFailsSP2   Counter32,
    spMaintStatsSendLetFailsSP3   Counter32,
    spMaintStatsSendLetFailsSP4   Counter32,
    spMaintStatsRecvLetSuccessMP  Counter32,
    spMaintStatsRecvLetSuccessSP1 Counter32,
    spMaintStatsRecvLetSuccessSP2 Counter32,
    spMaintStatsRecvLetSuccessSP3 Counter32,
    spMaintStatsRecvLetSuccessSP4 Counter32,
    spMaintStatsSendLetSuccessMP  Counter32,
    spMaintStatsSendLetSuccessSP1 Counter32,
    spMaintStatsSendLetSuccessSP2 Counter32,
    spMaintStatsSendLetSuccessSP3 Counter32,
    spMaintStatsSendLetSuccessSP4 Counter32,
    spMaintStatsRateLimitArpDrops Counter32,
    spMaintStatsRateLimitIcmpDrops Counter32,
    spMaintStatsRateLimitTcpDrops Counter32,
    spMaintStatsRateLimitUdpDrops Counter32,
    spMaintStatsPfdbFreeEmpty     Counter32
    }

spMaintStatsSpIndex OBJECT-TYPE
    SYNTAX  Integer32
    MAX-ACCESS  read-only
    STATUS  current
    DESCRIPTION
        "The SP index."
    ::= { spMaintStatsTableEntry 1 }

spMaintStatsPfdbFreeEmpty OBJECT-TYPE
    SYNTAX  Counter32
    MAX-ACCESS  read-only
    STATUS  current
    DESCRIPTION
        "The number of times the attempts were made to add entries to an
         already full FDB."
    ::= { spMaintStatsTableEntry 2 }

spMaintStatsResolveErrNoddw OBJECT-TYPE
    SYNTAX  Counter32
    MAX-ACCESS  read-only
    STATUS  current
    DESCRIPTION
        "The number of times MAC address resolution failed because there were
         no DMA descriptors."
    ::= { spMaintStatsTableEntry 3 }

spMaintStatsLearnErrNoddw OBJECT-TYPE
    SYNTAX  Counter32
    MAX-ACCESS  read-only
    STATUS  current
    DESCRIPTION
        "The number of times MAC address learn failed because there were
         no DMA descriptors."
    ::= { spMaintStatsTableEntry 4 }

spMaintStatsAgeMPNoddw OBJECT-TYPE
    SYNTAX  Counter32
    MAX-ACCESS  read-only
    STATUS  current
    DESCRIPTION
        "The number of times MAC address aging failed because there were
         no DMA descriptors."
    ::= { spMaintStatsTableEntry 5 }

spMaintStatsDeleteMiss OBJECT-TYPE
    SYNTAX  Counter32
    MAX-ACCESS  read-only
    STATUS  current
    DESCRIPTION
        "The number of times MAC address could not be found."
    ::= { spMaintStatsTableEntry 6 }

spMaintStatsRecvLetErrorsMP OBJECT-TYPE
    SYNTAX  Counter32
    MAX-ACCESS  read-only
    STATUS  current
    DESCRIPTION
        "The number of receive letter errors from MP."
    ::= { spMaintStatsTableEntry 7 }

spMaintStatsRecvLetErrorsSP1 OBJECT-TYPE
    SYNTAX  Counter32
    MAX-ACCESS  read-only
    STATUS  current
    DESCRIPTION
        "The number of receive letter errors from SP1. 
         If the current table index is the same as the SP number then a value 
         of 0 is returned."
    ::= { spMaintStatsTableEntry 8 }

spMaintStatsRecvLetErrorsSP2 OBJECT-TYPE
    SYNTAX  Counter32
    MAX-ACCESS  read-only
    STATUS  current
    DESCRIPTION
        "The number of receive letter errors from SP2. 
         If the current table index is the same as the SP number then a value 
         of 0 is returned."
    ::= { spMaintStatsTableEntry 9 }

spMaintStatsRecvLetErrorsSP3 OBJECT-TYPE
    SYNTAX  Counter32
    MAX-ACCESS  read-only
    STATUS  current
    DESCRIPTION
        "The number of receive letter errors from SP3. 
         If the current table index is the same as the SP number then a value 
         of 0 is returned."
    ::= { spMaintStatsTableEntry 10 }

spMaintStatsRecvLetErrorsSP4 OBJECT-TYPE
    SYNTAX  Counter32
    MAX-ACCESS  read-only
    STATUS  current
    DESCRIPTION
        "The number of receive letter errors from SP4.
         If the current table index is the same as the SP number then a value 
         of 0 is returned."
    ::= { spMaintStatsTableEntry 11 }

spMaintStatsSendLetFailsMP OBJECT-TYPE
    SYNTAX  Counter32
    MAX-ACCESS  read-only
    STATUS  current
    DESCRIPTION
        "The number of send letter failures to MP."
    ::= { spMaintStatsTableEntry 12 }

spMaintStatsSendLetFailsSP1 OBJECT-TYPE
    SYNTAX  Counter32
    MAX-ACCESS  read-only
    STATUS  current
    DESCRIPTION
        "The number of send letter failures to SP1.
         If the current table index is the same as the SP number then a value 
         of 0 is returned."
    ::= { spMaintStatsTableEntry 13 }

spMaintStatsSendLetFailsSP2 OBJECT-TYPE
    SYNTAX  Counter32
    MAX-ACCESS  read-only
    STATUS  current
    DESCRIPTION
        "The number of send letter failures to SP2.
         If the current table index is the same as the SP number then a value 
         of 0 is returned."
    ::= { spMaintStatsTableEntry 14 }

spMaintStatsSendLetFailsSP3 OBJECT-TYPE
    SYNTAX  Counter32
    MAX-ACCESS  read-only
    STATUS  current
    DESCRIPTION
        "The number of send letter failures to SP3.
         If the current table index is the same as the SP number then a value 
         of 0 is returned."
    ::= { spMaintStatsTableEntry 15 }

spMaintStatsSendLetFailsSP4 OBJECT-TYPE
    SYNTAX  Counter32
    MAX-ACCESS  read-only
    STATUS  current
    DESCRIPTION
        "The number of send letter failures to SP4.
         If the current table index is the same as the SP number then a value 
         of 0 is returned."
    ::= { spMaintStatsTableEntry 16 }

spMaintStatsRecvLetSuccessMP OBJECT-TYPE
    SYNTAX  Counter32
    MAX-ACCESS  read-only
    STATUS  current
    DESCRIPTION
        "The number of receive letter success from MP."
    ::= { spMaintStatsTableEntry 17 }

spMaintStatsRecvLetSuccessSP1 OBJECT-TYPE
    SYNTAX  Counter32
    MAX-ACCESS  read-only
    STATUS  current
    DESCRIPTION
        "The number of receive letter success from SP1.
         If the current table index is the same as the SP number then a value 
         of 0 is returned."
    ::= { spMaintStatsTableEntry 18 }

spMaintStatsRecvLetSuccessSP2 OBJECT-TYPE
    SYNTAX  Counter32
    MAX-ACCESS  read-only
    STATUS  current
    DESCRIPTION
        "The number of receive letter success from SP2.
         If the current table index is the same as the SP number then a value 
         of 0 is returned."
    ::= { spMaintStatsTableEntry 19 }

spMaintStatsRecvLetSuccessSP3 OBJECT-TYPE
    SYNTAX  Counter32
    MAX-ACCESS  read-only
    STATUS  current
    DESCRIPTION
        "The number of receive letter success from SP3.
         If the current table index is the same as the SP number then a value 
         of 0 is returned."
    ::= { spMaintStatsTableEntry 20 }

spMaintStatsRecvLetSuccessSP4 OBJECT-TYPE
    SYNTAX  Counter32
    MAX-ACCESS  read-only
    STATUS  current
    DESCRIPTION
        "The number of receive letter success from SP4.
         If the current table index is the same as the SP number then a value 
         of 0 is returned."
    ::= { spMaintStatsTableEntry 21 }

spMaintStatsSendLetSuccessMP OBJECT-TYPE
    SYNTAX  Counter32
    MAX-ACCESS  read-only
    STATUS  current
    DESCRIPTION
        "The number of send letter success to MP."
    ::= { spMaintStatsTableEntry 22 }

spMaintStatsSendLetSuccessSP1 OBJECT-TYPE
    SYNTAX  Counter32
    MAX-ACCESS  read-only
    STATUS  current
    DESCRIPTION
        "The number of send letter success to SP1.
         If the current table index is the same as the SP number then a value 
         of 0 is returned."
    ::= { spMaintStatsTableEntry 23 }

spMaintStatsSendLetSuccessSP2 OBJECT-TYPE
    SYNTAX  Counter32
    MAX-ACCESS  read-only
    STATUS  current
    DESCRIPTION
        "The number of send letter success to SP2.
         If the current table index is the same as the SP number then a value 
         of 0 is returned."
    ::= { spMaintStatsTableEntry 24 }

spMaintStatsSendLetSuccessSP3 OBJECT-TYPE
    SYNTAX  Counter32
    MAX-ACCESS  read-only
    STATUS  current
    DESCRIPTION
        "The number of send letter success to SP3.
         If the current table index is the same as the SP number then a value 
         of 0 is returned."
    ::= { spMaintStatsTableEntry 25 }

spMaintStatsSendLetSuccessSP4 OBJECT-TYPE
    SYNTAX  Counter32
    MAX-ACCESS  read-only
    STATUS  current
    DESCRIPTION
        "The number of send letter success to SP4.
         If the current table index is the same as the SP number then a value 
         of 0 is returned."
    ::= { spMaintStatsTableEntry 26 }
    
spMaintStatsRateLimitArpDrops OBJECT-TYPE
    SYNTAX  Counter32
    MAX-ACCESS  read-only
    STATUS  current
    DESCRIPTION
        "The total number of ARP packets dropped due to rate limiting."
    ::= { spMaintStatsTableEntry 27 }
    
spMaintStatsRateLimitIcmpDrops OBJECT-TYPE
    SYNTAX  Counter32
    MAX-ACCESS  read-only
    STATUS  current
    DESCRIPTION
        "The total number of ICMP packets are dropped due to rate limiting."
    ::= { spMaintStatsTableEntry 28 }

spMaintStatsRateLimitTcpDrops OBJECT-TYPE
    SYNTAX  Counter32
    MAX-ACCESS  read-only
    STATUS  current
    DESCRIPTION
        "The total number of TCP packets are dropped due to rate limiting."
    ::= { spMaintStatsTableEntry 29 }

spMaintStatsRateLimitUdpDrops OBJECT-TYPE
    SYNTAX  Counter32
    MAX-ACCESS  read-only
    STATUS  current
    DESCRIPTION
        "The total number of UDP packets are dropped due to rate limiting."
    ::= { spMaintStatsTableEntry 30 }
    
spMemStatsTable OBJECT-TYPE
    SYNTAX  SEQUENCE OF SpMemStatsTableEntry 
    MAX-ACCESS  not-accessible
    STATUS  current
    DESCRIPTION
        "The table of SP memory statistics."
    ::= { spStats 3 }

spMemStatsTableEntry OBJECT-TYPE
    SYNTAX  SpMemStatsTableEntry
    MAX-ACCESS  not-accessible
    STATUS  current
    DESCRIPTION
        "A row in the SP memory statistics table."
    INDEX   { spMemStatsIndex }
    ::= { spMemStatsTable 1 }

SpMemStatsTableEntry ::= SEQUENCE {
    spMemStatsIndex             Integer32,
    spMemStatsTotal             Integer32,
    spMemStatsCurr              Integer32,
    spMemStatsAllocs            Counter32,
    spMemStatsFrees             Counter32,
    spMemStatsAllocsFailures    Counter32,
    spMemStatsHiWat             Integer32 
    }

spMemStatsIndex OBJECT-TYPE
    SYNTAX  Integer32
    MAX-ACCESS  read-only
    STATUS  current
    DESCRIPTION
        "The SP index."
    ::= { spMemStatsTableEntry 1 }

spMemStatsTotal OBJECT-TYPE
    SYNTAX  Integer32 
    MAX-ACCESS  read-only
    STATUS  current
    DESCRIPTION
        "The total memory of SP in bytes."
    ::= { spMemStatsTableEntry 2 }

spMemStatsCurr OBJECT-TYPE
    SYNTAX  Integer32
    MAX-ACCESS  read-only
    STATUS  current
    DESCRIPTION
        "The current memory of SP in bytes."
    ::= { spMemStatsTableEntry 3 }

spMemStatsAllocs OBJECT-TYPE
    SYNTAX  Counter32 
    MAX-ACCESS  read-only
    STATUS  current
    DESCRIPTION
        "The total number of dynamic memory allocations in SP."
    ::= { spMemStatsTableEntry 4 }

spMemStatsFrees OBJECT-TYPE
    SYNTAX  Counter32 
    MAX-ACCESS  read-only
    STATUS  current
    DESCRIPTION
        "The total number of dynamic memory frees in SP."
    ::= { spMemStatsTableEntry 5 }

spMemStatsAllocsFailures OBJECT-TYPE
    SYNTAX  Counter32 
    MAX-ACCESS  read-only
    STATUS  current
    DESCRIPTION
        "The total number of dynamic memory allocation failures in SP."
    ::= { spMemStatsTableEntry 6 }

spMemStatsHiWat OBJECT-TYPE
    SYNTAX  Integer32
    MAX-ACCESS  read-only
    STATUS  current
    DESCRIPTION
        "The high watermark in SP."
    ::= { spMemStatsTableEntry 7 }

-- Management Port Statistics

mgmtStatsRxpackets OBJECT-TYPE
    SYNTAX  Counter32
    MAX-ACCESS  read-only
    STATUS  current
    DESCRIPTION
        "Total number of packet allocations from the packet buffer pool by 
         the TCP/IP protocol stack."
    ::= { mgmtStats 1 }
 
mgmtStatsRxErrors OBJECT-TYPE
    SYNTAX  Counter32
    MAX-ACCESS  read-only
    STATUS  current
    DESCRIPTION
	    "The number of inbound packets that contained
	     errors preventing them from being deliverable to a
	     higher-layer protocol."
    ::= { mgmtStats 2 }
 
mgmtStatsRxDropped OBJECT-TYPE
    SYNTAX  Counter32
    MAX-ACCESS  read-only
    STATUS  current
    DESCRIPTION
	    "The number of inbound packets that were dropped."
    ::= { mgmtStats 3 }
 
mgmtStatsRxOverruns OBJECT-TYPE
    SYNTAX  Counter32
    MAX-ACCESS  read-only
    STATUS  current
    DESCRIPTION
	    "The number of data overruns over this link."
    ::= { mgmtStats 4 }
 
mgmtStatsRxFrame OBJECT-TYPE
    SYNTAX  Counter32
    MAX-ACCESS  read-only
    STATUS  current
    DESCRIPTION
	    "The number of frames received on this link."
    ::= { mgmtStats 5 }
 
mgmtStatsTxpackets OBJECT-TYPE
    SYNTAX  Counter32
    MAX-ACCESS  read-only
    STATUS  current
    DESCRIPTION
        "Total number of packet allocations from the packet buffer pool by 
         the TCP/IP protocol stack."
    ::= { mgmtStats 6 }
 
mgmtStatsTxErrors OBJECT-TYPE
    SYNTAX  Counter32
    MAX-ACCESS  read-only
    STATUS  current
    DESCRIPTION
	    "The number of outbound packets that contained
	     errors preventing them from being deliverable to a
	     higher-layer protocol."
    ::= { mgmtStats 7 }
 
mgmtStatsTxDropped OBJECT-TYPE
    SYNTAX  Counter32
    MAX-ACCESS  read-only
    STATUS  current
    DESCRIPTION
	    "The number of outbound packets that were dropped."
    ::= { mgmtStats 8 }
 
mgmtStatsTxOverruns OBJECT-TYPE
    SYNTAX  Counter32
    MAX-ACCESS  read-only
    STATUS  current
    DESCRIPTION
	    "The number of data overruns over this link."
    ::= { mgmtStats 9 }
 
mgmtStatsTxCarrier OBJECT-TYPE
    SYNTAX  Counter32
    MAX-ACCESS  read-only
    STATUS  current
    DESCRIPTION
 	"The number of times that the carrier sense
         condition was lost or never asserted when
         attempting to transmit a frame on a this
         interface."
    ::= { mgmtStats 10 }
 
mgmtStatsTxCollisions OBJECT-TYPE
    SYNTAX  Counter32
    MAX-ACCESS  read-only
    STATUS  current
    DESCRIPTION
	    "The number of collisions on this outbound segment."
    ::= { mgmtStats 11 }
 
mgmtStatsTxQueueLen OBJECT-TYPE
    SYNTAX  Counter32
    MAX-ACCESS  read-only
    STATUS  current
    DESCRIPTION
	    "The length of the TCP transmit queue." 
    ::= { mgmtStats 12 }

mgmtStatsRxBytes OBJECT-TYPE
    SYNTAX  Counter32
    MAX-ACCESS  read-only
    STATUS  current
    DESCRIPTION
            "The total number of bytes received."
    ::= { mgmtStats 13 }

mgmtStatsRxMulticast OBJECT-TYPE
    SYNTAX  Counter32
    MAX-ACCESS  read-only
    STATUS  current
    DESCRIPTION
            "The total number of multicast packets received."
    ::= { mgmtStats 14 }

mgmtStatsTxBytes OBJECT-TYPE
    SYNTAX  Counter32
    MAX-ACCESS  read-only
    STATUS  current
    DESCRIPTION
            "The total number of bytes transmitted."
    ::= { mgmtStats 15 }

-- IP ACL Bogon Info
ipAclBogonInfo OBJECT IDENTIFIER ::= { securityInfo 1 } 

ipAclBogonInfoTableMaxSize OBJECT-TYPE
    SYNTAX  Integer32
    MAX-ACCESS  read-only
    STATUS  current
    DESCRIPTION
        "The number of bogon IPs in IP ACL table."
    ::= { ipAclBogonInfo 1 }

ipAclBogonInfoTable OBJECT-TYPE
    SYNTAX  SEQUENCE OF IpAclBogonInfoTableEntry
    MAX-ACCESS  not-accessible
    STATUS  current
    DESCRIPTION
        "The table of bogons."
    ::= { ipAclBogonInfo 2 }

ipAclBogonInfoTableEntry OBJECT-TYPE
    SYNTAX  IpAclBogonInfoTableEntry
    MAX-ACCESS  not-accessible
    STATUS  current
    DESCRIPTION
        "An entry in the bogon IP ACL table."
    INDEX   { ipAclBogonInfoIndex }
    ::= { ipAclBogonInfoTable 1 }

IpAclBogonInfoTableEntry ::= SEQUENCE {
    ipAclBogonInfoIndex      Integer32,
    ipAclBogonInfoIp         IpAddress,
    ipAclBogonInfoMask       IpAddress
    }

ipAclBogonInfoIndex OBJECT-TYPE
    SYNTAX  Integer32
    MAX-ACCESS  read-only
    STATUS  current
    DESCRIPTION
        "The table index."
    ::= { ipAclBogonInfoTableEntry 1 }

ipAclBogonInfoIp OBJECT-TYPE
    SYNTAX  IpAddress
    MAX-ACCESS  read-only
    STATUS  current
    DESCRIPTION
        "Bogon IP Address."
    ::= { ipAclBogonInfoTableEntry 2 }

ipAclBogonInfoMask OBJECT-TYPE
    SYNTAX  IpAddress
    MAX-ACCESS  read-only
    STATUS  current
    DESCRIPTION
        "Mask for the bogon IP."
    ::= { ipAclBogonInfoTableEntry 3 }
-- End of Bogon Info 

-- Start of Symantec Info.
symantecInfo OBJECT IDENTIFIER ::= { securityInfo 2 }

symIpsEngineVersion OBJECT-TYPE
    SYNTAX  DisplayString (SIZE(0..16))
    MAX-ACCESS  read-only
    STATUS  current
    DESCRIPTION
        "Symantec IPS Engine Version."
    ::= { symantecInfo 1 }

symMatchInfoSpTable OBJECT-TYPE
    SYNTAX  SEQUENCE OF SymMatchInfoSpTableEntry 
    MAX-ACCESS  not-accessible
    STATUS  current
    DESCRIPTION
	"Symantec Match Info SP table."
    ::= { symantecInfo 2 }

symMatchInfoSpTableEntry OBJECT-TYPE
    SYNTAX  SymMatchInfoSpTableEntry
    MAX-ACCESS  not-accessible
    STATUS  current
    DESCRIPTION
	"A Symantec Match Info SP table entry."
    INDEX   { symMatchInfoSpTableIndex }
    ::= { symMatchInfoSpTable 1 }

SymMatchInfoSpTableEntry ::= SEQUENCE {
   symMatchInfoSpTableIndex	Integer32,
   symMatchInfoSpClientIp       IpAddress,
   symMatchInfoSpServerIp       IpAddress,
   symMatchInfoSpClientPort	Integer32,
   symMatchInfoSpServerPort	Integer32,
   symMatchInfoSpProtocol	DisplayString,
   symMatchInfoSpNumOfMatches   Integer32
   }

symMatchInfoSpTableIndex OBJECT-TYPE
    SYNTAX  Integer32
    MAX-ACCESS  read-only
    STATUS  current
    DESCRIPTION
        "The Match Info SP table index which is the SP index."
    ::= { symMatchInfoSpTableEntry 1 }

symMatchInfoSpClientIp OBJECT-TYPE
    SYNTAX  IpAddress
    MAX-ACCESS  read-only
    STATUS  current
    DESCRIPTION
        "The Client IP Address."
    ::= { symMatchInfoSpTableEntry 2 } 

symMatchInfoSpServerIp OBJECT-TYPE
    SYNTAX  IpAddress
    MAX-ACCESS  read-only
    STATUS  current
    DESCRIPTION
        "The Server IP Address."
    ::= { symMatchInfoSpTableEntry 3 }

symMatchInfoSpClientPort OBJECT-TYPE
    SYNTAX  Integer32
    MAX-ACCESS  read-only
    STATUS  current
    DESCRIPTION
        "The Client Port."
    ::= { symMatchInfoSpTableEntry 4 }

symMatchInfoSpServerPort OBJECT-TYPE
    SYNTAX  Integer32
    MAX-ACCESS  read-only
    STATUS  current
    DESCRIPTION
        "The Server Port."
    ::= { symMatchInfoSpTableEntry 5 }

symMatchInfoSpProtocol OBJECT-TYPE
    SYNTAX  DisplayString (SIZE(0..16))
    MAX-ACCESS  read-only
    STATUS  current
    DESCRIPTION
        "The Protocol."
    ::= { symMatchInfoSpTableEntry 6 }

symMatchInfoSpNumOfMatches OBJECT-TYPE
    SYNTAX  Integer32
    MAX-ACCESS  read-only
    STATUS  current
    DESCRIPTION
 	"Number of matches."
    ::= { symMatchInfoSpTableEntry 7 }

symMatchInfoSpSigActTable OBJECT-TYPE
    SYNTAX  SEQUENCE OF SymMatchInfoSpSigActTableEntry
    MAX-ACCESS  not-accessible
    STATUS  current
    DESCRIPTION
	"Symantec Match Info SP Signature-Action table."
    ::= { symantecInfo 3 }

symMatchInfoSpSigActTableEntry OBJECT-TYPE
    SYNTAX  SymMatchInfoSpSigActTableEntry
    MAX-ACCESS  not-accessible
    STATUS  current
    DESCRIPTION
	"A Symantec Match Info SP Signature-Action table entry."
    INDEX   { symMatchInfoSpSigActTblSpIndex, symMatchInfoSpSigActTblIndex }
    ::= { symMatchInfoSpSigActTable 1 }

SymMatchInfoSpSigActTableEntry ::= SEQUENCE {
   symMatchInfoSpSigActTblSpIndex	Integer32,
   symMatchInfoSpSigActTblIndex		Integer32,
   symMatchInfoSpSigActTblSigId		Integer32,
   symMatchInfoSpSigActTblAction        DisplayString	
   }

symMatchInfoSpSigActTblSpIndex OBJECT-TYPE
    SYNTAX  Integer32
    MAX-ACCESS  read-only
    STATUS  current
    DESCRIPTION
        "The match info signature action table SP index."
    ::= { symMatchInfoSpSigActTableEntry 1 }

symMatchInfoSpSigActTblIndex OBJECT-TYPE
    SYNTAX  Integer32
    MAX-ACCESS  read-only
    STATUS  current
    DESCRIPTION
        "The Match Info signature action table index."
    ::= { symMatchInfoSpSigActTableEntry 2 }

symMatchInfoSpSigActTblSigId OBJECT-TYPE
    SYNTAX  Integer32
    MAX-ACCESS  read-only
    STATUS  current
    DESCRIPTION
        "The Signature Id matched."
    ::= { symMatchInfoSpSigActTableEntry 3 }

symMatchInfoSpSigActTblAction OBJECT-TYPE
    SYNTAX  DisplayString (SIZE(0..16))
    MAX-ACCESS  read-only
    STATUS  current
    DESCRIPTION
 	"Action taken for the signature Id."
    ::= { symMatchInfoSpSigActTableEntry 4 }

-- End of Symantec Info.

-- Management Port Infor
mgmtPortInfoSpeed OBJECT-TYPE
    SYNTAX  INTEGER {
        mbs10(1),
        mbs100(2),
        any(3)
        }
    MAX-ACCESS  read-only
    STATUS  current
    DESCRIPTION
        "The current operational speed of the management port."
    ::= { mgmtInfo 1 }

mgmtPortInfoMode OBJECT-TYPE
    SYNTAX  INTEGER {
        full-duplex(1),
        half-duplex(2),
        any(3)
        }
    MAX-ACCESS  read-only
    STATUS  current
    DESCRIPTION
        "The current operational mode of the management port."
    ::= { mgmtInfo 2 }

mgmtPortInfoLink OBJECT-TYPE
    SYNTAX  INTEGER {
        up(1),
        down(2),
        disabled(3)
        }
     MAX-ACCESS  read-only
     STATUS  current
     DESCRIPTION
         "The current operational link status of the management port."
     ::= { mgmtInfo 3 }
 
hwOrderNumber OBJECT-TYPE
    SYNTAX  DisplayString (SIZE(0..16))
    MAX-ACCESS  read-only
    STATUS  current
    DESCRIPTION
        "The hardware order number of the Alteon Switch."
    ::= { hardware 5 }

hwMainBoardNumber OBJECT-TYPE
    SYNTAX  DisplayString (SIZE(0..16))
    MAX-ACCESS  read-only
    STATUS  current
    DESCRIPTION
        "The hardware main board number of the Alteon Switch."
    ::= { hardware 6 }

hwMainBoardRevision OBJECT-TYPE
    SYNTAX DisplayString (SIZE(0..16))
    MAX-ACCESS read-only
    STATUS current
    DESCRIPTION
        "The hardware main board revision.  If the revision is not
         available, a zero length string should be returned."
    ::= { hardware 7 }

hwEthernetBoardNumber OBJECT-TYPE
    SYNTAX  DisplayString (SIZE(0..16))
    MAX-ACCESS  read-only
    STATUS  current
    DESCRIPTION
        "The hardware ethernet board number of the Alteon Switch."
    ::= { hardware 8 }

hwEthernetBoardRevision OBJECT-TYPE
    SYNTAX DisplayString (SIZE(0..16))
    MAX-ACCESS read-only
    STATUS current
    DESCRIPTION
        "The hardware ethernet board revision.  If the revision is not
         available, a zero length string should be returned."
    ::= { hardware 9 }

hwChassisSerialNumber OBJECT-TYPE
    SYNTAX  DisplayString (SIZE(0..16))
    MAX-ACCESS  read-only
    STATUS  current
    DESCRIPTION
        "The chassis serial number of the Alteon Switch."
    ::= { hardware 10 }

hwChassisRevision OBJECT-TYPE
    SYNTAX DisplayString (SIZE(0..16))
    MAX-ACCESS read-only
    STATUS current
    DESCRIPTION
        "The chassis revision.  If the revision is not
         available, a zero length string should be returned."
    ::= { hardware 11 }


hwPower OBJECT-TYPE
    SYNTAX  INTEGER {
        ac(1),
        dc(2)
        }
    MAX-ACCESS  read-only
    STATUS  current
    DESCRIPTION
	"The type of power supply."
    ::= { hardware 24 }

END
