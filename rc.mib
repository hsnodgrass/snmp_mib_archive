RAPID-CITY DEFINITIONS ::= BEGIN
-- Title:       Rapid-City Communications Enterprise MIB
-- Date:        December 4, 1996
-- By:         	Edwin Tsang  
-- Revision:	 
--        v1  : 05/28/96 - Initial version from Ian Wallis. 
--        v2  : 06/23/96 - VLAN table now has port memberships 
--        v3  : 06/27/96 - Added Port table         
--        v4  : 07/03/96 - Rearranged rcSystem group so scalars 
--                         are grouped together 
--        v5  : 07/29/96 - Modified rcVlan and rcCard groups. 
--                         Added rcMirror and rcDipSwitch groups.  
--        v6  : 08/09/96 - Cleaned up rcVlanPortTable and rcTftp  
--                         groups. 
--        v7  : 08/21/96 - Added rcTraps group, rcVlanColorCode, 
--                         rcSysLastVlanChange, rcError group. 
--	  v9  : 09/10/96 - Added rcTblSize group.   
--		           Added rc16x100BaseTX(7) to rcCardType variable.  
--			   Added rcVlanStpTrapEnable to rcVlanEntry. 
--			   Added rcStpNewRoot and rcStpTopologyChange traps. 
--			   Added rcPortOperation to rcPortEntry. 
--			   Added rcSysCpuUtil and rcSysSwitchFabricUtil to 
--			   rcSystem. 
--			   Added rcVlanHighPriority and rcPortHighPriority. 
--	  v10 : 09/23/96 - Changed rcSysNvRam to rcSysNvRamSize. 
--			   Added rcVlanRoutingEnable and rcVlanIfIndex. 
--			   Added rcIp group. 
--	  v11 : 10/01/96 - Added rcSysRmonEnable, rcSysRmonMemSize, and 
--                         rcSysLastSaveToNVRam. 
-- 	  v12 : 10/16/96 - Added rcSysRmonSaveConfig. 
--                         Changed rcIpAdEntBcastAddr to  
--                         rcIpAdEntBcastAddrFormat 
--        v13 : 11/1/96  - Added rcTestTypes, rcTestCodesAdded,  
--                         and rcQos. 
--	  v14 : 11/12/96 - Added saveToSlaveNVRAM and switchOver to 
--			   rcSysAction variable. 
--			   Changed range of rcVlanColorCode. 
--			   Removed rcPortPerformBridging. 
--			   Removed rcPortOperation. 
--			   Added rcSysResult. 
--			   Added rcSysLastSaveToSlaveNVRam. 
--			   Added rcVlanAction and rcVlanResult. 
-- 			   Added rcPortAction and rcPortResult. 
--	  v15 : 12/04/96 - Added rcSysSupportRouting.  
--			   Changed rcVlanPortMembers. 
--			   Added rcVlanMemberType, rcVlanAllowToJoin 
--			   	 rcVlanType, rcVlanProtocolId,  
--			         rcVlanSubnetAddr, rcVlanSubnetMask. 
--			   Added rcVlanPortType.  
--			   Added rcVlanMacTable. 
--			   Added rcChasNumPorts. 
--			   Added rcCardPCMCIAType.  
--			   Added rcIpConfTable. 
--			   Removed loadFromNVRAM from rcSysAction. 
--	  v16 : 12/09/96 - Changed rcVlanProtocolId to an enumeration. 
--			   Added rcErrorText. 
--			   Maded rcQosProtocol an index in rcQosEntry. 
--	  v17 : 12/12/96 - Added rcStgTable and rcStgPortTable. 
--			   Changed rcStpNewRoot and rcStpTopologyChange 
--			   traps to use rcStgId instead of rcVlanId. 
--	  v18 : 12/18/96 - Added rcVlanStgId. 
--			   Removed rcVlanStpEnable, rcVlanStpTrapEnable. 
--		           Shifted rVlanPortMembers, rcVlanMemberType, 
--			   rcVlanNotAllowToJoin. 
--		           Added fail(14) to rcPortAction. 
--			   Added rcPortDefaultConnector. 
--			   Added rcPortActiveConnector. 
--			   Renamed all(5) to flushAll(5) to rcPortAction. 
--			   Added switchConnector(6) to rcPortAction. 
--			   Added types to rcCardType. 
--			   Added rcVlanMemberType to rcVlanStaticMembers. 
--			   Removed rcVlanPortTrunk 
--			   Added rcErrorReturnCode 
--			   Added rcTblArVlanByPortAdded 
--			   Added rcTblArVlanByPortDeleted 
--			   Added rcTblArVlanByProtocolAdded 
--			   Added rcTblArVlanByProtocolDeleted 
--			   Added rcTblArVlanByIpSubnetAdded 
--			   Added rcTblArVlanByIpSubnetDeleted 
--			   Added rcTblArIpSubnetsAdded 
--			   Added rcTblArIpSubnetsDeleted 
--			   Added rcTblArRsvpsAdded 
--			   Added rcTblArRsvpsDeleted 
--			   Added rcTblArIpMcastAdded 
--			   Added rcTblArIpMcastDeleted 
--			   Added rcTblArFree 
--			   Added rcTblArTblSize 
--			   Added rcTblArMcastTblSize 
--			   Added rcTblArFreeMcastGroups 
--			   Added rcTblBrdgFdbSize 
--			   Added rcStgPortMembers 
--			   Added rcQosPriority 
--			   Added rcStgUnassignedPorts 
--	  v19 : 1/6/97  -  Added rcSysTrapRecvVersion 
--        v20 : 1/7/97  -  Removed switchConnector(6) from rcPortAction 
--                         Added write access to rcPortActiveConnector 
--                         Added rcPortStandbyConnectorStatus to  
--                         rcPortTable. 
--	  v21 : 1/9/97  -  Renamed rcPortDefaultConnector to 
--                         rcPortPrimaryConnector. 
--			   Removed write access to rcPortActiveConnector. 
--			   Renamed rcPortStandbyConnectorStatus to 
--                         rcPortBackupConnectorStatus. 
--	                   Renamed rcVlanColorCode to rcVlanColor 
--                         Renamed switchOver to cpuSwitchOver. 
--                         Changed Access of rcStgId to read-only. 
--	  v22 : 1/17/97  - Added rcBoot group 
--                         Added rcPing group 
--                         Added rcTraceTable 
--                         Added rcTrace trap 
--                         Added rcBridge Tables 
--	  v23 : 1/20/97  - Added rcTraceFeatureId and rcTraceLevel  
--                         objects to rcTraceNotification trap. 
--                         Removed rcPingPort from rcPing group. 
--                         Added rcBridgeFdbTblSize  
--                         Added rcBridgeStaticTblSize  
--                         Added rcBridgeFilterTblSize  
--                         Removed rcStgPortEnable from  
--                         rcStgPortTable  
--                         Added rcStgPortEnableStg to 
--                         rcStgPortTable  
--                         Added rcStgPortInConfigBpdus, 
--                         Added rcStgPortInTcnBpdus,  
--                         Added rcStgPortInBadBpdus  
--                         Added rcStgPortOutConfigBpdus, 
--                         Added rcStgPortOutTcnBpdus  
--                         Removed ipxAny and snaAny from  
--                         rcVlanProtocolId  
--                         Renamed byMacAddr to bySrcMac in 
--                         rcVlanType 
--                         Added byDstMcast value to rcVlanType 
--	  v24 : 1/23/97  - Added rcSysRmonTrapOption. 
--                         Added agent, port, chassis, bridge, ip 
--                         to rcTraceFeatureId. 
--	  v25 : 1/25/97  - Removed rcTraceRowStatus. 
--                         Changed Access of rcTraceFeatureId to Read-only 
--                         Added more error codes to rcErrorReturnCode.  
--                         Rearranged the objects in the rcMirrorGroup. 
--                         Renamed rcMirrorByPort to rcMirrorByPortEnable 
--                         Added rcMirrorSaveConfig to rcMirror. 
--                         Added rcWebEnableServer. 
--                         Added rcWebAccessTable. 
--                         Added rcWebAccessTblSize scalar object. 
--                         Added rcVlanAgingTime in rcVlanTable. 
--                         Added rcStgPortFastStart in rcStgPortTable. 
--                         Added flushDynMemb to rcVlanAction.  
--        v26 : 2/13/97  - Rename downloadSw to downloadSwToFlash  
--                         and added downloadSwToPcmcia to rcTftpAction. 
--                         Modified rcIpAdEtReasmMaxSize to be read-only. 
--                         Added  "removed" to rcCardOperStatus.  
--                         Added  more featureIds to rcTraceFeatureId.  
--        v27 : 2/19/97  - Added checkSwInFlash and  
--                         checkSwInPcmcia  to rcTftpAction. 
--                         Added more result codes to rcTftpResult. 
--        v27 : 2/19/97  - Added checkSwInFlash and  
--                         checkSwInPcmcia  to rcSysAction. 
--                         Added more result codes to rcSysResult. 
--                         Added more result codes to rcTftpResult. 
--	  v28 : 2/28/97  - Expanded rcWeb and removed rcWebAccessTbl. 
--	  v29 : 3/20/97  - Changed rcCardSerialNum and rcChassisSerialNum 
--			   to a DisplayString. 
--	  v30 : 3/26/97  - Added rcSysSupportWebServer to rcSystem Group. 
--                         Removed rcStgName from rcStgTable. 
--                         Changed rcStgId range from 1..50 to 1..25. 
--                         Added rcVlanPotentialMembers to rcVlanTable.   
--                         Added rcChasType to rcChassisGroup. 
--                         Removed rcChasFanOperStatus from rcChassisGroup. 
--                         Added rcChasFanTable. 
--                         Modified rcChasPowerSupplyId range. 
--                         Added rcErrorSendTrap to rcError group. 
--                         Added rcPortType, rcPortAutoNegotiate, rcPortDuplex, 
--                         rcPortSetDuplex, rcPortSetSpeed to rcPortTable. 
--			   Changed enterprise mib oid from 
--			   1024 to 2272. 
--	  v31 : 3/31/97  - changed enums for rcChasType. 
--                         changed rcF1200 and rcF600 OID.  
--	  v32 : 4/01/97  - renamed rcPortSetSpeed to rcPortAdminSpeed  
--	                 - renamed rcPortSetDuplex to rcPortAdminDuplex  
--	                 - renamed rcPortDuplex to rcPortOperDuplex  
--	                 - Added rcPortOperSpeed to rcPortTable.  
--	                 - Added rcIpFlowTable. 
--			 - Removed "both" from trap version. 
--			 - Added rcStatGigTable. 
--        v33 : 4/21/97  - Added default value for rcStgTaggedBpduAddress. 
--                         Removed rcStgTagAccessPortBpdus. 
--			   Added rcVlanMacAddress. 
--			   Added additional enums to rcErrorReturnCode. 
--			   Removed rcStatGigRxFlowControlFrames and 
--			   rcStatGigRxRuntFrames. 
--                         Added rcStatTbl. 
--	  v34 : 5/08/97  - Added a bunch of bridging and routing 
--                         counters to the rcStat group. 
--	  v35 : 6/09/97  - Added a bunch of bridging and routing 
--                         Added rcPortRipEnable, rcPortOspfEnable, 
--                         rcPortOspfRtrPriority, rcPortOspfMetric, 
--                         rcPortOpsfAuthKey to rcPortTable. 
--                         Added additional error codes for ospf. 
--                         Added rcStatOspf group. 
--                         Added rcStatOspfIfTable. 
--                         Added error codes for Ospf. 
--                         Added rcIpRoutingRedistributeRipToOspf group. 
--                         Added rcIpRoutingRedistributeOspfToRip group. 
--                         Added rcIpRoutingRedistributeRipToOspfRouteTable 
--                         Added rcIpRoutingRedistributeOspfToRipRouteTable. 
--                         Added counters for mismatches in rcStatOspfIfTable. 
--                         Added rcIpConfAddrAssigned in rcIpConfTable. 
--                         Added rcSysOspfTrapEnable in rcSystem group. 
--                         Added rcIpConfOspfTable. 
--                         Moved rcIpConfOspfMetric, rcIpConfOspfRtrPriority, 
--                         and rcIpOspfAuthKey to rcIpConfOspfTable. 
--	  v36 : 6/16/97  - Added rc2x1000BaseFF200, rc8x100BaseTXF200,  
--			   rc16x100BaseTXF200 to rcCardType. 
--                         Misc. syntax changes to rcStatEntry group. 
--			   Changed all variables that are used as 
--			   ifIndex to the InterfaceIndex variable 
-- 			   type. 
--	  v37 : 6/30/97  - changed range for FanId values. 
--			   added additional error codes. 
--			   renamed the following variables: 
--			   rcMirrorDstPort to rcMirrorByPortMirrorPort 
--			   rcMirrorEnableSrcPortOne to rcMirrorByPortEnableMirroredPortOne 
--		 	   rcMirrorSrcPortOne to rcMirrorByPortMirroredPortOne. 
--			   rcMirrorEnableSrcPortTwo to rcMirrorByPortEnableMirroredPortTwo 
--		 	   rcMirrorSrcPortTwo to rcMirrorByPortMirroredPortTwo. 
--			   removed rcPing group 
--			   removed rcTrace group 
--        v38 : 7/09/97  - added new error codes 
--			   added new enums to rcTftpResult 
--			   added rcStgFastStart to rcStgTable. 
--        v39 : 7/15/97  - added InFlowCtrlPkts, OutFlowCtrlPkts to 
--                         rcStatGigTable. 
--                         removed enum "removed" from rcCardOperStatus. 
--                         Added enum "mbps1000" to  rcPortAdminSpeed. 
--                         Added new error codes. 
--	  v40 : 7/10/97  - added rcIpConfOspfCost group. 
--                         added rcIpRoutingRedistributeRipToOspfRouteMetric 
--                         and rcIpRoutingRedistributeOspfToRipRouteMetric 
--                         removed LeakAllSubnets from  
--                         rcIpRoutingRedistributeRipToOspfTable. 
--                         removed Internal, External1 and External2  
--                         from rcIpRoutingRedistributeRipToOspfTable. 
--                         Added rcIpRoutingRedistributeOspfToRipUseDefaultMetric 
--                         Added rcIpRoutingRedistributeRipToOspfUseDefaultMetric 
--                         Added ospf error codes. 
--                         Added rcCardPartNumber in rcCardEntry. 
--			   Changed saveToSlaveNVRAM to saveToStandbyNVRAM. 
--        		   Added rc2x1000BaseDualFF200 to rcCardType.  
--	  v41 : 8/28/97  - Changed rcCardType to new format. 
--                         Changed rcChasType to new format. 
--			   Removed mbps1000 enumeration. 
--			   Removed rcStgFastStart variable. 
--	  vigmp : 6/07/97  - Added rcIpConfIgmpTable, rcIgmpGroupTable. 
--                         Added rcStatIgmp group. 
--                         Added new card types for rcCardType. 
--	  v42 : 09/09/97 - Made rcIpAdEntBcastAddrFormat read-only. 
--	  v43 : 9/15/97  - added rcIpConfOspfHelloInterval and  
--                         rcIpConfOspfRtrDeadInterval to rcIpConfOspfTable 
--                         added rcIpConfOspf group. 
--                         moved rcSysOspfTrapEnable to rcIpConfOspf group. 
--                         added LsdbTblSize to rcStatOspf group. 
--	  v44 : 09/16/97 - Added rcPortIndex to rcStpTopologyChange trap. 
--			   Added additional error codes. 
--	  v45 : 09/18/97 - Added rcChasPowerSupplyDown rcChasFanDown 
--                         traps. 
--	  v46 : 09/26/97 - Changed rcSysIpAddr, rcSysNetMask, and rcSysBroadcast 
--			   from read-write to read-only. 
--	  v47 : 10/28/97 - Added rcSysTrapRecvSrcAddress to rcSysTrapRecvTable.  
--			 - Added enums to rcTftpResult. 
--			 - Added "other(n)" enum to rcPortPrimaryConnector, 
--		           rcPortActiveConnector, rcPortBackupConnectorStatus, 
--                         rcPortAdminSpeed. 
--	  v48 : 10/24/97 - Removed rcIpConfOspfExternalMetricType. 
--                         Renamed UseDefaultMetric to UseExplicitMetric 
--                         and DefaultMetric to ExplicitMetric in 
--                         RedistributeRipToOspf and RedistributeOspfToRip 
--                         Added ExternalMetricType to RedistributeRipToOspf  
--                         Added rcIpRoutingRedistributeDirectToOspf 
--                         and rcIpRoutingRedistributeStaticToOspf grps 
--                         removed un used error codes (148, 153, 158). 
--                         Added rcIpRoutingRedistributeDirectToRip 
--                         and rcIpRoutingRedistributeStaticToRip grps. 
--                         Added new error codes for ip addr. 
--        v49 : 11/24/97 - Added rcIpRouteTable group.  
--	  v50 : 11/24/97 - Modified the value of rcIpConfOspfMetric  
--	                   Modified the default value of  
--                         rcIpRoutingRedistributeDirectToOspfExplicitMetric.  
--        v51 : 12/01/97 - Changed rcSysTrapRecvVersion to v1. 
--                         Added enums to rcTftpAction and rcTftpResult. 
--        v52 : 12/03/97 - Added rcHighPriorityMode.   
--	  v53 : 12/18/97 - Added rcIpConfDhcpTable and rcIpDhcpForwardTable. 
--        v54 : 12/29/97 - Changed rcVlanPotentialMembers to  rcVlanActiveMembers. 
--                         Added rcVlanPortDiscardTaggedFrames,  
--                               rcVlanPortDiscardUntaggedFrames,  
--                               rcVlanPortDefaultVlanId. 
--                         Added rcSysLastIpAddrChange. 
--        v55 : 12/31/97 - Added rcDevice group. 
--	  v56 : 01/09/97 - Fixed compiler warning messages and added 
--                         default values to some DHCP variables. 
--	  v57 : 01/12/97 - Added enums to rcErrorReturnCode. 
--			   Changed Max VLAN IDs from 4095 to 4094. 
--        v58 : 01/21/98 - Obsoleted rcBoot. 
--                         Took rcDeviceLastBootSourceFileNum off from rcDevice. 
--                         Added rcDeviceFlashNumFiles, rcDevicePcmciaNumFiles 
--                         into rcDevice. 
--                         For rcDevice, added invalidDeviceFileNumber(179), 
--                         notExecutableDeviceFile(180), deletedDeviceFile(181) 
--                         into rcError. 
--                         Changed rcDeviceFlashFileMod to rcDeviceFlashFileMode. 
--                         For rcDeviceAction, changed squeezePcmica(3) to 
--                         squeezePcmcia(3). 
--	  v59 : 01/28/98 - Added enums to rcCardType.   
--			   Added vines(13) to rcVlanProtocolId. 
--	  v60 : 01/26/98 - Modified enum for rcPortAdminSpeed. 
--			   Added enums to rcCardType. 
--	  v61 : 02/02/98 - Added rcTestTypesExtLoopBack. 
--	  v62 : 02/06/98 - Changed IpDhcpForwardMode enum value. 
--		           Added rcDeviceConfigSource and rcDeviceConfigSourceFileNum. 
--	  v63 : 02/09/98 - Changed FileNum variables in rcDevice to be FileNames. 
--	  v64 : 02/19/97 - Added rcIpFilter group and rcMlt group. 
--      v64.1 : 04/09/98 - Modify the two "FIXME" field in rcIpFilter group. 
--	  v65 : 02/27/98 - Added more error codes. 
--			   Added rcPortLock group. 
--			   Added rcPortLocked. 
--        v66 : 02/25/98 - Added recoverFlash and recoverPcmcia to rcDeviceAction. 
--        v66 : 04/16/98 - Added snoopIpMcastAddrExist, error code 215. 
--	v66.1 : 04/02/98 - Added rc2x1000BaseXDWG and rc2x1000BaseXDBB card types. 
--      v66.2 : 04/16/98 - Changed snoopIpMcastAddrExist to snoopStaticGroupExist. 
--	  v67 : 03/05/98 - Added rcCli group. 
--	  v68 : 03/09/98 - Changed all read-write variables that have none(1) 
--			   to none(0).  
--			   Added IdList data type. 
--			   Added rcSysCommReadWriteLayer3 and rcSysCommReadWriteLayer2.  
--	  v69 : 03/18/98 - Added rcSysAccessPolicyEnable and  
--			   rcSysAccessPolicyTable. 
--        v70 : 03/18/98 - Added error code invalidDeviceFileLength 
--	  v71 : 03/23/98 - Backed out changes to xxxAction variables that made 
--			   none(1) to none(0). 
--			 - Added flushSnoopMembers to rcVlanAction. 
--	  v72 : 04/21/98 - Added rcIpPolicyAddrTable,  
--                         rcIpPolicyNetTable, rcIpPolicyListTable, 
--                         rcIpPolicyRipAnnounceTable, rcIpPolicyOspfAnnounceTable, 
--                         rcIpPolicyRipAcceptTable, rcIpPolicyOspfAcceptTable 
--	  v73 : 04/29/98 - obsoleted rcIpRoutingRedistribute groups. 
--                         added additional error codes. 
--	  v74 : 04/30/98 - added "none" to rcIpFilterPortMode.  
--	v74.1 : 05/01/98 - changed the choice order of rcIpFilterPortMode.  
--	  v75 : 05/08/98 - added "resetConsole" and "resetModem" to rcSysAction. 
--	  v76 : 05/08/98 - added "rcMltPortType" to rcMltTable.  
--	  v77 : 05/11/98 - Added rcVlanUserDefinedPid.  
--			   Added new enums for rcVlanProtocolId. 
--			   Added rcIpConfGlobal group. 
--	  v78 : 05/19/98 - Added error codes for rcip accept policies and filters. 
--	  v79 : 05/20/98 - Added rcPortAutoNegotiationSupported. 
--			   Added rcIpConfGlobalRipHoldDownTime 
--	  v80 : 05/11/98 - modified ospfIfAuthKey SYNTAX in rcIpConfOsptTable. 
--                         added rcIpConfOspfSpfHoldDownTime to rcIpConfOspf grp 
--                         added rcIpConfOspfIfAreaId to rcIpConfOspfTable. 
--	  v81 : 05/27/98 - Added rcChasAruMode. 
--			   Added rcPortSingleRoutablePort. 
-- 			   Deprecated rcPortPerformRouting. 
-- 			   Deprecated rcVlanRoutingEnable. 
--	  v82 : 05/29/98 - Added error codes for mlt. 
--                         Added Default values in rcRipExtEntry &rcArpExtEntry. 
--	  v83 : 06/01/98 - Added rcIpConfDhcpAlwaysBroadcast. 
--	  v84 : 06/03/98 - Added rcIpVrrp group. 
--	  v85 : 06/03/98 - Added rcIpConfOspfAreaTable. 
--	  v86 : 06/04/98 - Enhancement in rcVlanTable and 
--                         rcVlanIgmpSnoopStaticTable. 
-- 	  v87 : 06/05/98 - Removed rcIpVrrp group. 
-- 	  v87 : 06/05/98 - Removed rcIpVrrp group. 
--        v88 : 06/12/98 - Added rcVlanSnoopActiveQuerier, 
--                         rcVlanSnoopMRouterExpiration in rcVlan table. 
--                         Added rcMltEnable, rcMltLoadBalance, 
--                         rcMltDistributionAlgorithm in rcMlt table. 
--        v89 : 06/17/98 - Changed rcVlanSnoopActiveMRouterPorts, 
--                         rcVlanSnoopActiveQuerier, and 
--                         rcVlanSnoopMRouterExpiration to 
--                         rcVlanIgmpSnoopActiveMRouterPorts, 
--                         rcVlanIgmpSnoopActiveMRouterPorts, and 
--                         rcVlanIgmpSnoopMRouterExpiration respectively. 
--        v90 : 06/12/98 - Added rcIpConfRipAutoAggrerateEnable, 
--                         added additional error codes for route aggregation. 
--        v91 : 06/29/98 - Added new trap rcLinkOscillation. 
--        v92 : 07/01/98 - Added rcSyslog. 
--        v93 : 07/08/98 - Added rcVlanIgmpSnoopAccessTable. 
--	  v94 : 07/09/98 - Added rcChasPowerSupplyDetailTable.  
--	  v95 : 07/14/98 - Added rcVlanIgmpSnoopQuerierPort. 
--	  v96 : 07/17/98 - Added additional error codes. 
--	  v97 : 07/20/98 - Added rcIpFilterMode and rcIpFilterPortDefaultAction. 
--			   Added rcMltIfIndex. 
--			   Obsoleted rcIpFilterPortMode.  
--			   Added rcDiag group. 
--	  v98 : 07/21/98 - Modified the rcIpPolicy group. 
--	  v99 : 07/24/98 - Added description for Syslog group. 
--	 v100 : 07/24/98 - Added a new card type rc8x10BaseFBB. 
--       v101 : 07/29/98 - Added rcIpConfRipGenerateDefaultRoute. 
--		         - Added triggerRipUpdate to rcVlanAction. 
--	 v102 : 07/30/98 - Changed rcSysAccessPolicyActive to 
--                         rcSysAccessPolicyPolicyEnable. 
--	 v103 : 07/30/98 - modified the policy table index variable ACCESS 
--                         to read-only. 
--	 v104 : 08/04/98 - Added rc10BaseF to rcPortType. 
--	 v105 : 08/11/98 - Changed range of rcMltId. 
--	 v106 : 08/24/98 - Changed the option definition of rcSyslogHostModuleId 
--                         in hexdecimal. 
--       v107 : 08/28/98 - Added flushSnoopMRtr to rcVlanAction. 
--       v108 : 08/28/98 - Backed out changes made in v106. 
--	 v109 : 08/25/98 - Changed name size in policy & ip filter tables. 
--       v110 : 09/01/98 - Added rcStgNotAllowedPorts to rcStg group. 
--	 v111 : 09/28/98 - Changed rcVlanIgmpSnoopAccessMode options. 
--                         Added rcPortPerformMacLearning for rcPortTable. 
--       v112 : 10/01/98 - Add rcIpxAddrTbl 
--       v113 : 10/06/98 - Added rcIpDvmrp.  Added rcIpConfIgmpRobustness  
--                         and rcIpConfIgmpLastMemberQueryInterval 
--	 v114 : 10/06/98 - Added rc4xOC3, rc1xOC12, and rcRMON card types. 
--	 v115 : 10/06/98 - Changed rcIpDvmrp table to rcIpConfDvmrpTable. 
-- 
--       v116 : 09/29/98 - Added new items to rcIpFilter group. 
--       v117 : 10/01/98 - Changed rcPortPerformMacLearning to read-write. 
--       v118 : 10/07/98 - Changed rcPortPerformMacLearning to 
--                         rcPortUnknownMacDiscard. 
--       v119 : 09/29/98 - Merged rcIpFilter group from rel1.3. 
--                         Added more rcError items. 
--	 v120 : 10/15/98 - Added to "rarp" to rcVlanProtocolId. 
--       v121 : 10/15/98 - Add rcIpDvmrpEnable into rcIpDvmrp. 
--       v122 : 10/15/98 - Changed the range of rcIpConfIgmpRobustness. 
--       v123 : 10/20/98 - Added rcStatMlt group. 
--       v124 : 10/21/98 - Removed rcIpConfIgmp group. 
--       v125 : 10/27/98 - Added rcChasEnableEOCMode, rcPortPerformMacLearning 
--                         and rcError 323. 
--       v126 : 10/12/98 - added rcIpUdpProtocolTable,  rcIpUdpPortFwdTable, 
--                         rcIpUdpPortFwdListTable, rcIpUdpConfBroadcastIntfTable. 
--       v127 : 10/30/98 - Added rcVlanIgmpSnoopSenderTable. 
--       v128 : 11/02/98 - Added AuthType field to rcIpConfOspfTable. 
--       v129 : 11/03/98 - Changed the index keys of rcipIgmpGroupTable. 
--       v130 : 11/05/98 - Added enum none(0) to rcVlanIgmpSnoopSenderAction. 
--       v131 : 11/05/98 - Added rcChasEocModeAdminStatus and 
--                         rcChasEocModeOperStatus. Deleted rcChasEnableEOCMode. 
--       v132 : 11/10/98 - Changed rcChasEocModeAdminStatus to read-write and 
--                         rcChasEocModeOperStatus to read-only. 
--                         Changed aruMixed of rcChasAruMode to aruThree. 
--       v133 : 11/11/98 - Added PerformTagging into rcVlanPortTable. 
--       v134 : 11/12/98 - Added range limit for rcIpConfigDvmrpTableMetric. 
--       v135 : 11/16/98 - Added rcPortNumStateTransition in rcPort. 
--  
 
 
-- ISSUES 
-- 
-- None outstanding 
 
IMPORTS 
	MODULE-IDENTITY				FROM SNMPv2-SMI 
--	TEXTUAL-CONVENTION                  	FROM SNMPv2-TC 
	enterprises,  IpAddress, TimeTicks	FROM RFC1155-SMI 
	Counter					FROM RFC1155-SMI 
	OBJECT-TYPE 				FROM RFC-1212 
	DisplayString			 	FROM RFC1213-MIB 
	RowStatus, TruthValue, MacAddress 	FROM SNMPv2-TC 
	Gauge32, NOTIFICATION-TYPE		FROM SNMPv2-SMI 
	Counter32, Counter64			FROM SNMPv2-SMI;  
 
rapidCity MODULE-IDENTITY 
       LAST-UPDATED 	"9701010000Z" 
       ORGANIZATION 	"Bay Networks, Rapid-City Group" 
       CONTACT-INFO 	" 
				 	Edwin Tsang 
                	 Postal: 	Bay Networks, Inc.  
                       			4401 Great America Parkway  
                       			Santa Clara, CA 95052-8185  
 
                   	 Tel: 		408-495-6159 
                   	 Fax: 		408-495-5215  
                	 E-mail:	edwin_tsang@baynetworks.com  
			" 
       DESCRIPTION 	"Enterprise MIB for the Accelar product family." 
       ::= { enterprises 2272 } 
 
--  
-- Local defines to avoid having to pull-in other RFC's. 
-- 
BridgeId	::= OCTET STRING (SIZE (8)) 
Timeout		::= INTEGER 
 
-- 
-- This variable type is used through out the Rapid-City enterprise 
-- MIB to denote the standard ifIndex in mib-2.  
-- 
InterfaceIndex	::= INTEGER 
 
-- 
-- The string is 32 octets long, for a total of 256 bits. Each bit 
-- corresponds to a port, as represented by its ifIndex value . When a 
-- bit has the value one(1), the corresponding port is a member of the 
-- set. When a bit has the value zero(0), the corresponding port is not 
-- a member of the set. The encoding is such that the most significant 
-- bit of octet #1 corresponds to ifIndex 0, while the least significant 
-- bit of octet #32 corresponds to ifIndex 255." 
-- 
PortSet 	::= OCTET STRING (SIZE (32)) 
IdList 		::= OCTET STRING 
 
 
-- 
-- Additions to resolve some SNMP V2 dependencies so we don't 
-- have to pull-in a lot of mib modules. 
--                   
internet  	OBJECT IDENTIFIER ::= { iso org(3) dod(6) 1 } 
snmpV2 		OBJECT IDENTIFIER ::= { internet 6 } 
snmpModules 	OBJECT IDENTIFIER ::= { snmpV2 3 } 
snmpMIB 	OBJECT IDENTIFIER ::= { snmpModules 1 } 
snmpMIBObjects 	OBJECT IDENTIFIER ::= { snmpMIB 1 } 
snmpTraps 	OBJECT IDENTIFIER ::= { snmpMIBObjects 5 } 
 
 
-- 
-- Enterprise specific MIB groups 
-- 
rcMgmt 		OBJECT IDENTIFIER ::= { rapidCity 1 } 
rcA1100		OBJECT IDENTIFIER ::= { rapidCity 2 } 
rcA1250    	OBJECT IDENTIFIER ::= { rapidCity 6 } 
rcA1150    	OBJECT IDENTIFIER ::= { rapidCity 7 } 
rcA1200    	OBJECT IDENTIFIER ::= { rapidCity 8 } 
rcA1050    	OBJECT IDENTIFIER ::= { rapidCity 9 } 
 
rcSystem  	OBJECT IDENTIFIER ::= { rcMgmt 1 } 
rcTftp 	  	OBJECT IDENTIFIER ::= { rcMgmt 2 } 
rcVlan 	  	OBJECT IDENTIFIER ::= { rcMgmt 3 } 
rcChassis 	OBJECT IDENTIFIER ::= { rcMgmt 4 } 
rcMirror	OBJECT IDENTIFIER ::= { rcMgmt 5 } 
rcDipSwitch	OBJECT IDENTIFIER ::= { rcMgmt 6 } 
rcTblSize	OBJECT IDENTIFIER ::= { rcMgmt 7 } 
rcIp		OBJECT IDENTIFIER ::= { rcMgmt 8 } 
rcArp		OBJECT IDENTIFIER ::= { rcMgmt 9 } 
rcRip		OBJECT IDENTIFIER ::= { rcMgmt 10 } 
rcTest		OBJECT IDENTIFIER ::= { rcMgmt 11 } 
rcStat		OBJECT IDENTIFIER ::= { rcMgmt 12 } 
rcStg		OBJECT IDENTIFIER ::= { rcMgmt 13 } 
rcBridge	OBJECT IDENTIFIER ::= { rcMgmt 14 } 
rcBoot		OBJECT IDENTIFIER ::= { rcMgmt 15 } 
rcDevice	OBJECT IDENTIFIER ::= { rcMgmt 16 } 
rcMlt		OBJECT IDENTIFIER ::= { rcMgmt 17 } 
rcWeb		OBJECT IDENTIFIER ::= { rcMgmt 18 } 
rcCli		OBJECT IDENTIFIER ::= { rcMgmt 19 } 
rcError		OBJECT IDENTIFIER ::= { rcMgmt 20 } 
rcTraps		OBJECT IDENTIFIER ::= { rcMgmt 21 } 
rcSyslog	OBJECT IDENTIFIER ::= { rcMgmt 22 } 
rcDiag          OBJECT IDENTIFIER ::= { rcMgmt 23 } 
-- RCIPX 
rcIpx 		OBJECT IDENTIFIER ::= { rcMgmt 24 } 
-- RCIPX 
 
 
-- LOGICAL (System) Elements 
 
rcSysIpAddr OBJECT-TYPE 
        SYNTAX        IpAddress 
        ACCESS        read-only 
        STATUS        mandatory 
        DESCRIPTION   "This entity's IP address." 
        ::= { rcSystem 1 } 
 
rcSysNetMask OBJECT-TYPE 
        SYNTAX        IpAddress 
        ACCESS        read-only 
        STATUS        mandatory 
        DESCRIPTION   "This entity's subnet mask." 
        ::= { rcSystem 2 } 
 
rcSysBroadcast OBJECT-TYPE 
        SYNTAX        IpAddress 
        ACCESS        read-only 
        STATUS        mandatory 
        DESCRIPTION   "This entity's broadcast address." 
        ::= { rcSystem 3 } 
 
-- Community Strings 
 
rcSysCommReadWriteAll OBJECT-TYPE 
        SYNTAX        DisplayString (SIZE (0..20)) 
        ACCESS        read-write 
        STATUS        mandatory 
        DESCRIPTION   "When an SNMP message is received by this entity, the 
                      community string in the message is compared with this 
                      string first.  If it matches, read-write access is 
                      granted to all items in the MIB.  If it doesn't 
                      match, the rcSysCommReadWrite string is compared next." 
        ::= { rcSystem 4 } 
 
rcSysCommReadWrite OBJECT-TYPE 
        SYNTAX        DisplayString (SIZE (0..20)) 
        ACCESS        read-write 
        STATUS        mandatory 
        DESCRIPTION   "When an SNMP message is received by this entity, the 
                      community string in the message is compared with this 
                      string second.  If it matches, read-write access is 
                      granted to all items in the MIB except community 
                      strings.  (Community strings appear empty when read 
                      and return a no such name error when an attempt is 
                      made to write them.)  If it doesn't match, the 
                      rcSysCommReadWriteLayer3 string is compared next." 
        ::= { rcSystem 5 } 
 
rcSysCommReadOnly OBJECT-TYPE 
        SYNTAX        DisplayString (SIZE (0..20)) 
        ACCESS        read-write 
        STATUS        mandatory 
        DESCRIPTION   "When an SNMP message is received by this entity, the 
                      community string in the message is compared with this 
                      string third.  If it matches, read-only access is 
                      granted to all items in the MIB except community 
                      strings.  (Community strings appear empty when read.) 
                      If it doesn't match, no access is granted, no 
                      response is sent back to the SNMP requester, and 
                      SNMP traps are sent to the SNMP trap receiver(s) if 
                      configured." 
        ::= { rcSystem 6 } 
 
-- Other 
 
rcSysVersion OBJECT-TYPE 
	SYNTAX 		DisplayString (SIZE (0..20)) 
	ACCESS 		read-only 
	STATUS 		mandatory 
	DESCRIPTION	"Software version running on device" 
	::= { rcSystem 7 } 
 
rcSysAction OBJECT-TYPE 
        SYNTAX       INTEGER { 
                         none(1),               -- none of the following 
                         hardReset(2),          -- power on tests 
                         softReset(3),          -- reset w/o power on tests 
                         saveToNVRAM(4),        -- save current config to NVRAM 
                         resetCounters(5),      -- reset all statistic counters 
                         saveToStandbyNVRAM(6), -- save config to slave NVRAM 
                         cpuSwitchOver(7),      -- CPU board switch-over 
		         checkSwInFlash(8),        
		         checkSwInPcmcia(9), 
			 resetConsole(10), 
			 resetModem(11), 
			 flushIpRouteTbl(12) 
 	              } 
        ACCESS        read-write 
        STATUS        mandatory 
	DESCRIPTION   "Initiate a system action." 
	DEFVAL 	      { none } 
        ::= { rcSystem 8 } 
 
rcSysResult OBJECT-TYPE 
	SYNTAX       INTEGER { 
		         none(1),		-- none of the following 
		         inProgress(2),		-- in progress 
		         success(3),		-- success 
		         fail(4),		-- failure 
		         flashReadFailed(5),	-- could not read from flash 
		         pcmciaReadFailed(6),	-- could not read from pcmcia 
		         crcCheckFailed(7), 
                         noStandbyCpu(8) 
	              } 
        ACCESS        read-only 
        STATUS        mandatory 
	DESCRIPTION   "Result from the last system action." 
	DEFVAL 	      { none } 
        ::= { rcSystem 9 } 
 
rcSysLastChange OBJECT-TYPE 
        SYNTAX        TimeTicks 
        ACCESS        read-only 
        STATUS        mandatory 
        DESCRIPTION   "Last management initiated configuration  
		      change since sysUpTime." 
        ::= { rcSystem 10 } 
 
rcSysLastVlanChange OBJECT-TYPE 
        SYNTAX        TimeTicks 
        ACCESS        read-only 
        STATUS        mandatory 
        DESCRIPTION   "Last management initiated VLAN configuration  
		      change since sysUpTime." 
        ::= { rcSystem 11 } 
 
rcSysLastStatisticsReset OBJECT-TYPE 
        SYNTAX        TimeTicks 
        ACCESS        read-only 
        STATUS        mandatory 
        DESCRIPTION   "Last management initiated statistics reset  
		      since sysUpTime." 
        ::= { rcSystem 12 } 
 
-- Global Statistics 
 
rcSysBufferUtil OBJECT-TYPE 
	SYNTAX        INTEGER (0..100) 
	ACCESS        read-only 
	STATUS        mandatory 
	DESCRIPTION   "Buffer utilization as a percentage of the 
                      total amount of buffer space in the system.   
                      A high value indicates congestion." 
	::= { rcSystem 13 } 
 
rcSysBufferUtilPeak OBJECT-TYPE 
	SYNTAX        INTEGER (0..100) 
	ACCESS        read-only 
	STATUS        mandatory 
	DESCRIPTION   "The largest buffer utilization since sysUpTime" 
	::= { rcSystem 14 } 
 
rcSysBufferUtilPeakTime OBJECT-TYPE 
	SYNTAX        TimeTicks 
	ACCESS        read-only 
	STATUS        mandatory 
	DESCRIPTION   "Timestamp for rcSysPeakBandwidth" 
	::= { rcSystem 15 } 
 
rcSysNVRamSize OBJECT-TYPE 
	SYNTAX        Gauge32 
	ACCESS        read-only 
	STATUS        mandatory 
	DESCRIPTION   "Total Non-volatile RAM in Kbytes" 
	::= { rcSystem 16 } 
 
rcSysNVRamUsed OBJECT-TYPE 
	SYNTAX        Gauge32 
	ACCESS        read-only 
	STATUS        mandatory 
	DESCRIPTION   "Non-volatile RAM in use in Kbytes" 
	::= { rcSystem 17 } 
 
rcSysLastSaveToNVRam    OBJECT-TYPE 
        SYNTAX        TimeTicks 
        ACCESS        read-only 
        STATUS        mandatory 
        DESCRIPTION   "SysUpTime of the last time when NVRAM was 
                      written to.  This could be a save of the system 
                      configuration or via a file transfer of a 
                      configuration file." 
        ::= { rcSystem 18 } 
 
rcSysLastSaveToStandbyNVRam OBJECT-TYPE 
        SYNTAX        TimeTicks 
        ACCESS        read-only 
        STATUS        mandatory 
        DESCRIPTION   "SysUpTime of the last time when the standby NVRAM 
                      (on the back-up CPU board) was written to." 
        ::= { rcSystem 19 } 
 
rcSysCpuUtil OBJECT-TYPE 
        SYNTAX        Gauge32 
        ACCESS        read-only 
        STATUS        mandatory 
        DESCRIPTION   "Percentage of CPU utilization" 
        ::= { rcSystem 20 } 
 
rcSysSwitchFabricUtil OBJECT-TYPE 
        SYNTAX        Gauge32 
        ACCESS        read-only 
        STATUS        mandatory 
        DESCRIPTION   "Percentage of Switching Fabric utilization" 
        ::= { rcSystem 21 } 
 
rcSysRmonMemSize OBJECT-TYPE 
        SYNTAX        INTEGER (250000..4000000) 
        ACCESS        read-write 
        STATUS        mandatory 
        DESCRIPTION   "Amount of RAM in bytes to allocate for RMON 
                      to use when rcSysRmonEnable is TRUE." 
        ::= { rcSystem 22 } 
 
rcSysRmonEnable OBJECT-TYPE 
        SYNTAX        TruthValue 
        ACCESS        read-write 
        STATUS        mandatory 
        DESCRIPTION   "Control whether the RMON feature should be 
                      enabled. 
 
		      To enable the RMON feature, set this variable to 
		      true.  The RMON agent in the device will get  
                      started immediately if the amount of memory 
		      specified by rcSysRmonMemSize is currently 
		      available in the device. 
 
		      To disable the RMON feature, set this variable to 
		      false, save the new setting to NVRAM, and reboot 
		      the device.  After the device is rebooted the 
		      RMON agent will not be operational."  
        ::= { rcSystem 23 } 
 
rcSysRmonSaveConfig OBJECT-TYPE 
        SYNTAX        TruthValue 
        ACCESS        read-write 
        STATUS        mandatory 
        DESCRIPTION   "Control whether RMON configuration information  
                      should be saved to NVRAM so RMON settings can  
                      be automatically reinstalled after a system 
                      reboot.  
 
		      Setting rcSysRmonSaveConfig to true does not  
		      immediately save the configuration information. 
		      The save happens when the rcSysAction variable  
		      is set to 'saveToNVRAM(4)'. 
 
                      This option is only meaningful when the  
                      rcSysRmonEnable variable is set to true." 
        ::= { rcSystem 24 } 
 
rcSysRmonTrapOption OBJECT-TYPE 
        SYNTAX        INTEGER { 
		 	 toOwner(1), 
			 toAll(2) 
		      } 
        ACCESS        read-write 
        STATUS        mandatory 
        DESCRIPTION   "Used to indicate whether RMON traps should be 
		      sent to only the owner of the RMON alarm (i.e., 
		      the manager that created the alarm entry) or  
		      all trap recipients in the system trap receiver 
		      table." 
	DEFVAL	      { toOwner } 
        ::= { rcSystem 25 } 
 
rcSysSupportRouting OBJECT-TYPE 
        SYNTAX        TruthValue 
        ACCESS        read-only 
        STATUS        mandatory 
        DESCRIPTION   "Used to indicate whether routing is supported 
                      in this product." 
        ::= { rcSystem 26 } 
 
rcSysSupportWebServer OBJECT-TYPE 
        SYNTAX        TruthValue 
        ACCESS        read-only 
        STATUS        mandatory 
        DESCRIPTION   "Used to indicate whether WebServer is supported 
                      in this product." 
        ::= { rcSystem 27 } 
 
rcSysLastIpAddrChange OBJECT-TYPE 
        SYNTAX        TimeTicks 
        ACCESS        read-only 
        STATUS        mandatory 
        DESCRIPTION   "Last management initiated IP address change  
                       since sysUpTime.  Any addition or deletion of 
                       an IP address to a single routable port or 
                       a VLAN is time-stamped by this variable." 
        ::= { rcSystem 28 } 
 
rcSysCommReadWriteLayer3 OBJECT-TYPE 
        SYNTAX        DisplayString (SIZE (0..20)) 
        ACCESS        read-write 
        STATUS        mandatory 
        DESCRIPTION   "When an SNMP message is received by this entity, the 
                      community string in the message is compared with this 
                      string third.  If it matches, read-write access is  
		      granted to all Layer-3 items in the MIB except community 
                      strings.  (Community strings appear empty when read 
                      and return a no such name error when an attempt is 
                      made to write them.)  If it doesn't match, the 
                      rcSysCommReadWriteLayer2 string is compared next." 
        ::= { rcSystem 29 } 
 
rcSysCommReadWriteLayer2 OBJECT-TYPE  
        SYNTAX        DisplayString (SIZE (0..20))  
        ACCESS        read-write  
        STATUS        mandatory  
        DESCRIPTION   "When an SNMP message is received by this entity, the  
                      community string in the message is compared with this  
                      string fourth.  If it matches, read-write access is  
                      granted to all Layer-2 items in the MIB except community 
                      strings.  (Community strings appear empty when read  
                      and return a no such name error when an attempt is 
                      made to write them.)  If it doesn't match, the 
                      rcSysCommReadOnly string is compared next."  
        ::= { rcSystem 30 } 
 
rcSysAccessPolicyEnable OBJECT-TYPE 
        SYNTAX        TruthValue 
        ACCESS        read-write 
        STATUS        mandatory 
        DESCRIPTION   "Used to configure the system access policy feature. 
		      if 'true', the rcSysAccessPolicyTable is examined to 
		      determine which packets should be allowed or denied 
                      access to this device."  
	DEFVAL	      { false } 
        ::= { rcSystem 31 } 
 
 
-- Trap Receiver Table 
  
rcSysTrapRecvTable OBJECT-TYPE 
        SYNTAX        SEQUENCE OF RcSysTrapRecvEntry 
        ACCESS        not-accessible 
        STATUS        mandatory 
        DESCRIPTION   "The trap receiver table (0 to 25 entries).  This 
                      table lists the addresses of Network Management 
                      Stations that should receive trap messages from  
                      this entity when an exception condition occurs." 
        ::= { rcSystem 60 } 
 
rcSysTrapRecvEntry OBJECT-TYPE 
        SYNTAX        RcSysTrapRecvEntry 
        ACCESS        not-accessible 
        STATUS        mandatory 
        DESCRIPTION   "A trap receiver table entry." 
        INDEX         { rcSysTrapRecvAddress } 
        ::= { rcSysTrapRecvTable 1 } 
  
RcSysTrapRecvEntry ::= 
        SEQUENCE { 
                rcSysTrapRecvAddress IpAddress, 
                rcSysTrapRecvVersion INTEGER, 
                rcSysTrapRecvCommunity DisplayString, 
                rcSysTrapRecvSrcAddress IpAddress, 
                rcSysTrapRecvRowStatus RowStatus 
        } 
  
rcSysTrapRecvAddress OBJECT-TYPE 
        SYNTAX        IpAddress 
        ACCESS        read-only 
        STATUS        mandatory 
        DESCRIPTION   "IP address for trap receiver." 
        ::= { rcSysTrapRecvEntry 1 } 
  
rcSysTrapRecvVersion OBJECT-TYPE 
        SYNTAX        INTEGER { 
		         v1(1),           
		         v2c(2) 
	              } 
        ACCESS        read-write 
        STATUS	      mandatory 
	DEFVAL 	      { v1 } 
	::= { rcSysTrapRecvEntry 2 } 
 
rcSysTrapRecvCommunity OBJECT-TYPE 
        SYNTAX        DisplayString (SIZE (0..20)) 
        ACCESS        read-write 
        STATUS        mandatory 
        DESCRIPTION   "Community string used for trap messages to this 
                       trap receiver." 
        ::= { rcSysTrapRecvEntry 3 } 
 
rcSysTrapRecvSrcAddress OBJECT-TYPE  
        SYNTAX        IpAddress 
        ACCESS        read-write 
        STATUS        mandatory 
        DESCRIPTION   "Source IP address to use when sending traps. 
		       This IP address will be inserted into the 
		       source IP address field in the UDP trap packet." 
        ::= { rcSysTrapRecvEntry 4 }  
  
rcSysTrapRecvRowStatus OBJECT-TYPE 
        SYNTAX        RowStatus 
        ACCESS        read-write 
        STATUS        mandatory 
        DESCRIPTION   "Used to create/delete entries" 
        ::= { rcSysTrapRecvEntry 5 } 
 
 
-- Access Policy Table 
  
rcSysAccessPolicyTable OBJECT-TYPE 
        SYNTAX        SEQUENCE OF RcSysAccesspolicyEntry 
        ACCESS        not-accessible 
        STATUS        mandatory 
        DESCRIPTION   "Management access policy table.  This table is  
		       used to permit or deny access to this device via 
		       the specified source Id." 
        ::= { rcSystem 61 } 
 
rcSysAccessPolicyEntry OBJECT-TYPE 
        SYNTAX        RcSysAccesspolicyEntry 
        ACCESS        not-accessible 
        STATUS        mandatory 
        DESCRIPTION   "An access policy table entry." 
        INDEX         { rcSysAccessPolicyId } 
        ::= { rcSysAccessPolicyTable 1 } 
  
RcSysAccesspolicyEntry ::= 
        SEQUENCE { 
                rcSysAccessPolicyId INTEGER, 
                rcSysAccessPolicyName DisplayString, 
                rcSysAccessPolicyPolicyEnable TruthValue, 
                rcSysAccessPolicyMode INTEGER, 
                rcSysAccessPolicyService INTEGER, 
                rcSysAccessPolicyPrecedence INTEGER, 
                rcSysAccessPolicyNetAddr IpAddress, 
                rcSysAccessPolicyNetMask IpAddress, 
                rcSysAccessPolicyTrustedHostAddr IpAddress, 
                rcSysAccessPolicyTrustedHostUserName DisplayString, 
                rcSysAccessPolicyAccessLevel INTEGER, 
                rcSysAccessPolicyLog TruthValue, 
                rcSysAccessPolicyUsage Counter, 
                rcSysAccessPolicyRowStatus RowStatus 
        } 
  
rcSysAccessPolicyId OBJECT-TYPE  
        SYNTAX        INTEGER (1..65535) 
        ACCESS        read-only 
        STATUS        mandatory 
        DESCRIPTION   "Policy Id." 
        ::= { rcSysAccessPolicyEntry 1 }  
 
rcSysAccessPolicyName OBJECT-TYPE 
        SYNTAX        DisplayString (SIZE (0..15)) 
        ACCESS        read-write 
        STATUS        mandatory 
        DESCRIPTION   "Name of this policy." 
        ::= { rcSysAccessPolicyEntry 2 } 
 
rcSysAccessPolicyPolicyEnable OBJECT-TYPE 
        SYNTAX        TruthValue 
        ACCESS        read-write 
        STATUS        mandatory 
        DESCRIPTION   "Indicate whether this policy is currently  
                       active." 
	DEFVAL	      { true } 
        ::= { rcSysAccessPolicyEntry 3 } 
 
rcSysAccessPolicyMode OBJECT-TYPE 
        SYNTAX        INTEGER { 
                        allow(1),  
                        deny(2) 
                      }           
        ACCESS        read-write 
        STATUS        mandatory 
        DESCRIPTION   "Used to indicate whether a packet having a 
		       source IP address that matches this entry 
		       should be permitted to enter the device or 
 		       denied access."  
	DEFVAL	      { allow } 
        ::= { rcSysAccessPolicyEntry 4 } 
 
rcSysAccessPolicyService OBJECT-TYPE 
        SYNTAX        INTEGER { 
			telnet(1), 
			snmp(2), 
			tftp(4), 
			ftp(8), 
			http(16), 
			rlogin(32) 
	    	      }		 
        ACCESS        read-write 
        STATUS        mandatory 
        DESCRIPTION   "Is represented as bitset to indicate which protocol 
                      this entry should be applied to." 
	DEFVAL	      { snmp } 
        ::= { rcSysAccessPolicyEntry 5 } 
 
rcSysAccessPolicyPrecedence OBJECT-TYPE 
        SYNTAX        INTEGER (1..128) 
        ACCESS        read-write 
        STATUS        mandatory 
        DESCRIPTION   "Used to indicate the precedence of this policy. 
		       The Lower the number the higher the precedence." 
	DEFVAL	      { 10 } 
        ::= { rcSysAccessPolicyEntry 6 } 
 
rcSysAccessPolicyNetAddr OBJECT-TYPE 
        SYNTAX        IpAddress 
        ACCESS        read-write 
        STATUS        mandatory 
        DESCRIPTION   "Source network IP address." 
        ::= { rcSysAccessPolicyEntry 7 } 
  
rcSysAccessPolicyNetMask OBJECT-TYPE 
        SYNTAX        IpAddress 
        ACCESS        read-write 
        STATUS        mandatory 
        DESCRIPTION   "Source network mask." 
        ::= { rcSysAccessPolicyEntry 8 } 
  
rcSysAccessPolicyTrustedHostAddr OBJECT-TYPE 
        SYNTAX        IpAddress 
        ACCESS        read-write 
        STATUS        mandatory 
        DESCRIPTION   "Trusted IP address of host performing a rlogin 
		       into the device." 
        ::= { rcSysAccessPolicyEntry 9 } 
  
rcSysAccessPolicyTrustedHostUserName OBJECT-TYPE 
        SYNTAX        DisplayString (SIZE (0..30)) 
        ACCESS        read-write 
        STATUS        mandatory 
        DESCRIPTION   "User name on the trusted host performing a rlogin 
                       into the device." 
        ::= { rcSysAccessPolicyEntry 10 } 
 
rcSysAccessPolicyAccessLevel OBJECT-TYPE 
        SYNTAX        INTEGER { 
                        readOnly(1),  
                        readWrite(2), 
                        readWriteAll(3) 
                      }           
        ACCESS        read-write 
        STATUS        mandatory 
        DESCRIPTION   "Access level of trusted host."  
	DEFVAL	      { readWrite } 
        ::= { rcSysAccessPolicyEntry 11 } 
 
rcSysAccessPolicyLog OBJECT-TYPE 
        SYNTAX        TruthValue 
        ACCESS        read-write 
        STATUS        mandatory 
        DESCRIPTION   "Used to indicate whether logging should be  
		       performed if this policy was applied." 
	DEFVAL	      { false } 
        ::= { rcSysAccessPolicyEntry 12 } 
 
rcSysAccessPolicyUsage OBJECT-TYPE 
        SYNTAX  	Counter 
        ACCESS  	read-only 
        STATUS  	mandatory 
        DESCRIPTION 	"Usage counter" 
        ::= { rcSysAccessPolicyEntry 13 } 
 
rcSysAccessPolicyRowStatus OBJECT-TYPE 
        SYNTAX        RowStatus 
        ACCESS        read-write 
        STATUS        mandatory 
        DESCRIPTION   "Used to create/delete an entry" 
        ::= { rcSysAccessPolicyEntry 14 } 
 
 
-- TFTP Upload/Download 
 
rcTftpHost OBJECT-TYPE 
        SYNTAX        IpAddress 
        ACCESS        read-write 
        STATUS        mandatory 
        DESCRIPTION   "Name of source/destination host for the TFTP 
                      transfer." 
        ::= { rcTftp 1 } 
 
rcTftpFile OBJECT-TYPE 
        SYNTAX        DisplayString (SIZE (0..64)) 
        ACCESS        read-write 
        STATUS        mandatory 
        DESCRIPTION   "Name of file for the TFTP transfer." 
        ::= { rcTftp 2 } 
 
rcTftpAction OBJECT-TYPE 
        SYNTAX        INTEGER { 
		         none(1),          -- none of the following 
		         downloadConfig(2), 
		         uploadConfig(3), 
		         downloadSwToFlash(4), 
                         downloadSwToPcmcia(5), 
                         uploadSw(6), 
                         downloadSwToDram(7) 
	              } 
        ACCESS	      read-write 
        STATUS	      mandatory 
	DEFVAL 	      { none } 
	::= { rcTftp 3 } 
 
rcTftpResult OBJECT-TYPE 
        SYNTAX        INTEGER { 
		         none(1), 
		         inProgress(2), 
		         noResponse(3), 
		         fileAccessError(4), 
		         badFlash(5), 
		         flashEraseFailed(6), 
		         pcmciaEraseFailed(7), 
		         success(8), 
		         fail(9), 
                         writeToNvramFailed(10), 
		         flashWriteFailed(11), 
		         pcmciaWriteFailed(12), 
                         configFileTooBig(13), 
                         imageFileTooBig(14), 
			 noPcmciaDetect(15), 
			 pcmciaNotSupported(16), 
			 invalidFile(17), 
			 noMemory(18), 
			 xferError(19), 
			 crcError(20), 
                         readNvramFailed(21), 
                         pcmciaWriteProtect(22) 
	              } 
        ACCESS        read-only 
        STATUS        mandatory 
        DESCRIPTION   "Contains result of the last Tftp action request." 
        ::= { rcTftp 4 } 
 
 
-- VLAN Table 
 
rcVlanNumVlans OBJECT-TYPE 
        SYNTAX        INTEGER (1..128) 
        ACCESS        read-only 
        STATUS        mandatory 
        DESCRIPTION   "The number of VLANs currently defined in the switch." 
        ::= { rcVlan 1 } 
 
rcVlanTable OBJECT-TYPE 
        SYNTAX        SEQUENCE OF RcVlanEntry 
        ACCESS        not-accessible 
        STATUS        mandatory 
        DESCRIPTION   "A list of Virtual LAN entries. The number of entries 
                      is given by rcVlanNumVlans." 
        ::= { rcVlan 2 } 
 
rcVlanEntry OBJECT-TYPE 
        SYNTAX        RcVlanEntry 
        ACCESS        not-accessible 
        STATUS        mandatory 
        DESCRIPTION   "Entry containing configuration information for a  
                      particular Virtual LAN. 
 
                      The relationship between the various port sets in a  
                      VLAN Entry are : 
 
                      o The set of ports defined by PortMembers must be a  
                        subset of the set of ports in the underlying STG of  
                        the VLAN. 
 
                      o The bitwise AND of PortMembers and NotAllowToJoin must  
                        be the empty set. 
 
                      o The bitwise OR of PortMembers and NotAllowToJoin must  
                        be the set of ports in the underlying STG of the VLAN. 
 
                      o The set of ports defined by StaticMembers must be a  
                        subset of the set of ports defined by PortMembers. 
 
                      o The bitwise XOR of PortMembers and StaticMembers defines  
                        the set of dynamic (potential) members of the VLAN. 
 
                      o The set of ports defined by ActiveMembers must be a subset  
                        of the set of ports defined by PortMembers. 
                      " 
        INDEX         { rcVlanId } 
        ::= { rcVlanTable 1 } 
 
RcVlanEntry ::= SEQUENCE { 
                rcVlanId INTEGER, 
                rcVlanName DisplayString, 
                rcVlanColor INTEGER, 
                rcVlanHighPriority TruthValue, 
                rcVlanRoutingEnable TruthValue, 
                rcVlanIfIndex InterfaceIndex, 
                rcVlanAction INTEGER, 
                rcVlanResult INTEGER, 
                rcVlanStgId INTEGER, 
                rcVlanType INTEGER, 
                rcVlanPortMembers PortSet, 
                rcVlanActiveMembers PortSet, 
                rcVlanStaticMembers PortSet, 
                rcVlanNotAllowToJoin PortSet, 
                rcVlanProtocolId INTEGER, 
                rcVlanSubnetAddr IpAddress, 
                rcVlanSubnetMask IpAddress, 
                rcVlanAgingTime  INTEGER, 
                rcVlanMacAddress MacAddress, 
                rcVlanRowStatus RowStatus, 
                rcVlanIgmpSnoopEnable TruthValue, 
                rcVlanIgmpSnoopReportProxyEnable TruthValue, 
                rcVlanIgmpSnoopRobustness INTEGER, 
                rcVlanIgmpSnoopQueryInterval INTEGER, 
                rcVlanIgmpSnoopMRouterPorts PortSet, 
		rcVlanUserDefinedPid INTEGER, 
		rcVlanIgmpSnoopActiveMRouterPorts PortSet, 
		rcVlanProtocolIds INTEGER, 
		rcVlanIgmpSnoopActiveQuerier IpAddress, 
		rcVlanIgmpSnoopMRouterExpiration INTEGER, 
		rcVlanIgmpSnoopQuerierPort InterfaceIndex 
        } 
 
rcVlanId OBJECT-TYPE 
        SYNTAX        INTEGER (1..4094) 
        ACCESS        read-only 
        STATUS        mandatory 
        DESCRIPTION   "A value that uniquely identifies the Virtual LAN  
                      associated with this entry. This value corresponds 
                      to the lower 12 bits in the IEEE 802.1Q VLAN Tag." 
        ::= { rcVlanEntry 1 } 
 
rcVlanName OBJECT-TYPE 
        SYNTAX        DisplayString (SIZE (0..20)) 
        ACCESS        read-write 
        STATUS        mandatory 
        DESCRIPTION   "An administratively-assigned name for this VLAN." 
        ::= { rcVlanEntry 2 } 
 
rcVlanColor OBJECT-TYPE 
        SYNTAX        INTEGER (0..32) 
        ACCESS        read-write 
        STATUS        mandatory 
        DESCRIPTION   "An administratively-assigned color code for this 
                      VLAN. The value of this object is used by the VLAN 
                      Manager GUI tool to select a color when it draws 
                      this VLAN on the screen." 
        ::= { rcVlanEntry 3 } 
 
rcVlanHighPriority OBJECT-TYPE 
        SYNTAX        TruthValue 
        ACCESS        read-write 
        STATUS        mandatory 
        DESCRIPTION   "A flag to note whether frames in this VLAN should  
                      be assigned a high switching priority." 
        DEFVAL        { false } 
        ::= { rcVlanEntry 4 } 
 
rcVlanRoutingEnable OBJECT-TYPE 
        SYNTAX        TruthValue 
        ACCESS        read-write 
        STATUS        deprecated 
        DESCRIPTION   "A flag to note whether IP routing is enabled in 
                      this VLAN."  
        DEFVAL        { false } 
        ::= { rcVlanEntry 5 } 
 
rcVlanIfIndex OBJECT-TYPE 
        SYNTAX        InterfaceIndex  
        ACCESS        read-only 
        STATUS        mandatory 
        DESCRIPTION   "When rcVlanRoutingEnable is set to true(1), this  
                      value indicates the 'logical' ifIndex assigned to 
                      this VLAN.  Otherwise, this value is meaningless 
                      and should be set to zero." 
        ::= { rcVlanEntry 6 } 
 
rcVlanAction OBJECT-TYPE 
        SYNTAX        INTEGER { 
                         none(1),             -- none of the following 
                         flushMacFdb(2),      -- flush MAC forwarding table 
                         flushArp(3),         -- flush ARP table 
                         flushIp(4),          -- flush IP route table 
                         flushDynMemb(5),     -- flush Dynamic Members 
                         all(6),              -- flush all tables  
			 flushSnoopMemb(7),   -- flush IGMP Snoop Members 
                         triggerRipUpdate(8), -- manually trigger rip update 
			 flushSnoopMRtr(9)    -- flush snoop multicast router 
                      } 
        ACCESS        read-write 
        STATUS        mandatory 
        DESCRIPTION   "VLAN related actions." 
        DEFVAL        { none } 
        ::= { rcVlanEntry 7 } 
 
rcVlanResult OBJECT-TYPE 
        SYNTAX        INTEGER { 
                         none(1),        -- none of the following 
                         inProgress(2),  -- in progress 
                         success(3),     -- success 
                         fail(4)         -- failure 
                      } 
        ACCESS        read-only 
        STATUS        mandatory 
        DESCRIPTION   "The result from the last VLAN action." 
        DEFVAL        { none } 
        ::= { rcVlanEntry 8 } 
 
rcVlanStgId OBJECT-TYPE 
        SYNTAX        INTEGER (0..128) 
        ACCESS        read-write 
        STATUS        mandatory 
        DESCRIPTION   "Indicates the Spanning Tree Group (STG) used by 
                      this VLAN to determine the state of its ports. 
                      If this VLAN is not associated with any STG, this 
                      value should be set to zero." 
        DEFVAL        { 1 } 
        ::= { rcVlanEntry 9 } 
 
rcVlanType OBJECT-TYPE 
        SYNTAX        INTEGER { 
                         byPort(1),       -- VLAN by Port  
                         byIpSubnet(2),   -- VLAN by IP subnet  
                         byProtocolId(3), -- VLAN by Protocol Id 
                         bySrcMac(4),     -- VLAN by Src MAC address 
                         byDstMcast(5)    -- VLAN by Dst MultiCast 
                      } 
        ACCESS        read-write 
        STATUS        mandatory 
        DESCRIPTION   "The type of VLAN, distinguished according to the 
                      policy used to define its port membership." 
        ::= { rcVlanEntry 10 } 
 
rcVlanPortMembers OBJECT-TYPE 
        SYNTAX        PortSet 
        ACCESS        read-write 
        STATUS        mandatory 
        DESCRIPTION   "The set of ports that are members (static or  
                      dynamic) of this VLAN." 
        ::= { rcVlanEntry 11 } 
  
rcVlanActiveMembers OBJECT-TYPE 
        SYNTAX        PortSet 
        ACCESS        read-only 
        STATUS        mandatory 
        DESCRIPTION   "The set of ports that are currently active in  
                      this VLAN. Active ports include all static ports 
                      and any dynamic ports where the VLAN policy was 
                      met." 
        ::= { rcVlanEntry 12 } 
  
rcVlanStaticMembers OBJECT-TYPE 
        SYNTAX        PortSet 
        ACCESS        read-write 
        STATUS        mandatory 
        DESCRIPTION   "The set of ports that are static members of this 
                      VLAN. A static member of a VLAN is always active  
                      and is never aged out." 
        ::= { rcVlanEntry 13 } 
 
rcVlanNotAllowToJoin OBJECT-TYPE 
        SYNTAX        PortSet 
        ACCESS        read-write 
        STATUS        mandatory 
        DESCRIPTION   "The set of ports that are not allowed to become 
                      members of this VLAN." 
        ::= { rcVlanEntry 14 } 
 
rcVlanProtocolId OBJECT-TYPE 
        SYNTAX        INTEGER { 
                         none(0), 
                         ip(1), 
                         ipx802dot3(2), 
                         ipx802dot2(3), 
                         ipxSnap(4), 
                         ipxEthernet2(5), 
                         appleTalk(6), 
                         decLat(7), 
                         decOther(8), 
                         sna802dot2(9), 
                         snaEthernet2(10), 
                         netBios(11), 
                         xns(12), 
			 vines(13), 
                         ipV6(14),  
                         usrDefined(15), 
			 rarp(16) 
                      } 
        ACCESS        read-write 
        STATUS        mandatory 
        DESCRIPTION   "The protocol identifier of this VLAN. This value  
                      is meaningful only if rcVlanType is equal to  
                      byProtocolId(3). For other VLAN types it should 
                      have the value none(0)." 
        ::= { rcVlanEntry 15 } 
 
rcVlanSubnetAddr OBJECT-TYPE 
        SYNTAX        IpAddress 
        ACCESS        read-write 
        STATUS        mandatory 
        DESCRIPTION   "The IP subnet address of this VLAN. This value  
                      is meaningful only if rcVlanType is equal to  
                      byIpSubnet(2). For other VLAN types it should 
                      have the value 0.0.0.0." 
        ::= { rcVlanEntry 16 } 
 
rcVlanSubnetMask OBJECT-TYPE 
        SYNTAX        IpAddress 
        ACCESS        read-write 
        STATUS        mandatory 
        DESCRIPTION   "The IP subnet mask of this VLAN. This value 
                      is meaningful only if rcVlanType is equal to  
                      byIpSubnet(2). For other VLAN types it should 
                      have the value 0.0.0.0." 
        ::= { rcVlanEntry 17 } 
 
rcVlanAgingTime OBJECT-TYPE 
        SYNTAX        INTEGER (10..1000000) 
        ACCESS        read-write 
        STATUS        mandatory 
        DESCRIPTION   "The timeout period (in seconds) used for aging 
                      out dynamic members of this VLAN. This field is 
                      only relevant for policy-based VLANs." 
        DEFVAL        { 600 } 
        ::= { rcVlanEntry 18 } 
 
rcVlanMacAddress OBJECT-TYPE 
        SYNTAX        MacAddress 
        ACCESS        read-only 
        STATUS        mandatory 
        DESCRIPTION   "The MAC address assigned to the virtual router 
                      interface of this VLAN. This field is meaningful  
                      only if rcVlanRoutingEnable is equal to true(1)." 
        ::= { rcVlanEntry 19 } 
 
rcVlanRowStatus OBJECT-TYPE 
        SYNTAX        RowStatus 
        ACCESS        read-write 
        STATUS        mandatory 
        DESCRIPTION   "Used to create/delete entries in the rcVlanTable." 
        ::= { rcVlanEntry 20 } 
 
rcVlanIgmpSnoopEnable OBJECT-TYPE 
        SYNTAX        TruthValue 
        ACCESS        read-write 
        STATUS        mandatory 
        DESCRIPTION   "A flag to note whether IGMP Snooping is enabled 
                      on this VLAN." 
        DEFVAL        { false } 
        ::= { rcVlanEntry 21 } 
  
rcVlanIgmpSnoopReportProxyEnable OBJECT-TYPE 
        SYNTAX        TruthValue 
        ACCESS        read-write 
        STATUS        mandatory 
        DESCRIPTION   "A flag to note whether IGMP Report Proxy is 
                      enabled on this VLAN." 
        DEFVAL        { true } 
        ::= { rcVlanEntry 22 } 
  
rcVlanIgmpSnoopRobustness OBJECT-TYPE 
        SYNTAX        INTEGER (2..255) 
        ACCESS        read-write 
        STATUS        mandatory 
        DESCRIPTION   "This variable allows tuning for the expected 
                      packet loss on a subnet. If a subnet is expected 
                      to be lossy, the Robustness variable may be 
                      increased. IGMP is robust to (Robustness - 1) 
                      packet losses." 
        DEFVAL        { 2 } 
        ::= { rcVlanEntry 23 } 
  
rcVlanIgmpSnoopQueryInterval OBJECT-TYPE 
        SYNTAX        INTEGER (1..65535) 
        ACCESS        read-write 
        STATUS        mandatory 
        DESCRIPTION   "The interval (in seconds) between IGMP Host-Query 
                      packets transmitted on this interface." 
        DEFVAL        { 125 } 
        ::= { rcVlanEntry 24 } 
  
rcVlanIgmpSnoopMRouterPorts OBJECT-TYPE 
        SYNTAX        PortSet 
        ACCESS        read-write 
        STATUS        mandatory 
        DESCRIPTION   "The set of ports in this VLAN that provide 
                      connectivity to an IP Multicast router." 
        ::= { rcVlanEntry 25 } 
 
rcVlanUserDefinedPid OBJECT-TYPE 
        SYNTAX        INTEGER 
        ACCESS        read-write 
        STATUS        mandatory 
        DESCRIPTION   "When rcVlanProtocolId is set to usrDefined(15) 
                       in a protocol-based VLAN, this field represents 
                       the 16-bit user defined protocol identifier." 
        ::= { rcVlanEntry 26 } 
  
rcVlanIgmpSnoopActiveMRouterPorts OBJECT-TYPE 
        SYNTAX        PortSet 
        ACCESS        read-only 
        STATUS        mandatory 
        DESCRIPTION   "Active ports." 
        ::= { rcVlanEntry 27 } 
 
rcVlanProtocolIds OBJECT-TYPE 
        SYNTAX        INTEGER 
        ACCESS        read-write 
        STATUS        mandatory 
        DESCRIPTION   "Bitfield of protocol ids." 
        ::= { rcVlanEntry 28 } 
 
rcVlanIgmpSnoopActiveQuerier OBJECT-TYPE 
        SYNTAX        IpAddress 
        ACCESS        read-only 
        STATUS        mandatory 
        DESCRIPTION   "IP address of multicast querier router." 
        ::= { rcVlanEntry 29 } 
 
rcVlanIgmpSnoopMRouterExpiration OBJECT-TYPE 
        SYNTAX        INTEGER 
        ACCESS        read-only 
        STATUS        mandatory 
        DESCRIPTION   "Multicast querier router aging time out." 
        ::= { rcVlanEntry 30 } 
 
rcVlanIgmpSnoopQuerierPort OBJECT-TYPE 
        SYNTAX        InterfaceIndex 
        ACCESS        read-only 
        STATUS        mandatory 
        DESCRIPTION   "The port on which the multicast querier router 
		       was heard." 
        ::= { rcVlanEntry 31 } 
 
 
-- VLAN Port Table 
 
rcVlanPortTable OBJECT-TYPE 
        SYNTAX        SEQUENCE OF RcVlanPortEntry 
        ACCESS        not-accessible 
        STATUS        mandatory 
        DESCRIPTION   "A table used to maintain VLAN port related  
                      information."  
        ::= { rcVlan 3 } 
 
rcVlanPortEntry OBJECT-TYPE 
        SYNTAX        RcVlanPortEntry 
        ACCESS        not-accessible 
        STATUS        mandatory 
        DESCRIPTION   "Entry containing VLAN information regarding a  
                      particular port." 
        INDEX         { rcVlanPortIndex } 
        ::= { rcVlanPortTable 1 } 
 
RcVlanPortEntry ::= SEQUENCE { 
                rcVlanPortIndex INTEGER, 
                rcVlanPortNumVlanIds INTEGER, 
                rcVlanPortVlanIds IdList, 
                rcVlanPortType INTEGER, 
                rcVlanPortDiscardTaggedFrames TruthValue, 
                rcVlanPortDiscardUntaggedFrames TruthValue, 
                rcVlanPortDefaultVlanId INTEGER, 
                rcVlanPortPerformTagging TruthValue 
        } 
 
rcVlanPortIndex OBJECT-TYPE 
        SYNTAX        INTEGER  
        ACCESS        read-only 
        STATUS        mandatory 
        DESCRIPTION   "An unique index used to identify a particular  
                      port in the system. This index is equal to the 
                      ifIndex of the port." 
        ::= { rcVlanPortEntry 1 } 
 
rcVlanPortNumVlanIds OBJECT-TYPE 
        SYNTAX        INTEGER 
        ACCESS        read-only 
        STATUS        mandatory 
        DESCRIPTION   "Used to indicate the number of VLAN IDs that 
                      are stored in the rcVlanPortVlanIds variable." 
        ::= { rcVlanPortEntry 2 } 
 
rcVlanPortVlanIds OBJECT-TYPE 
        SYNTAX        IdList (SIZE (250)) 
        ACCESS        read-write   
        STATUS        mandatory 
        DESCRIPTION   "An array used to identify which VLANs this port  
                      is assigned to.  Each VLAN ID is stored as a two 
                      octet value. The first octet in the pair holds 
                      bits 15-8 of the VLAN ID, while the second octet 
                      holds bits 7-0 of the VLAN ID." 
        ::= { rcVlanPortEntry 3 } 
 
rcVlanPortType OBJECT-TYPE 
        SYNTAX        INTEGER { 
                         access(1),     -- access port type 
                         trunk(2)       -- trunk port type 
                      } 
        ACCESS        read-write 
        STATUS        mandatory 
        DESCRIPTION   "The type of port: access(1) or trunk(2)." 
        DEFVAL        { access } 
        ::= { rcVlanPortEntry 4 } 
 
rcVlanPortDiscardTaggedFrames OBJECT-TYPE 
        SYNTAX        TruthValue 
        ACCESS        read-write 
        STATUS        mandatory 
        DESCRIPTION   "A flag used to determine how to process tagged 
                      frames received on this access port. When the  
                      flag is set, these frames are discarded by the 
                      forwarding process. When the flag is reset, these 
                      frames are processed normally. 
 
		      This field is meaningless when the port is not 
		      an access port and should be set to false(2)." 
        DEFVAL        { false } 
        ::= { rcVlanPortEntry 5 } 
 
rcVlanPortDiscardUntaggedFrames OBJECT-TYPE 
        SYNTAX        TruthValue 
        ACCESS        read-write 
        STATUS        mandatory 
        DESCRIPTION   "A flag used to determine how to process untagged 
                      frames received on this trunk port. When the flag  
                      is set, these frames are discarded by the  
                      forwarding process. When the flag is reset, these 
                      frames are assigned to the VLAN specified by  
                      rcVlanPortDefaultVlanId. 
 
		      This field is meaningless when the port is not 
		      a trunk port and should be set to false(2)." 
        DEFVAL        { false } 
        ::= { rcVlanPortEntry 6 } 
 
rcVlanPortDefaultVlanId OBJECT-TYPE 
        SYNTAX        INTEGER (1..4094) 
        ACCESS        read-write 
        STATUS        mandatory 
        DESCRIPTION   "The VLAN ID assigned to untagged frames received 
                      on this trunk port. 
 
		      This field is meaningless when the port is not 
		      a trunk port." 
        DEFVAL        { 1 } 
        ::= { rcVlanPortEntry 7 }  
 
rcVlanPortPerformTagging OBJECT-TYPE 
        SYNTAX        TruthValue 
        ACCESS        read-write 
        STATUS        mandatory 
        DESCRIPTION   "" 
        DEFVAL        { false } 
        ::= { rcVlanPortEntry 8 } 
 
-- VLAN MAC Table 
 
rcVlanMacTable OBJECT-TYPE 
        SYNTAX        SEQUENCE OF RcVlanMacEntry 
        ACCESS        not-accessible 
        STATUS        mandatory 
        DESCRIPTION   "A table used to maintain MAC addresses assigned  
                      to a particular VLAN by MAC address." 
        ::= { rcVlan 4 } 
  
rcVlanMacEntry OBJECT-TYPE 
        SYNTAX        RcVlanMacEntry 
        ACCESS        not-accessible 
        STATUS        mandatory 
        DESCRIPTION   "Entry containing VLAN information regarding a 
                      particular port." 
        INDEX         { rcVlanMacVlanId, rcVlanMacAddr } 
        ::= { rcVlanMacTable 1 } 
  
RcVlanMacEntry ::= SEQUENCE { 
                rcVlanMacVlanId INTEGER, 
                rcVlanMacAddr MacAddress, 
                rcVlanMacRowStatus RowStatus 
        } 
  
rcVlanMacVlanId OBJECT-TYPE 
        SYNTAX        INTEGER 
        ACCESS        read-only 
        STATUS        mandatory 
        DESCRIPTION   "An unique index used to identify a VLAN (by MAC  
                      address) in the system." 
        ::= { rcVlanMacEntry 1 } 
 
rcVlanMacAddr OBJECT-TYPE 
        SYNTAX        MacAddress 
        ACCESS        read-only 
        STATUS        mandatory 
        DESCRIPTION   "An unique index used to identify a MAC address 
                      assigned to a particular VLAN." 
        ::= { rcVlanMacEntry 2 } 
 
rcVlanMacRowStatus OBJECT-TYPE 
        SYNTAX        RowStatus 
        ACCESS        read-write 
        STATUS        mandatory 
        DESCRIPTION   "Row status for this entry." 
        ::= { rcVlanMacEntry 3 } 
 
 
-- VLAN IGMP Snoop Table 
 
rcVlanIgmpSnoopNumGroups OBJECT-TYPE 
        SYNTAX        INTEGER 
        ACCESS        read-only 
        STATUS        mandatory 
        DESCRIPTION   "The number of entries (rows) in the 
                      rcVlanIgmpSnoopTable." 
        ::= { rcVlan 5 } 
 
rcVlanIgmpSnoopTable OBJECT-TYPE 
        SYNTAX        SEQUENCE OF RcVlanIgmpSnoopEntry 
        ACCESS        not-accessible 
        STATUS        mandatory 
        DESCRIPTION   "The (conceptual) table listing the IP multicast 
                      groups for which there are members on a particular 
                      interface on a particular VLAN." 
    ::= { rcVlan 6 } 
  
rcVlanIgmpSnoopEntry OBJECT-TYPE 
        SYNTAX        RcVlanIgmpSnoopEntry 
        ACCESS        not-accessible 
        STATUS        mandatory 
        DESCRIPTION   "An entry (row) in the rcVlanIgmpSnoopTable." 
        INDEX         { rcVlanIgmpSnoopVlanId, rcVlanIgmpSnoopIpAddress, 
                        rcVlanIgmpSnoopIfIndex, rcVlanIgmpSnoopMember } 
        ::= { rcVlanIgmpSnoopTable 1 } 
  
RcVlanIgmpSnoopEntry ::= SEQUENCE { 
            rcVlanIgmpSnoopVlanId     INTEGER, 
            rcVlanIgmpSnoopIpAddress  IpAddress, 
            rcVlanIgmpSnoopIfIndex    InterfaceIndex, 
            rcVlanIgmpSnoopMember     IpAddress, 
            rcVlanIgmpSnoopExpiration INTEGER, 
            rcVlanIgmpSnoopType       INTEGER 
        } 
 
rcVlanIgmpSnoopVlanId OBJECT-TYPE 
        SYNTAX        INTEGER (1..4094) 
        ACCESS        read-only 
        STATUS        mandatory 
        DESCRIPTION   "The VLAN for which this entry contains 
                      information." 
        ::= { rcVlanIgmpSnoopEntry 1 }  
 
rcVlanIgmpSnoopIpAddress OBJECT-TYPE 
        SYNTAX        IpAddress 
        ACCESS        read-only 
        STATUS        mandatory 
        DESCRIPTION   "The IP multicast group address for which this  
                      entry contains information." 
        ::= { rcVlanIgmpSnoopEntry 2 } 
  
rcVlanIgmpSnoopIfIndex OBJECT-TYPE 
        SYNTAX        InterfaceIndex 
        ACCESS        read-only 
        STATUS        mandatory 
        DESCRIPTION   "The interface for which this entry contains  
                      information for this IP multicast group address." 
        ::= { rcVlanIgmpSnoopEntry 3 } 
  
rcVlanIgmpSnoopMember OBJECT-TYPE 
        SYNTAX        IpAddress 
        ACCESS        read-only 
        STATUS        mandatory 
        DESCRIPTION   "The IP Address of the source of the membership 
                      report received for this IP Multicast group address 
                      on this interface. If no membership report has been 
                      received, this object has the value 0.0.0.0." 
        ::= { rcVlanIgmpSnoopEntry 4 } 
  
  
rcVlanIgmpSnoopExpiration OBJECT-TYPE 
         SYNTAX       INTEGER 
         ACCESS       read-only 
         STATUS       mandatory 
         DESCRIPTION  "The minimum amount of time remaining before this  
                      entry will be aged out." 
         ::= { rcVlanIgmpSnoopEntry 5 } 
 
rcVlanIgmpSnoopType OBJECT-TYPE 
         SYNTAX       INTEGER { 
                         dynamic(1),    -- created via IGMP 
                         static(2)      -- created via management 
                      } 
         ACCESS       read-only 
         STATUS       mandatory 
         DESCRIPTION  "The type of entry: dynamic(1) entries are 
                      created by snooping IGMP messages, static(2) 
                      entries are created via management." 
         ::= { rcVlanIgmpSnoopEntry 6 } 
 
 
-- VLAN IGMP Snoop Static Table 
 
rcVlanIgmpSnoopStaticTable OBJECT-TYPE 
        SYNTAX        SEQUENCE OF RcVlanIgmpSnoopStaticEntry 
        ACCESS        not-accessible 
        STATUS        mandatory 
        DESCRIPTION   "The (conceptual) table listing the statically- 
                      defined IP multicast groups for which there are 
                      members on a particular interface on a particular 
                      VLAN." 
    	::= { rcVlan 7 } 
  
rcVlanIgmpSnoopStaticEntry OBJECT-TYPE 
        SYNTAX        RcVlanIgmpSnoopStaticEntry 
        ACCESS        not-accessible 
        STATUS        mandatory 
        DESCRIPTION   "An entry (row) in the rcVlanIgmpSnoopStaticTable." 
        INDEX         { rcVlanIgmpSnoopStaticVlanId, 
rcVlanIgmpSnoopStaticIpAddress } 
        ::= { rcVlanIgmpSnoopStaticTable 1 } 
  
RcVlanIgmpSnoopStaticEntry ::= SEQUENCE { 
            rcVlanIgmpSnoopStaticVlanId           INTEGER, 
            rcVlanIgmpSnoopStaticIpAddress        IpAddress, 
            rcVlanIgmpSnoopStaticMemberPorts      PortSet, 
            rcVlanIgmpSnoopStaticRowStatus        RowStatus, 
            rcVlanIgmpSnoopStaticNotAllowedToJoin PortSet 
        } 
 
rcVlanIgmpSnoopStaticVlanId OBJECT-TYPE 
        SYNTAX        INTEGER (1..4094) 
        ACCESS        read-only 
        STATUS        mandatory 
        DESCRIPTION   "The VLAN for which this entry contains 
                      information." 
        ::= { rcVlanIgmpSnoopStaticEntry 1 }  
 
rcVlanIgmpSnoopStaticIpAddress OBJECT-TYPE 
        SYNTAX        IpAddress 
        ACCESS        read-only 
        STATUS        mandatory 
        DESCRIPTION   "The IP multicast group address for which this  
                      entry contains information.  The address must 
		      fall within 224.0.1.0 to 239.255.255.255." 
        ::= { rcVlanIgmpSnoopStaticEntry 2 } 
 
rcVlanIgmpSnoopStaticMemberPorts OBJECT-TYPE 
        SYNTAX        PortSet 
        ACCESS        read-write 
        STATUS        mandatory 
        DESCRIPTION   "The set of ports in this VLAN multicast traffic 
		      for the rcVlanIgmpSnoopStaticIpAddress is to be 
		      forwarded to." 
        ::= { rcVlanIgmpSnoopStaticEntry 3 } 
 
rcVlanIgmpSnoopStaticRowStatus OBJECT-TYPE 
        SYNTAX        RowStatus 
        ACCESS        read-write 
        STATUS        mandatory 
        DESCRIPTION   "Used to create/delete entries in the  
                      rcVlanIgmpSnoopStaticTable." 
        ::= { rcVlanIgmpSnoopStaticEntry 4 } 
 
rcVlanIgmpSnoopStaticNotAllowedToJoin OBJECT-TYPE 
        SYNTAX        PortSet 
        ACCESS        read-write 
        STATUS        mandatory 
        DESCRIPTION   "Not allowed to join" 
        ::= { rcVlanIgmpSnoopStaticEntry 5 } 
 
 
-- VLAN IGMP Snoop Access Table 
 
rcVlanIgmpSnoopAccessTable OBJECT-TYPE 
        SYNTAX        SEQUENCE OF RcVlanIgmpSnoopAccessEntry 
        ACCESS        not-accessible 
        STATUS        mandatory 
        DESCRIPTION   "" 
    	::= { rcVlan 8 } 
  
rcVlanIgmpSnoopAccessEntry OBJECT-TYPE 
        SYNTAX        RcVlanIgmpSnoopAccessEntry 
        ACCESS        not-accessible 
        STATUS        mandatory 
        DESCRIPTION   "An entry (row) in the rcVlanIgmpSnoopAccessTable." 
        INDEX         { rcVlanIgmpSnoopAccessVlanId, 
rcVlanIgmpSnoopAccessGrpAddr, rcVlanIgmpSnoopAccessHostAddr, 
rcVlanIgmpSnoopAccessHostMask } 
        ::= { rcVlanIgmpSnoopAccessTable 1 } 
  
 
RcVlanIgmpSnoopAccessEntry ::= SEQUENCE { 
            rcVlanIgmpSnoopAccessVlanId        INTEGER, 
            rcVlanIgmpSnoopAccessGrpAddr       IpAddress, 
            rcVlanIgmpSnoopAccessHostAddr      IpAddress, 
            rcVlanIgmpSnoopAccessHostMask      IpAddress, 
            rcVlanIgmpSnoopAccessMode          INTEGER, 
            rcVlanIgmpSnoopAccessRowStatus     RowStatus 
        } 
 
rcVlanIgmpSnoopAccessVlanId OBJECT-TYPE 
        SYNTAX        INTEGER (1..4094) 
        ACCESS        read-only 
        STATUS        mandatory 
        DESCRIPTION   "" 
        ::= { rcVlanIgmpSnoopAccessEntry 1 }  
 
rcVlanIgmpSnoopAccessGrpAddr OBJECT-TYPE 
        SYNTAX        IpAddress 
        ACCESS        read-only 
        STATUS        mandatory 
        DESCRIPTION   "" 
        ::= { rcVlanIgmpSnoopAccessEntry 2 }  
 
rcVlanIgmpSnoopAccessHostAddr OBJECT-TYPE 
        SYNTAX        IpAddress 
        ACCESS        read-only 
        STATUS        mandatory 
        DESCRIPTION   "" 
        ::= { rcVlanIgmpSnoopAccessEntry 3 } 
 
rcVlanIgmpSnoopAccessHostMask OBJECT-TYPE 
        SYNTAX        IpAddress 
        ACCESS        read-only 
        STATUS        mandatory 
        DESCRIPTION   "" 
        ::= { rcVlanIgmpSnoopAccessEntry 4 } 
 
rcVlanIgmpSnoopAccessMode OBJECT-TYPE 
        SYNTAX        INTEGER { 
                          denyTx(1), 
                          denyRx(2), 
                          denyBoth(3) 
                      } 
        ACCESS        read-write 
        STATUS        mandatory 
        DESCRIPTION   "" 
        ::= { rcVlanIgmpSnoopAccessEntry 5 } 
 
rcVlanIgmpSnoopAccessRowStatus OBJECT-TYPE 
        SYNTAX        RowStatus 
        ACCESS        read-write 
        STATUS        mandatory 
        DESCRIPTION   "" 
        ::= { rcVlanIgmpSnoopAccessEntry 6 } 
 
-- VLAN IGMP Snoop Sender Table 
 
rcVlanIgmpSnoopSenderTable OBJECT-TYPE 
        SYNTAX        SEQUENCE OF RcVlanIgmpSnoopSenderEntry 
        ACCESS        not-accessible 
        STATUS        mandatory 
         DESCRIPTION   "" 
    	::= { rcVlan 9 } 
  
rcVlanIgmpSnoopSenderEntry OBJECT-TYPE 
        SYNTAX        RcVlanIgmpSnoopSenderEntry 
        ACCESS        not-accessible 
        STATUS        mandatory 
        DESCRIPTION   "An entry (row) in the rcVlanIgmpSnoopSenderTable." 
        INDEX         { rcVlanIgmpSnoopSenderVlanId, 
                        rcVlanIgmpSnoopSenderIpAddress, 
                        rcVlanIgmpSnoopSenderIfIndex, 
                        rcVlanIgmpSnoopSenderMember } 
        ::= { rcVlanIgmpSnoopSenderTable 1 } 
  
 
RcVlanIgmpSnoopSenderEntry ::= SEQUENCE { 
            rcVlanIgmpSnoopSenderVlanId        INTEGER, 
            rcVlanIgmpSnoopSenderIpAddress     IpAddress, 
            rcVlanIgmpSnoopSenderIfIndex       InterfaceIndex, 
            rcVlanIgmpSnoopSenderMember        IpAddress, 
            rcVlanIgmpSnoopSenderAction        INTEGER 
        } 
 
rcVlanIgmpSnoopSenderVlanId OBJECT-TYPE 
        SYNTAX        INTEGER (1..4094) 
        ACCESS        read-only 
        STATUS        mandatory 
        DESCRIPTION   "" 
        ::= { rcVlanIgmpSnoopSenderEntry 1 }  
 
rcVlanIgmpSnoopSenderIpAddress OBJECT-TYPE 
        SYNTAX        IpAddress 
        ACCESS        read-only 
        STATUS        mandatory 
        DESCRIPTION   "" 
        ::= { rcVlanIgmpSnoopSenderEntry 2 }  
 
rcVlanIgmpSnoopSenderIfIndex OBJECT-TYPE 
        SYNTAX        InterfaceIndex 
        ACCESS        read-only 
        STATUS        mandatory 
        DESCRIPTION   "" 
        ::= { rcVlanIgmpSnoopSenderEntry 3 } 
  
rcVlanIgmpSnoopSenderMember OBJECT-TYPE 
        SYNTAX        IpAddress 
        ACCESS        read-only 
        STATUS        mandatory 
        DESCRIPTION   "" 
        ::= { rcVlanIgmpSnoopSenderEntry 4 }  
 
rcVlanIgmpSnoopSenderAction OBJECT-TYPE 
	SYNTAX        INTEGER { 
		         none(0), 
		         flushEntry(1), 
	     	         flushGrp(2) 
	              } 
        ACCESS        read-write 
        STATUS        mandatory 
        DESCRIPTION   "" 
        ::= { rcVlanIgmpSnoopSenderEntry 5 }  
 
 
-- PHYSICAL Elements 
 
rcChasType OBJECT-TYPE 
	SYNTAX	      INTEGER { 
		         unknown(1),  -- unknown chassis 
		         a1100(2),    -- 3 slots chassis (1/2, 1/2, full) 
		         a1250(6),    -- 4 slots chassis (full, ... , full) 
		         a1150(7),    -- 3 slots chassis (1/2, 1/2, full) 
		         a1200(8),    -- 8 slots chassis (full, ... , full) 
			 a1050(9)     -- 2 slots chassis (seahawk) 
	              } 
	ACCESS 	      read-only 
	STATUS 	      mandatory 
	DESCRIPTION   "Chassis Type" 
        ::= { rcChassis 1 } 
 
rcChasSerialNumber OBJECT-TYPE 
        SYNTAX        DisplayString (SIZE (0..8)) 
        ACCESS        read-only 
        STATUS        mandatory 
        DESCRIPTION   "Unique serial number for this chassis." 
        ::= { rcChassis 2 } 
 
rcChasHardwareRevision OBJECT-TYPE 
	SYNTAX 	      DisplayString (SIZE (0..20)) 
	ACCESS 	      read-only 
	STATUS 	      mandatory 
	DESCRIPTION   "Device hardware revision level" 
	::= { rcChassis 3 } 
	 
rcChasNumSlots OBJECT-TYPE 
        SYNTAX        INTEGER (1..16) 
        ACCESS        read-only 
        STATUS        mandatory 
        DESCRIPTION   "The number of slots in the chassis available for 
                      plug-in cards." 
        ::= { rcChassis 4 } 
 
rcChasNumPorts OBJECT-TYPE 
        SYNTAX        INTEGER (0..255)  
        ACCESS        read-only 
        STATUS        mandatory 
        DESCRIPTION   "The total number of ports currently installed in 
		      the chassis." 
        ::= { rcChassis 5 } 
 
-- TBD FIXME : We need to get the final list from Hardware 
rcChasTestResult OBJECT-TYPE 
	SYNTAX        INTEGER { 
			 other(1), 
			 ok(2), 
			 crceeprom(3), 
			 timer(4), 
			 procdram(5), 
			 led(6), 
       	         	 formaccpuaccess(7), 
       	         	 asiccpuaccess(8), 
                	 memory(9), 
                	 loopback(10) 
		      } 
	ACCESS 	      read-only 
	STATUS 	      mandatory 
	DESCRIPTION   "Chassis start-up diagnostic tests." 
	::= { rcChassis 6 } 
 
rcChasFan OBJECT IDENTIFIER ::= { rcChassis 7 } 
 
rcChasFanTable OBJECT-TYPE 
	SYNTAX        SEQUENCE OF RcChasFanEntry 
	ACCESS        not-accessible 
	STATUS        mandatory 
	DESCRIPTION   "This table contains information about power  
		      supplies." 
	::= { rcChasFan 1 } 
 
rcChasFanEntry OBJECT-TYPE 
	SYNTAX        RcChasFanEntry 
	ACCESS        not-accessible 
	STATUS        mandatory 
	DESCRIPTION   "Contains information regarding a power supply 
		      unit." 
	INDEX         { rcChasFanId } 
	::= { rcChasFanTable 1 } 
 
RcChasFanEntry ::= 
	SEQUENCE { 
		rcChasFanId INTEGER, 
		rcChasFanOperStatus INTEGER 
	} 
 
rcChasFanId OBJECT-TYPE 
	SYNTAX        INTEGER(1..4) 
	ACCESS        read-only 
	STATUS        mandatory 
	::= { rcChasFanEntry 1 } 
 
rcChasFanOperStatus OBJECT-TYPE 
	SYNTAX        INTEGER { 
		         unknown(1), 
		         up(2), 
		         down(3) 
	              } 
	ACCESS        read-only 
	STATUS        mandatory 
	DESCRIPTION   "Actual status of the Fan: 
	              - unknown(1) - status can not be determined. 
	              - up(2) - present and supplying power. 
	              - down(3) - present, but failure indicated." 
	::= { rcChasFanEntry 2 } 
 
rcChasPowerSupply OBJECT IDENTIFIER ::= { rcChassis 8 } 
 
rcChasPowerSupplyTable OBJECT-TYPE 
	SYNTAX        	SEQUENCE OF RcChasPowerSupplyEntry 
	ACCESS        	not-accessible 
	STATUS        	mandatory 
	DESCRIPTION   	"This table contains information about power  
		      	supplies." 
	::= { rcChasPowerSupply 1 } 
 
rcChasPowerSupplyEntry OBJECT-TYPE 
	SYNTAX        	RcChasPowerSupplyEntry 
	ACCESS        	not-accessible 
	STATUS        	mandatory 
	DESCRIPTION   	"Contains information regarding a power supply 
		      	unit." 
	INDEX  { rcChasPowerSupplyId } 
	::= { rcChasPowerSupplyTable 1 } 
 
RcChasPowerSupplyEntry ::= 
	SEQUENCE { 
		rcChasPowerSupplyId INTEGER, 
		rcChasPowerSupplyOperStatus INTEGER 
	} 
 
rcChasPowerSupplyId OBJECT-TYPE 
	SYNTAX        	INTEGER(1..2) 
	ACCESS        	read-only 
	STATUS        	mandatory 
	::= { rcChasPowerSupplyEntry 1 } 
 
 
rcChasPowerSupplyOperStatus OBJECT-TYPE 
	SYNTAX         INTEGER { 
		          unknown(1), 
		          empty(2), 
		          up(3), 
	     	          down(4) 
	               } 
	ACCESS         read-only 
	STATUS         mandatory 
	DESCRIPTION   "Actual status of the power supply: 
	              - unknown(1) - status can not be determined. 
	              - empty(2) - power supply not installed. 
	              - up(3) - present and supplying power. 
	              - down(4) - present, but failure indicated." 
	::= { rcChasPowerSupplyEntry 2 } 
 
 
rcChasPowerSupplyDetailTable OBJECT-TYPE 
	SYNTAX        	SEQUENCE OF RcChasPowerSupplyDetailEntry 
	ACCESS        	not-accessible 
	STATUS        	mandatory 
	DESCRIPTION   	"This table contains detailed information about 
			power supplies." 
	::= { rcChasPowerSupply 2 } 
 
rcChasPowerSupplyDetailEntry OBJECT-TYPE 
	SYNTAX        	RcChasPowerSupplyDetailEntry 
	ACCESS        	not-accessible 
	STATUS        	mandatory 
	DESCRIPTION   	"Contains detailae info regarding a power supply 
		      	unit." 
	INDEX  { rcChasPowerSupplyDetailId } 
	::= { rcChasPowerSupplyDetailTable 1 } 
 
RcChasPowerSupplyDetailEntry ::= 
	SEQUENCE { 
		rcChasPowerSupplyDetailId INTEGER, 
		rcChasPowerSupplyDetailType INTEGER, 
		rcChasPowerSupplyDetailSerialNumber DisplayString, 
		rcChasPowerSupplyDetailHardwareRevision DisplayString, 
		rcChasPowerSupplyDetailPartNumber DisplayString 
	} 
 
rcChasPowerSupplyDetailId OBJECT-TYPE 
	SYNTAX        	INTEGER(1..2) 
	ACCESS        	read-only 
	STATUS        	mandatory 
	::= { rcChasPowerSupplyDetailEntry 1 } 
 
rcChasPowerSupplyDetailType OBJECT-TYPE 
        SYNTAX        	INTEGER { 
				ac(1), 
				dc(2) 
		      	} 
        ACCESS        	read-only 
        STATUS        	mandatory 
        ::= { rcChasPowerSupplyDetailEntry 2 } 
 
rcChasPowerSupplyDetailSerialNumber OBJECT-TYPE 
        SYNTAX        DisplayString (SIZE (0..8)) 
        ACCESS        read-only 
        STATUS        mandatory 
        ::= { rcChasPowerSupplyDetailEntry 3 } 
 
rcChasPowerSupplyDetailHardwareRevision OBJECT-TYPE 
        SYNTAX        DisplayString (SIZE (0..8)) 
        ACCESS        read-only 
        STATUS        mandatory 
        ::= { rcChasPowerSupplyDetailEntry 4 } 
 
rcChasPowerSupplyDetailPartNumber OBJECT-TYPE 
        SYNTAX        DisplayString (SIZE (0..6)) 
        ACCESS        read-only 
        STATUS        mandatory 
        ::= { rcChasPowerSupplyDetailEntry 5 } 
 
 
rcCard OBJECT IDENTIFIER ::= { rcChassis 9 } 
 
rcCardTable OBJECT-TYPE 
	SYNTAX        SEQUENCE OF RcCardEntry 
	ACCESS        not-accessible 
	STATUS        mandatory 
	DESCRIPTION   "A table that contains information about the  
                      cards in this chassis.  For those slots that  
                      do not contain a physical card, the table may  
		      be implemented to contain a conceptual row  
                      with the type of physical module set to  
 		      'chasCardEmpty', or it may be implemented to  
		      have no conceptual row instance." 
	::= { rcCard 1 } 
 
rcCardEntry OBJECT-TYPE 
	SYNTAX        RcCardEntry 
	ACCESS        not-accessible 
	STATUS        mandatory 
	DESCRIPTION   "Card attributes" 
	INDEX         { rcCardIndex } 
	::= { rcCardTable 1 } 
 
RcCardEntry ::= 
	SEQUENCE { 
		rcCardIndex INTEGER, 
		rcCardType INTEGER, 
		rcCardSerialNumber DisplayString, 
		rcCardHardwareRevision DisplayString, 
		rcCardAdminStatus INTEGER, 
		rcCardOperStatus INTEGER, 
		rcCardPCMCIAType INTEGER, 
		rcCardPartNumber DisplayString 
	} 
 
rcCardIndex OBJECT-TYPE 
        SYNTAX        	INTEGER (1..8) 
        ACCESS        	read-only 
        STATUS       	mandatory 
        DESCRIPTION   	"A unique value for each module within the chassis. 
                      	This value is determined by the chassis slot number 
                      	where the module is inserted.  Valid entries are 1 
                      	to the value of rcChasNumSlots" 
        ::= { rcCardEntry 1 } 
 
rcCardType OBJECT-TYPE 
        SYNTAX INTEGER  
	{ 
	other(1),                        -- no card installed 
        rcCPU(2),                        -- [1200] CPU Card (A1200) 
        rc8x100BaseTX(3),                -- [1208TX] 8 port (cat 5) (A1200) 
        rc8x100BaseT2(4),                -- [] 8 port (cat 3) (A1200) 
        rc8x100BaseF(5),                 -- [1208FX] 8 port fiber (A1200) 
        rc16x100BaseTX(6),               -- [1216TX] 16 port (cat 5) (A1200) 
        rc8x100BaseTXWG(12),             -- [1108TX] 8 port (half width) (A1100) 
        rc16x100BaseTXWG(13),            -- [1100] 16 port + CPU (A1100) 
        rc4x100BaseFWG(14),              -- [1104FX] 4 port (half width) (A1100) 
        rc12x100BaseTXWG(15),            -- [1050] 12 port + CPU (A1050) 
        rc12x100BaseFBB(16),             -- [] 12 port (A1200) 
        rc8x100BaseFWG(17),              -- [1108FX] 8 port (A1100) 
        rc12x100BaseTX-2x100BaseFBB(18), -- [] 12 port + 2 port (A1200) 
        rc2x155BaseFBB(19),              -- [] 2 sonet port (A1200) 
        rc4x155BaseFBB(20),              -- [] 4 sonet port (A1200) 
        rc16x100BaseFBB(21),             -- [1216FX] 16 port fiber (A1200) 
        rc14x100BaseTX-2x100BaseFBB(22), -- [1216TF] 14 port + 2 port (A1200) 
        rc8x10BaseFBB(23),               -- [1208FL] 8 port fiber low-speed (A1200) 
	rc4xOC3(24),			 -- [1200xx] 4 port OC3 (A1200) 
	rc1xOC12(25),			 -- [1200xx] 1 port OC12 (A1200) 
        rcRMON(26),			 -- [1200xx] RMON (A1200)  
        rc4x1000BaseSXWG(1028),          -- [1150] 1 0 00 000 0100 + CPU (A1150) 
        rc1x1000BaseSXWG(1025),          -- [1101SX] 1 0 00 000 0001 
        rc2x1000BaseSXWG(1026),          -- [1102SX] 1 0 00 000 0010 
        rc1x1000BaseSXRWG(1537),         -- [1101SR] 1 1 00 000 0001 
        rc2x1000BaseSXRWG(1538),         -- [1102SR] 1 1 00 000 0010 
        rc1x1000BaseLXWG(1153),          -- [1101LX] 1 0 01 000 0001 
        rc2x1000BaseLXWG(1154),          -- [1102LX] 1 0 01 000 0010 
        rc2x1000BaseXDWG(1282),          -- [1102XD] 1 0 10 000 0010 
        rc1x1000BaseLXRWG(1665),         -- [1101LR] 1 1 01 000 0001 
        rc2x1000BaseLXRWG(1666),         -- [1102LR] 1 1 01 000 0010 
        rc1x1000BaseSXBB(1041),          -- [1201SX] 1 0 00 001 0001 
        rc2x1000BaseSXBB(1042),          -- [1202SX] 1 0 00 001 0010 
        rc1x1000BaseSXRBB(1553),         -- [1201SR] 1 1 00 001 0001 
        rc2x1000BaseSXRBB(1554),         -- [1202SR] 1 1 00 001 0010 
        rc1x1000BaseLXBB(1169),          -- [1201LX] 1 0 01 001 0001 
        rc2x1000BaseLXBB(1170),          -- [1202LX] 1 0 01 001 0010 
        rc2x1000BaseXDBB(1298),          -- [1202XD] 1 0 10 001 0010 
        rc1x1000BaseLXRBB(1681),         -- [1201LR] 1 1 01 001 0001 
        rc2x1000BaseLXRBB(1682)          -- [1202LR] 1 1 01 001 0010 
	} 
	ACCESS 	      read-only 
	STATUS 	      mandatory 
	DESCRIPTION   "Used to indicate a card type.  Gigabit cards use 
		      an encoded value according to the following rule: 
 
                              +-----+----+----+---+---+---+ 
                      bits  : |31-11| 10 |  9 |8-7|6-4|3-0| 
                              +-----+----+----+---+---+---+ 
                      field : |  a  |  b |  c | d | e | f | 
                              +-----+----+----+---+---+---+ 
 
                             a : not-used 
                             b : 1=gigabit 
                             c : 0=non-redundant,  
                                 1=redundant 
                             d : 0=short-haul,  
                                 1=long-haul,  
                                 2=extra-distance, 
                             e : 0=work-group(f200 & f800) 
                                 1=back-bone(f600 & f1200),  
                             f : 1=1-port, 2=2-port, 4=4-port 
                      " 
	::= { rcCardEntry 2 } 
 
rcCardSerialNumber OBJECT-TYPE 
        SYNTAX        DisplayString (SIZE (0..8)) 
	ACCESS        read-only 
	STATUS        mandatory 
	DESCRIPTION   "Unique serial number for this card." 
	::= { rcCardEntry 3 } 
 
rcCardHardwareRevision OBJECT-TYPE 
	SYNTAX        DisplayString (SIZE (0..8)) 
	ACCESS        read-only 
	STATUS        mandatory 
	DESCRIPTION   "Hardware Version" 
	::= { rcCardEntry 4 } 
 
rcCardAdminStatus OBJECT-TYPE 
        SYNTAX       INTEGER {  
			 up(1), 
         		 down(2), 
			 testing(3) 
                      } 
        ACCESS        read-write  
        STATUS        mandatory 
        DESCRIPTION   "Used to indicate the administrative status of this 
                       card" 
        ::= { rcCardEntry 5 } 
 
rcCardOperStatus OBJECT-TYPE 
	SYNTAX        INTEGER {  
			 up(1), 
         		 down(2), 
			 testing(3), 
			 unknown(4), 
		 	 dormant(5) 
                      } 
	ACCESS        read-only 
	STATUS        mandatory 
	DESCRIPTION   "Used to indicate the operational status of this card." 
	::= { rcCardEntry 6 } 
 
rcCardPCMCIAType OBJECT-TYPE 
        SYNTAX        INTEGER { 
			 none(1), 
			 modem28kbs(2), 
			 flash2meg(3), 
			 flash4meg(4) 
                      } 
        ACCESS        read-only 
        STATUS        mandatory 
        DESCRIPTION   "Used to indicate the type of PCMCIA card currently 
                      installed in this CPU card, if any. 
 
                      For non-CPU cards, this variable has no meaning and 
                      will always be set to none." 
	DEFVAL        { none } 
        ::= { rcCardEntry 7 } 
 
rcCardPartNumber OBJECT-TYPE 
        SYNTAX        	DisplayString (SIZE (0..6)) 
        ACCESS        	read-only 
        STATUS        	mandatory 
        DESCRIPTION   	"Card Part Number" 
        ::= { rcCardEntry 8 } 
 
-- Port Table 
 
rcPort OBJECT IDENTIFIER ::= { rcChassis 10 } 
 
rcPortTable OBJECT-TYPE 
        SYNTAX	      SEQUENCE OF RcPortEntry 
        ACCESS        not-accessible 
        STATUS        mandatory 
        DESCRIPTION   "Port table" 
        ::= { rcPort 1 } 
 
rcPortEntry OBJECT-TYPE 
        SYNTAX        RcPortEntry 
        ACCESS        not-accessible 
        STATUS        mandatory 
        DESCRIPTION   "Entry containing info. for a particular port" 
        INDEX         { rcPortIndex } 
        ::= { rcPortTable 1 } 
 
RcPortEntry ::= SEQUENCE { 
		rcPortIndex                    InterfaceIndex, 
		rcPortType                     INTEGER, 
                rcPortConnectorType            INTEGER, 
		rcPortPerformRouting           TruthValue, 
		rcPortHighPriority             TruthValue, 
                rcPortAction                   INTEGER, 
                rcPortResult                   INTEGER, 
                rcPortPrimaryConnector         INTEGER, 
                rcPortActiveConnector          INTEGER, 
                rcPortBackupConnectorStatus    INTEGER, 
                rcPortAutoNegotiate            TruthValue, 
                rcPortAdminDuplex              INTEGER, 
                rcPortOperDuplex               INTEGER, 
                rcPortAdminSpeed               INTEGER, 
                rcPortOperSpeed                INTEGER, 
		rcPortMltId		       INTEGER, 
		rcPortLocked		       TruthValue, 
		rcPortAutoNegotiationSupported TruthValue, 
		rcPortSingleRoutablePort       TruthValue, 
		rcPortUnknownMacDiscard        TruthValue, 
                rcPortNumStateTransition       Counter 
	} 
 
rcPortIndex OBJECT-TYPE 
        SYNTAX        InterfaceIndex 
        ACCESS        read-only 
        STATUS        mandatory 
        DESCRIPTION   "An index value that uniquely identifies a port. 
                      This value is similar to ifIndex in MIB2." 
        ::= { rcPortEntry 1 } 
 
rcPortType OBJECT-TYPE 
	SYNTAX        INTEGER { 
		         other(0),	     -- no port installed 
		         rc100BaseTX(1),     -- (cat 5) 
		         rc100BaseT2(2),     -- (cat 3) 
		         rc100BaseF(3),	     -- (100 mbps fiber) 
		         rc1000BaseF(4),     -- (1000 mbps fiber) 
		         rc1000BaseDualF(5), -- (fiber - dual connector) 
		         rc10BaseF(6) 	     -- (10 mbps fiber) 
	              } 
	ACCESS        read-only 
	STATUS        mandatory 
	DESCRIPTION   "Port type" 
	::= { rcPortEntry 2 } 
 
rcPortConnectorType OBJECT-TYPE 
        SYNTAX        INTEGER { 
                         nonRedundant(1), -- non-redundant connector type  
                         redundant(2) 	  -- redundant connector type  
                      } 
        ACCESS        read-only 
        STATUS        mandatory 
        DESCRIPTION   "Type of connector installed on this port." 
        DEFVAL        { nonRedundant } 
        ::= { rcPortEntry 3 } 
 
rcPortPerformRouting OBJECT-TYPE 
	SYNTAX 	      TruthValue 
	ACCESS 	      read-write 
        STATUS 	      deprecated 
	DESCRIPTION   "Indicate whether this port should perform 
                      routing" 
	DEFVAL	      { false } 
	::= { rcPortEntry 4 } 
 
rcPortHighPriority OBJECT-TYPE  
        SYNTAX 	      TruthValue 
        ACCESS 	      read-write 
        STATUS 	      mandatory 
        DESCRIPTION   "Indicate whether this port should treated with  
                      high priority" 
	DEFVAL 	      { false } 
        ::= { rcPortEntry 5 } 
 
rcPortAction OBJECT-TYPE 
        SYNTAX        INTEGER { 
                         none(1),            -- none of the following 
                         flushMacFdb(2),     -- flush MAC forwarding table 
                         flushArp(3),        -- flush ARP table 
                         flushIp(4),         -- flush IP route table 
                         flushAll(5),        -- flush all tables 
			 triggerRipUpdate(6) -- manually trigger rip update 
                      } 
        ACCESS        read-write 
        STATUS        mandatory 
        DESCRIPTION   "Port related actions." 
        DEFVAL        { none } 
        ::= { rcPortEntry 6 } 
  
rcPortResult OBJECT-TYPE  
        SYNTAX        	INTEGER {  
                       		none(1),        -- none of the following  
                       	  	inProgress(2),  -- in progress  
                       	  	success(3),     -- success 
                       	  	fail(4)         -- failure  
                      	}  
        ACCESS		read-only  
        STATUS        	mandatory  
        DESCRIPTION   	"Result from the last Vlan action."  
        DEFVAL        	{ none }  
        ::= { rcPortEntry 7 }  
 
rcPortPrimaryConnector OBJECT-TYPE  
        SYNTAX 		INTEGER {  
                		left(1),	-- left side connector 
                		right(2),	-- right side connector  
				other(3) 
        		}  
        ACCESS          read-write  
        STATUS          mandatory  
        DESCRIPTION     "For ports configured with redundant connectors, 
			 this value is used to indicate which connector  
			 should be used as the 'active' connector on this  
			 port the next time the port is placed into the  
			 ifAdminStatus=Up." 
	DEFVAL          { left }  
        ::= { rcPortEntry 8 } 
 
rcPortActiveConnector OBJECT-TYPE 
        SYNTAX        INTEGER { 
                         	left(1),	-- left side connector 
                         	right(2),       -- right side connector 
				other(3) 
                      } 
        ACCESS        read-only 
        STATUS        mandatory  
        DESCRIPTION   "For ports configured with redundant connectors, 
		      this value is used to indicate which connector 
		      is currently the active one.  Only one connector 
		      can be active an anytime." 
        DEFVAL        { left }  
        ::= { rcPortEntry 9 } 
 
rcPortBackupConnectorStatus OBJECT-TYPE 
        SYNTAX 		INTEGER { 
                		up(1),            -- link Up 
                		down(2),          -- link Down 
				other(3) 
        } 
        ACCESS          read-only 
        STATUS          mandatory 
        DESCRIPTION     "Indicate the status of the link attached to the 
		 	 back-up (non-active) connector." 
        ::= { rcPortEntry 10 } 
 
rcPortAutoNegotiate OBJECT-TYPE 
	SYNTAX 	      TruthValue 
	ACCESS 	      read-write 
        STATUS 	      mandatory 
	DESCRIPTION   "Indicate whether this port enabled for auto  
                      negotiations or not." 
	DEFVAL	      { true } 
	::= { rcPortEntry 11 } 
 
rcPortAdminDuplex OBJECT-TYPE 
        SYNTAX 		INTEGER {  
                		half(1),	-- half duplex 
                		full(2)		-- full duplex   
        		}  
	ACCESS 		read-write 
        STATUS 		mandatory 
	DESCRIPTION     "Indicates the port duplex type "	 
	DEFVAL		{ half } 
	::= { rcPortEntry 12 } 
 
rcPortOperDuplex OBJECT-TYPE 
        SYNTAX 		INTEGER {  
                		half(1),	-- half duplex 
                		full(2)		-- full duplex   
        		}  
	ACCESS 		read-only 
        STATUS 		mandatory 
	DESCRIPTION 	"Indicate this port's current duplex value." 
	::= { rcPortEntry 13 } 
 
rcPortAdminSpeed OBJECT-TYPE 
        SYNTAX 		INTEGER {  
				none(0), 
                		mbps10(1),	-- 10Mb/s 
                		mbps100(2),	-- 100Mb/s 
                		mbps1000(3)	-- 1000Mb/s 
        		}  
	ACCESS 		read-write 
        STATUS 		mandatory 
	DESCRIPTION 	"Indicate this port's speed." 
	DEFVAL		{ mbps10 } 
	::= { rcPortEntry 14 } 
 
rcPortOperSpeed OBJECT-TYPE 
        SYNTAX 		INTEGER   
	ACCESS 	      	read-only 
        STATUS 	      	mandatory 
	DESCRIPTION   	"Indicate this port's current speed value." 
	::= { rcPortEntry 15 } 
 
rcPortMltId OBJECT-TYPE 
        SYNTAX 		INTEGER   
	ACCESS 	      	read-only 
        STATUS 	      	mandatory 
	DESCRIPTION   	"Indicate which multi-link trunk (MLT) this port 
		 	is assigned to.  If this port is not associated 
			with any MLT, this value will be set to zero(0)." 
	DEFVAL		{ 0 } 
	::= { rcPortEntry 16 } 
 
rcPortLocked OBJECT-TYPE 
        SYNTAX        	TruthValue 
        ACCESS        	read-only 
        STATUS        	mandatory 
        DESCRIPTION   	"Indicate whether this port is locked."  
        DEFVAL        	{ false } 
        ::= { rcPortEntry 17 } 
 
rcPortAutoNegotiationSupported OBJECT-TYPE 
        SYNTAX        	TruthValue 
        ACCESS        	read-only 
        STATUS        	mandatory 
        DESCRIPTION   	"Indicate whether this port can support  
		      	auto-negotiation."  
        DEFVAL        	{ false } 
        ::= { rcPortEntry 18 } 
 
rcPortSingleRoutablePort OBJECT-TYPE 
        SYNTAX        	TruthValue 
        ACCESS        	read-only 
        STATUS        	mandatory 
        DESCRIPTION   	"Indicate whether this port is a single routable 
		      	port.  If this value is true, the port functions 
			like a traditional router port." 
        DEFVAL        	{ false } 
        ::= { rcPortEntry 19 } 
 
rcPortUnknownMacDiscard OBJECT-TYPE 
        SYNTAX          TruthValue 
        ACCESS          read-write 
        STATUS          mandatory 
        DESCRIPTION     "If rcUnknownMacDiscard is set to True,  
                         then a packet with an unknown source MAC address 
                         is dropped on that port, and other ports then 
                         will discard any packets with this MAC address 
                         in the destination field.   
                         For example,  
                         suppose 11:22:33:44:55:66 is an unknown source MAC, 
                         packets with source MAC 11:22:33:44:55 coming from  
                         this port is discarded, further more, packets with 
                         destination MAC 11:22:33:44:55:66 coming from 
                         other ports are also discarded, unless this address 
                         is later learned on another port or the restriction 
                         ages out." 
 
        DEFVAL          { false } 
        ::= { rcPortEntry 20 } 
 
rcPortNumStateTransition OBJECT-TYPE 
        SYNTAX        	Counter 
        ACCESS        	read-only 
        STATUS        	mandatory 
        DESCRIPTION   	"# state transitions." 
        ::= { rcPortEntry 21 } 
 
 
-- Port Lock Group 
 
rcPortLock OBJECT IDENTIFIER ::= { rcChassis 11 } 
 
rcPortLockEnable OBJECT-TYPE 
        SYNTAX        	TruthValue 
        ACCESS        	read-write 
        STATUS        	mandatory 
        DESCRIPTION   	"Indicate whether the port lock feature is enabled." 
        DEFVAL        	{ false } 
        ::= { rcPortLock 1 } 
 
rcPortLockLockedPorts OBJECT-TYPE 
        SYNTAX        	PortSet 
        ACCESS        	read-write 
        STATUS        	mandatory 
        DESCRIPTION   	"The set of ports that are administratively locked. 
		      	Locked ports cannot be modified in anyway until the 
		      	port is unlocked first." 
        ::= { rcPortLock 2 } 
 
 
-- Additional Chassis Group Variables 
 
rcChasAruMode OBJECT-TYPE 
        SYNTAX        	INTEGER  
			{ 
				aruOne(1), 
				aruTwo(2), 
				aruThree(3) 
			} 
        ACCESS        	read-only 
        STATUS        	mandatory 
        DESCRIPTION   	"The ARU mode the chassis is operating in." 
        ::= { rcChassis 12 } 
 
rcChasQuidMode OBJECT-TYPE 
        SYNTAX        	INTEGER  
			{ 
				quidMixed(1), 
				quidTwo(2), 
				quidThree(3), 
				quidFour(4), 
				quidFive(5) 
			} 
        ACCESS        	read-only 
        STATUS        	mandatory 
        DESCRIPTION   	"The Quid mode the chassis is operating in." 
        ::= { rcChassis 13 } 
 
rcChasEocModeAdminStatus OBJECT-TYPE 
        SYNTAX        	INTEGER  
			{ 
				default(0), 
				aru1Quid4(1), 
				aru2Quid4(2), 
				aru2Quid5(3), 
				aru3Quid4(4), 
				aru3Quid5(5) 
			} 
        ACCESS        	read-write 
        STATUS        	mandatory 
        DESCRIPTION   	"" 
        ::= { rcChassis 14 } 
 
rcChasEocModeOperStatus OBJECT-TYPE 
        SYNTAX        	INTEGER  
			{ 
				default(0), 
				aru1Quid4(1), 
				aru2Quid4(2), 
				aru2Quid5(3), 
				aru3Quid4(4), 
				aru3Quid5(5) 
			} 
        ACCESS        	read-only 
        STATUS        	mandatory 
        DESCRIPTION   	"" 
        ::= { rcChassis 15 } 
 
rcAtmPortLecExt OBJECT IDENTIFIER ::= { rcChassis 40 }

rcAtmPortLecExtTable OBJECT-TYPE
        SYNTAX        	SEQUENCE OF RcAtmPortLecExtEntry
        ACCESS        	not-accessible
        STATUS        	mandatory
        DESCRIPTION   	"An extension to the rcPort table used manage
		      	ATM specific options."
        ::= { rcAtmPortLecExt 1 }
 
rcAtmPortLecExtEntry OBJECT-TYPE
        SYNTAX        	RcAtmPortLecExtEntry
        ACCESS        	not-accessible
        STATUS        	mandatory
        DESCRIPTION   	"An entry in the rcAtmPortLecExtTable."
        INDEX         	{ rcAtmPortLecExtIfIndex }
        ::= { rcAtmPortLecExtTable 1 }
 
RcAtmPortLecExtEntry ::= SEQUENCE {
                rcAtmPortLecExtIfIndex             InterfaceIndex,
                rcAtmPortLecExtLecStatus           TruthValue,
                rcAtmPortLecExtLecState            INTEGER,
                rcAtmPortLecExtVirtualPortId       INTEGER,
                rcAtmPortLecExtElanName            DisplayString (SIZE(0..20)),
                rcAtmPortLecExtVlanId              INTEGER,
                rcAtmPortLecExtDesiredPhysicalPort INTEGER,
                rcAtmPortLecExtActualPhysicalPort  INTEGER,
                rcAtmPortLecExtFailoverEnable  	   TruthValue
        }
 
rcAtmPortLecExtIfIndex OBJECT-TYPE
        SYNTAX        	InterfaceIndex
        ACCESS        	read-only
        STATUS        	mandatory
        DESCRIPTION   	"An index value used to identify a LEC instance.
			Each LEC is treated as a logical port.  Therefore
			each LEC has a unique row in the 'ifTable' and 
			'rcPort' tables."
        ::= { rcAtmPortLecExtEntry 1 }

rcAtmPortLecExtLecStatus OBJECT-TYPE
        SYNTAX          TruthValue
        ACCESS        	read-write
        STATUS        	mandatory
        DESCRIPTION   	"Used to enable/disable the LEC."
 	DEFVAL		{ false }
        ::= { rcAtmPortLecExtEntry 2 }

rcAtmPortLecExtLecState OBJECT-TYPE
        SYNTAX          INTEGER  {
            notactive (1),
            operational (2),
            idle (3),
            error (4),
            unknown (5)
            }
        ACCESS           read-only
        STATUS           mandatory
        DESCRIPTION      "Reflects the current state of the LEC."
    DEFVAL		{ unknown }
        ::= { rcAtmPortLecExtEntry 3 }

rcAtmPortLecExtVirtualPortId OBJECT-TYPE
        SYNTAX           INTEGER  
        ACCESS           read-only
        STATUS           mandatory
        DESCRIPTION      "Reflects the virtual port mapping of the LEC."
        ::= { rcAtmPortLecExtEntry 4 }


rcAtmPortLecExtElanName OBJECT-TYPE
    SYNTAX DisplayString (SIZE(0..20))
    ACCESS read-write
    STATUS mandatory
    DESCRIPTION
        "The ELAN Name this client will use the next time it
         returns to the Initial State."
    ::= { rcAtmPortLecExtEntry 5}

rcAtmPortLecExtVlanId OBJECT-TYPE
        SYNTAX           INTEGER  
        ACCESS           read-only
        STATUS           mandatory
        DESCRIPTION      "Reflects the VLAN Id membership of the LEC.
                          0 indicated no membership. "
    DEFVAL		{ 0 }
        ::= { rcAtmPortLecExtEntry 6 }

rcAtmPortLecExtDesiredPhysicalPort OBJECT-TYPE
        SYNTAX        	INTEGER	{
				a1(1),
				a2(2)
			}
        ACCESS        	read-write
        STATUS        	mandatory
        DESCRIPTION   	"Used to configure the desired physical port this LEC
			instance should be associated with.  Each LEC
			can only be associated with one physical port.
			A physical port can support one or more LEC
			instances.  This object can only be written when
                        the Lec's status (rcAtmPortLecExtLecStatus) is
                        disabled."
	DEFVAL		{ a1 }
        ::= { rcAtmPortLecExtEntry 7 }

rcAtmPortLecExtActualPhysicalPort OBJECT-TYPE
        SYNTAX        	INTEGER	{
				a1(1),
				a2(2)
			}
        ACCESS        	read-only
        STATUS        	mandatory
        DESCRIPTION   	"Used to display the actual physical port 
                        this LEC instance should be associated with.  Each LEC
			can only be associated with one physical port. A physical 
                        port can support one or more LEC
			instances."
	DEFVAL		{ a1 }
        ::= { rcAtmPortLecExtEntry 8 }
 
 
rcAtmPortLecExtFailoverEnable OBJECT-TYPE
	SYNTAX        	TruthValue
        ACCESS        	read-write
        STATUS        	mandatory
        DESCRIPTION   	"Used to configure whether the fail-over feature
			should be enabled/disabled for this LEC instance.  Failover 
                        allows traffic to be moved from a failing port to the other port
                        if it is available.  The rcAtmPortLecExtActualPhysicalPort object
                        is used to identify which physical port is currently carrying a
                        Lec's traffic, while the rcAtmPortLecExtDesiredPhysicalPort object
                        is used to select a Lec's preferred port."
 	DEFVAL		{ false }
        ::= { rcAtmPortLecExtEntry 9 }

 
-- Mirror Group 
 
rcMirrorSaveConfig OBJECT-TYPE 
        SYNTAX        	TruthValue 
        ACCESS        	read-write 
        STATUS        	mandatory 
        DESCRIPTION   	"Control whether Mirror configuration information  
                       	should be saved to NVRAM so mirror settings can  
                       	be automatically reinstalled after a system 
                       	reboot.  
 
                       	Setting rcMirrorSaveConfig to true does not  
                       	immediately save the configuration information. 
                       	The save happens when the rcSysAction variable  
                       	is set to 'saveToNVRAM(4)'." 
        ::= { rcMirror 1 } 
 
rcMirrorByPort OBJECT IDENTIFIER ::= { rcMirror 2 } 
 
rcMirrorByPortEnable OBJECT-TYPE 
        SYNTAX        	TruthValue 
        ACCESS        	read-write 
        STATUS        	mandatory 
        DESCRIPTION   	"Used to indicate whether the mirror by port 
                       	feature is active.  The system can only support  
                       	mirroring on two ports.  When this feature is  
                       	active, all packets received on the port(s)  
                       	specified by rcMirrorSrcPortOne and/or  
                       	rcMirrorSrcPortTwo are copied to rcMirrorDstPort.   
                       	The mirroring operation is non-intrusive."  
	DEFVAL 		{ false } 
        ::= { rcMirrorByPort 1 } 
 
rcMirrorByPortMirrorPort OBJECT-TYPE  
        SYNTAX        	InterfaceIndex  
        ACCESS        	read-write 
        STATUS       	mandatory  
        DESCRIPTION   	"The ifIndex of the port to forward mirrored frames 
			to."  
        ::= { rcMirrorByPort 2 } 
 
rcMirrorByPortEnableMirroredPortOne OBJECT-TYPE 
        SYNTAX        	TruthValue 
        ACCESS        	read-write 
        STATUS        	mandatory 
        DESCRIPTION   	"Used to indicate whether the port specified in 
                       	rcMirrorByPortMirroredPortOne should be mirrored."  
	DEFVAL 		{ false } 
        ::= { rcMirrorByPort 3 } 
 
rcMirrorByPortMirroredPortOne OBJECT-TYPE 
        SYNTAX        	InterfaceIndex 
        ACCESS        	read-write 
        STATUS        	mandatory 
        DESCRIPTION   	"The ifIndex of the port to be mirrored.  That 
		       	is, traffic received on this port will be sent 
		       	to the mirror port."  
        ::= { rcMirrorByPort 4 } 
 
rcMirrorByPortEnableMirroredPortTwo OBJECT-TYPE 
        SYNTAX        	TruthValue 
        ACCESS        	read-write 
        STATUS        	mandatory 
        DESCRIPTION   	"Used to indicate whether the port specified in 
                       	rcMirrorByPortMirroredPortTwo should be mirrored."  
	DEFVAL 		{ false } 
        ::= { rcMirrorByPort 5 } 
 
rcMirrorByPortMirroredPortTwo OBJECT-TYPE 
        SYNTAX        	InterfaceIndex 
        ACCESS        	read-write 
        STATUS        	mandatory 
        DESCRIPTION   	"The ifIndex of the port to be mirrored.  That 
		       	is, traffic received on this port will be sent 
		       	to the mirror port."  
        ::= { rcMirrorByPort 6 } 
  
-- Dip-Switch Group 
 
rcIsolateUnconfigPorts OBJECT-TYPE 
        SYNTAX        TruthValue 
        ACCESS        read-only 
        STATUS        mandatory 
        DESCRIPTION   "Used to indicate whether ports that are unconfigured 
                      should be assigned to the 'isolated' VLAN.  Ports 
                      assigned to the 'isolated' VLAN can only communicate 
                      with the CP port.   If this option is not specified, 
                      unconfigured ports will be assigned to the 'default' 
                      VLAN" 
        ::= { rcDipSwitch 1 } 
 
rcUseFactorySettings OBJECT-TYPE 
        SYNTAX        TruthValue 
        ACCESS        read-only 
        STATUS        mandatory 
        DESCRIPTION   "Used to indicate whether the system should ignore 
                      the configuration information stored in NVRAM when 
                      the system is booted."    
        ::= { rcDipSwitch 2 } 
 
rcHighPriorityMode OBJECT-TYPE 
        SYNTAX        TruthValue 
        ACCESS        read-only 
        STATUS        mandatory 
        DESCRIPTION   "Used to indicate whether the system is configured 
                      to operate in a high priority mode.  The switch can   
                      operate in either a 'best effort' or 'high priority'  
                      mode.  In the 'best effort' setting, the maximum  
                      queue thresholds for the QUIDs are set to 768/768  
                      buffers.  In the 'high priority' mode the setting 
                      is 512/768.  This means that in 'high priority' mode 
                      the normal priority queue can't have more than 512  
                      buffers, while the high priority queue can have up  
                      to 768."  
        ::= { rcDipSwitch 3 } 
 
 
-- Table Size Group 
 
rcTblRmonStatSize OBJECT-TYPE 
        SYNTAX        INTEGER 
        ACCESS        read-only 
        STATUS        mandatory 
        DESCRIPTION   "Used to indicate the current size of the RMON 
                      Statistic table." 
        ::= { rcTblSize 1 } 
 
rcTblRmonHistoryControlSize OBJECT-TYPE 
        SYNTAX        INTEGER 
        ACCESS        read-only 
        STATUS        mandatory 
        DESCRIPTION   "Used to indicate the current size of the RMON   
                      History Control table."  
        ::= { rcTblSize 2 } 
 
rcTblRmonHistoryEnetSize OBJECT-TYPE 
        SYNTAX        INTEGER 
        ACCESS        read-only 
        STATUS        mandatory 
        DESCRIPTION   "Used to indicate the current size of the RMON   
                      History Ethernet table."  
        ::= { rcTblSize 3 } 
 
rcTblRmonAlarmSize OBJECT-TYPE 
        SYNTAX        INTEGER 
        ACCESS        read-only 
        STATUS        mandatory 
        DESCRIPTION   "Used to indicate the current size of the RMON   
                      Alarm table."  
        ::= { rcTblSize 4 } 
 
rcTblRmonEventSize OBJECT-TYPE 
        SYNTAX        INTEGER 
        ACCESS        read-only 
        STATUS        mandatory 
        DESCRIPTION   "Used to indicate the current size of the RMON   
                      Event table."  
        ::= { rcTblSize 5 } 
 
rcTblRmonLogSize OBJECT-TYPE 
        SYNTAX        INTEGER 
        ACCESS        read-only 
        STATUS        mandatory 
        DESCRIPTION   "Used to indicate the current size of the RMON   
                      Log table."  
        ::= { rcTblSize 6 } 
 
rcTblArTblSize OBJECT-TYPE   
        SYNTAX        INTEGER   
        ACCESS        read-only   
        STATUS        mandatory   
        DESCRIPTION   "Used to indicate the size of the Address  
                      Translation (AR) table." 
        ::= { rcTblSize 7 } 
 
 
rcTblArFree OBJECT-TYPE   
        SYNTAX        INTEGER   
        ACCESS        read-only   
        STATUS        mandatory   
        DESCRIPTION   "Used to indicate the number of free 
                      entries that are available in the Address  
                      Translation (AR) table." 
        ::= { rcTblSize 8 } 
 
rcTblArNoSpace OBJECT-TYPE   
        SYNTAX        INTEGER   
        ACCESS        read-only   
        STATUS        mandatory   
        DESCRIPTION   "Used to indicate the number of entries that could 
                      not be added to the Address Translation (AR) table 
                      due to lack of space."   
        ::= { rcTblSize 9 } 
 
rcTblArAdded OBJECT-TYPE 
        SYNTAX        INTEGER 
        ACCESS        read-only 
        STATUS        mandatory 
        DESCRIPTION   "Used to indicate the number of entries added to 
                      the Address Translation (AR) table."  
        ::= { rcTblSize 10 } 
 
rcTblArDeleted OBJECT-TYPE  
        SYNTAX        INTEGER  
        ACCESS        read-only  
        STATUS        mandatory  
        DESCRIPTION   "Used to indicate the number of entries deleted to 
                      the Address Translation (AR) table." 
        ::= { rcTblSize 11 } 
 
rcTblArMacAdded OBJECT-TYPE  
        SYNTAX        INTEGER  
        ACCESS        read-only  
        STATUS        mandatory  
        DESCRIPTION   "Used to indicate the number of MAC entries added to 
                      the Address Translation (AR) table." 
        ::= { rcTblSize 12 } 
 
rcTblArMacDeleted OBJECT-TYPE  
        SYNTAX        INTEGER  
        ACCESS        read-only  
        STATUS        mandatory  
        DESCRIPTION   "Used to indicate the number of MAC entries deleted to 
                      the Address Translation (AR) table." 
        ::= { rcTblSize 13 } 
 
rcTblArMacMoved OBJECT-TYPE  
        SYNTAX        INTEGER  
        ACCESS        read-only  
        STATUS        mandatory  
        DESCRIPTION   "Used to indicate the number of MAC entries moved in  
                      the Address Translation (AR) table." 
        ::= { rcTblSize 14 } 
 
rcTblArIpAdded OBJECT-TYPE  
        SYNTAX        INTEGER  
        ACCESS        read-only  
        STATUS        mandatory  
        DESCRIPTION   "Used to indicate the number of IP entries added to 
                      the Address Translation (AR) table." 
        ::= { rcTblSize 15 } 
 
rcTblArIpDeleted OBJECT-TYPE   
        SYNTAX        INTEGER   
        ACCESS        read-only   
        STATUS        mandatory   
        DESCRIPTION   "Used to indicate the number of IP entries deleted to  
                      the Address Translation (AR) table."     
        ::= { rcTblSize 16 } 
 
rcTblArMcastTblSize OBJECT-TYPE   
        SYNTAX        INTEGER   
        ACCESS        read-only   
        STATUS        mandatory   
        DESCRIPTION   "Used to indicate the size of the Multicast  
                      Address Translation (AR) table." 
        ::= { rcTblSize 17 } 
 
 
rcTblArFreeMcastGroups OBJECT-TYPE   
        SYNTAX        INTEGER   
        ACCESS        read-only   
        STATUS        mandatory   
        DESCRIPTION   "Used to indicate the number of free multicast 
                      groups availabe in the Address Translation (AR)  
                      table." 
        ::= { rcTblSize 18 } 
 
rcTblArIpMcastAdded OBJECT-TYPE   
        SYNTAX        INTEGER   
        ACCESS        read-only   
        STATUS        mandatory   
        DESCRIPTION   "Used to indicate the number of Ip multicast 
                      entries that are added to the Address  
                      Translation (AR) table." 
        ::= { rcTblSize 19 } 
 
rcTblArIpMcastDeleted OBJECT-TYPE   
        SYNTAX        INTEGER   
        ACCESS        read-only   
        STATUS        mandatory   
        DESCRIPTION   "Used to indicate the number of Ip multicast 
                      entries that are deleted from the Address  
                      Translation (AR) table." 
        ::= { rcTblSize 20 } 
 
rcTblArVlanByPortAdded OBJECT-TYPE   
        SYNTAX        INTEGER   
        ACCESS        read-only   
        STATUS        mandatory   
        DESCRIPTION   "Used to indicate the number of VLAN by port 
                      entries that are added to the Address  
                      Translation (AR) table." 
        ::= { rcTblSize 21 } 
 
rcTblArVlanByPortDeleted OBJECT-TYPE   
        SYNTAX        INTEGER   
        ACCESS        read-only   
        STATUS        mandatory   
        DESCRIPTION   "Used to indicate the number of VLAN by port 
                      entries that are deleted from the Address  
                      Translation (AR) table." 
        ::= { rcTblSize 22 } 
 
rcTblArVlanByProtocolAdded OBJECT-TYPE   
        SYNTAX        INTEGER   
        ACCESS        read-only   
        STATUS        mandatory   
        DESCRIPTION   "Used to indicate the number of Vlans by  
                      Protocol Type entries that are added to  
                      the Address Translation (AR) table." 
        ::= { rcTblSize 23 } 
 
rcTblArVlanByProtocolDeleted OBJECT-TYPE   
        SYNTAX        INTEGER   
        ACCESS        read-only   
        STATUS        mandatory   
        DESCRIPTION   "Used to indicate the number of Vlans by  
                      Protocol Type entries that are deleted from  
                      the Address Translation (AR) table." 
        ::= { rcTblSize 24 } 
 
rcTblArVlanByIpSubnetAdded OBJECT-TYPE   
        SYNTAX        INTEGER   
        ACCESS        read-only   
        STATUS        mandatory   
        DESCRIPTION   "Used to indicate the number of VLAN by Ip  
                      entries that are added to the Address  
                      Translation (AR) table." 
        ::= { rcTblSize 25 } 
 
rcTblArVlanByIpSubnetDeleted OBJECT-TYPE   
        SYNTAX        INTEGER   
        ACCESS        read-only   
        STATUS        mandatory   
        DESCRIPTION   "Used to indicate the number of VLAN by Ip  
                      entries that are deleted from the Address  
                      Translation (AR) table." 
        ::= { rcTblSize 26 } 
 
rcTblArIpSubnetsAdded OBJECT-TYPE   
        SYNTAX        INTEGER   
        ACCESS        read-only   
        STATUS        mandatory   
        DESCRIPTION   "Used to indicate the number of Ip subnet 
                      entries that are added to the Address  
                      Translation (AR) table." 
        ::= { rcTblSize 27 } 
 
rcTblArIpSubnetsDeleted OBJECT-TYPE   
        SYNTAX        INTEGER   
        ACCESS        read-only   
        STATUS        mandatory   
        DESCRIPTION   "Used to indicate the number of Ip subnet  
                      entries that are deleted from the Address  
                      Translation (AR) table." 
        ::= { rcTblSize 28 } 
 
rcTblArRsvpsAdded OBJECT-TYPE   
        SYNTAX        INTEGER   
        ACCESS        read-only   
        STATUS        mandatory   
        DESCRIPTION   "Used to indicate the number of RSVP 
                      entries that are added to the Address  
                      Translation (AR) table." 
        ::= { rcTblSize 29 } 
 
rcTblArRsvpsDeleted OBJECT-TYPE   
        SYNTAX        INTEGER   
        ACCESS        read-only   
        STATUS        mandatory   
        DESCRIPTION   "Used to indicate the number of RSVP 
                      entries that are deleted from the Address  
                      Translation (AR) table." 
        ::= { rcTblSize 30 } 
 
 
rcTblBrdgFdbSize OBJECT-TYPE   
        SYNTAX        INTEGER   
        ACCESS        read-only   
        STATUS        mandatory   
        DESCRIPTION   "Used to indicate the number of entries in the  
                      dot1d forwarding database table."     
        ::= { rcTblSize 31 } 
 
rcTblBrdgStaticSize OBJECT-TYPE   
        SYNTAX        INTEGER   
        ACCESS        read-only   
        STATUS        mandatory   
        DESCRIPTION   "Used to indicate the number of entries in the  
                      dot1d Static Address Filtering table."     
        ::= { rcTblSize 32 } 
 
rcTblIpAddrSize OBJECT-TYPE   
        SYNTAX        INTEGER   
        ACCESS        read-only   
        STATUS        mandatory   
        DESCRIPTION   "Used to indicate the number of entries in the  
                      IP Address table."     
        ::= { rcTblSize 33 } 
 
rcTblIpForwardingSize OBJECT-TYPE   
        SYNTAX        INTEGER   
        ACCESS        read-only    
        STATUS        mandatory    
        DESCRIPTION   "Used to indicate the number of entries in the  
                      IP Forwarding table."         
        ::= { rcTblSize 34 } 
 
rcTblIpNetToMediaSize OBJECT-TYPE   
        SYNTAX        INTEGER   
        ACCESS        read-only    
        STATUS        mandatory    
        DESCRIPTION   "Used to indicate the number of entries in the  
                      IP Net-to-media table."         
        ::= { rcTblSize 35 } 
 
 
-- IP Group 
 
rcIpConf OBJECT IDENTIFIER ::= { rcIp 1 } 
 
-- IP Configuration Table 
 
rcIpConfTable OBJECT-TYPE 
        SYNTAX        SEQUENCE OF RcIpConfEntry 
        ACCESS        not-accessible 
        STATUS        mandatory 
        DESCRIPTION   "A table used to maintain IP routing information  
                      for a particular interface." 
        ::= { rcIpConf 1 } 
  
rcIpConfEntry OBJECT-TYPE 
        SYNTAX        RcIpConfEntry 
        ACCESS        not-accessible 
        STATUS        mandatory 
        DESCRIPTION   "Entry containing IP routing information.  An entry 
                      is automatically created in this table when routing  
		      is enabled for an interface -or- when an ip address  
                      is configured on an interface." 
        INDEX         { rcIpConfIfIndex } 
        ::= { rcIpConfTable 1 } 
  
RcIpConfEntry ::= SEQUENCE { 
                rcIpConfIfIndex               InterfaceIndex, 
                rcIpConfAdvertDefRte          TruthValue, 
                rcIpConfAcceptDefRte          TruthValue, 
		rcIpConfRowStatus             RowStatus, 
                rcIpConfRipEnable             TruthValue, 
                rcIpConfOspfEnable            TruthValue, 
                rcIpConfIgmpEnable            TruthValue, 
                rcIpConfAddrAssigned          TruthValue, 
                rcIpConfDhcpEnable            TruthValue, 
                rcIpConfTriggeredUpdateEnable TruthValue, 
                rcIpConfRipAutoAggrerateEnable TruthValue, 
                rcIpConfRipGenerateDefaultRoute TruthValue 
        } 
 
rcIpConfIfIndex OBJECT-TYPE 
        SYNTAX        InterfaceIndex (0..4094) 
        ACCESS        read-only 
        STATUS        mandatory 
        DESCRIPTION   "An unique value to identify a physical interface  
 		      or a logical interface (VLAN)." 
        ::= { rcIpConfEntry 1 } 
 
rcIpConfAdvertDefRte OBJECT-TYPE 
        SYNTAX        TruthValue 
        ACCESS        read-write 
        STATUS        mandatory 
        DESCRIPTION   "Used to indicate whether this interface should 
		      advertize a RIP default route."  
        ::= { rcIpConfEntry 2 } 
 
rcIpConfAcceptDefRte OBJECT-TYPE 
        SYNTAX        TruthValue 
        ACCESS        read-write 
        STATUS        mandatory 
        DESCRIPTION   "Used to indicate whether this interface should 
		      accept a RIP default route." 
        ::= { rcIpConfEntry 3 } 
 
rcIpConfRowStatus OBJECT-TYPE 
        SYNTAX        RowStatus 
        ACCESS        read-write 
        STATUS        mandatory 
        DESCRIPTION   "Row status for this entry." 
        ::= { rcIpConfEntry 4 } 
 
rcIpConfRipEnable OBJECT-TYPE 
        SYNTAX        TruthValue 
        ACCESS        read-write 
        STATUS        mandatory 
        DESCRIPTION   "Enable or disable RIP routing on the specified 
                      interface." 
        ::= { rcIpConfEntry 5 } 
  
rcIpConfOspfEnable OBJECT-TYPE 
        SYNTAX        TruthValue 
        ACCESS        read-write 
        STATUS        mandatory 
        DESCRIPTION   "Enable or disable OSPF routing on the specified 
                      interface." 
        ::= { rcIpConfEntry 6 } 
  
rcIpConfIgmpEnable OBJECT-TYPE 
        SYNTAX        TruthValue 
        ACCESS        read-write 
        STATUS        mandatory 
        DESCRIPTION   "Enable or disable IGMP on the specified 
                      interface." 
        ::= { rcIpConfEntry 7 } 
  
rcIpConfAddrAssigned OBJECT-TYPE 
        SYNTAX        TruthValue 
        ACCESS        read-only 
        STATUS        mandatory 
        DESCRIPTION   "Indicate whether IpAddress has been assigned  
                      for this interface." 
        ::= { rcIpConfEntry 8 } 
 
rcIpConfDhcpEnable OBJECT-TYPE 
        SYNTAX        TruthValue 
        ACCESS        read-write 
        STATUS        mandatory 
        DESCRIPTION   "Enable or disable DHCP on the specified 
                      interface." 
        ::= { rcIpConfEntry 9 } 
 
rcIpConfTriggeredUpdateEnable OBJECT-TYPE 
        SYNTAX        TruthValue 
        ACCESS        read-write 
        STATUS        mandatory 
        DESCRIPTION   "Used to indicate whether the RIP triggered update 
		      feature should be enabled on this interface."  
        ::= { rcIpConfEntry 10 } 
  
rcIpConfRipAutoAggrerateEnable OBJECT-TYPE 
        SYNTAX        TruthValue 
        ACCESS        read-write 
        STATUS        mandatory 
        DESCRIPTION   "Used to indicate whether the auto aggregation  
		      feature should be enabled on this interface."  
        ::= { rcIpConfEntry 11 } 
  
rcIpConfRipGenerateDefaultRoute OBJECT-TYPE 
        SYNTAX        TruthValue 
        ACCESS        read-write 
        STATUS        mandatory 
        DESCRIPTION   "Used to indicate whether to generate a default 
		      RIP route	on this interface."  
        ::= { rcIpConfEntry 12 } 
  
 
-- Ospf Configuration Table 
  
rcIpConfOspfTable OBJECT-TYPE 
        SYNTAX        SEQUENCE OF RcIpConfOspfEntry 
        ACCESS        not-accessible 
        STATUS        mandatory 
        DESCRIPTION   "A table used to maintain OSPF information 
                      for a particular interface." 
        ::= { rcIpConf 2 } 
  
rcIpConfOspfEntry OBJECT-TYPE 
        SYNTAX        RcIpConfOspfEntry 
        ACCESS        not-accessible 
        STATUS        mandatory 
        DESCRIPTION   "Entry containing OSPF information.  An entry is 
                      automatically created in this table when routing  
		      is enabled for an interface -or- when an ip address  
                      is configured on an interface."  
        INDEX         { rcIpConfOspfIfIndex } 
        ::= { rcIpConfOspfTable 1 } 
  
RcIpConfOspfEntry ::= SEQUENCE { 
                rcIpConfOspfIfIndex           InterfaceIndex, 
                rcIpConfOspfRtrPriority       INTEGER, 
                rcIpConfOspfMetric            INTEGER, 
                rcIpConfOspfAuthKey           DisplayString, 
                rcIpConfOspfRowStatus         RowStatus, 
                rcIpConfOspfHelloInterval     INTEGER, 
                rcIpConfOspfRtrDeadInterval   INTEGER, 
                rcIpConfOspfIfAreaId          IpAddress, 
                rcIpConfOspfAuthType          INTEGER 
        } 
  
rcIpConfOspfIfIndex OBJECT-TYPE 
        SYNTAX        InterfaceIndex (0..4094) 
        ACCESS        read-only 
        STATUS        mandatory 
        DESCRIPTION   "An unique value to identify a physical interface  
 		      or a logical interface (VLAN)." 
        ::= { rcIpConfOspfEntry 1 } 
 
rcIpConfOspfRtrPriority OBJECT-TYPE 
        SYNTAX        INTEGER (0..'FF'h) 
        ACCESS        read-write 
        STATUS        mandatory 
        DESCRIPTION   "The priority of this interface.  Used in multi- 
                      access networks, this field is used in the 
                      designated router election algorithm.  The value 0 
                      signifies that the router is not eligible to become 
                      the designated router on this particular network. 
                      In the event of a tie in this value, routers will 
                      use their router id as a tie breaker." 
        DEFVAL        { 1 } 
        ::= { rcIpConfOspfEntry 2 } 
  
rcIpConfOspfMetric OBJECT-TYPE 
        SYNTAX        INTEGER (0..'FFFF'h) 
        ACCESS        read-write 
        STATUS        mandatory 
        DESCRIPTION   "The metric for this type of service (TOS) on this 
                      interface.  The default value of the TOS 0 Metric 
                      is (10^9 / ifSpeed). The value FFFF means 'no route  
		      via this TOS'. A value of 0 means the interface speed  
                      (rcIpConfOspfDefaultMetric) will be used as metric  
		      value, when the state of the interface is up."  
        DEFVAL        { 0 } 
        ::= { rcIpConfOspfEntry 3 } 
  
rcIpConfOspfAuthKey OBJECT-TYPE 
        SYNTAX        DisplayString (SIZE(8)) 
        ACCESS        read-write 
        STATUS        mandatory 
        DESCRIPTION   "The Authentication Key.  If the Area's 
                      Authorization Type is simplePassword, and the key 
                      length is shorter than 8 octets, the agent will 
                      left adjust and zero fill to 8 octets.  When read, 
                      ospfIfAuthKey always returns an Octet String of 
                      length zero." 
        REFERENCE     "OSPF Version 2, Section 9 The Interface Data 
                      Structure" 
        ::= { rcIpConfOspfEntry 4 } 
 
rcIpConfOspfRowStatus OBJECT-TYPE 
        SYNTAX        RowStatus 
        ACCESS        read-write 
        STATUS        mandatory 
        DESCRIPTION   "Row status for this entry." 
        ::= { rcIpConfOspfEntry 5 } 
 
rcIpConfOspfHelloInterval OBJECT-TYPE 
        SYNTAX        INTEGER (1..'FFFF'h) 
        ACCESS        read-write 
        STATUS        mandatory 
        DESCRIPTION   "The length of time, in seconds, between the  
                      Hello packets that the router sends on the  
                      interface. This value must be the same for all 
                      routers attached to a common network." 
        DEFVAL        { 10 } 
        ::= { rcIpConfOspfEntry 6 } 
 
rcIpConfOspfRtrDeadInterval OBJECT-TYPE 
        SYNTAX        INTEGER (1..'7FFFFFFF'h) 
        ACCESS        read-write 
        STATUS        mandatory 
        DESCRIPTION   "The number of seconds that a router's Hello  
                      packets have not been seen before it's  
                      neighbors declare the router down. This should 
                      be some multiple of the Hello interval. This  
                      value must be the same for all routers attached 
                      to a common network." 
        DEFVAL        { 40 } 
        ::= { rcIpConfOspfEntry 7 } 
 
rcIpConfOspfIfAreaId OBJECT-TYPE 
         SYNTAX        IpAddress 
         ACCESS        read-write 
         STATUS        mandatory 
         DESCRIPTION   "A 32-bit integer uniquely identifying the area to 
                       which the interface connects.  Area ID 0.0.0.0 is used 
                       for the OSPF backbone." 
         DEFVAL   { '00000000'H }    -- 0.0.0.0 
         ::= { rcIpConfOspfEntry 8 } 
 
rcIpConfOspfAuthType OBJECT-TYPE 
         SYNTAX        INTEGER { 
                           none (0), 
                           simplePassword (1), 
                           md5 (2) 
                            
                       } 
        ACCESS         read-write 
        STATUS         mandatory 
        DESCRIPTION    "The authentication type specified for  an 
interface.    
                       Additional  authentication types may be assigned 
locally." 
        REFERENCE      "OSPF Version 2, Appendix E Authentication" 
        DEFVAL { 0 }        -- no authentication, by default 
        ::= { rcIpConfOspfEntry 9 } 
 
  
-- Ospf Cost Grp 
 
rcIpConfOspfDefaultMetric   OBJECT IDENTIFIER       ::= { rcIpConf 3 } 
  
rcIpConfOspfDefaultMetric10MegPort OBJECT-TYPE 
        SYNTAX        INTEGER (1..'FFFF'h) 
        ACCESS        read-write 
        STATUS        mandatory 
        DESCRIPTION   "Used to indicate the cost associated with 
                      10Meg Interface(Port)." 
        ::= { rcIpConfOspfDefaultMetric 1 } 
  
rcIpConfOspfDefaultMetric100MegPort OBJECT-TYPE 
        SYNTAX        INTEGER (1..'FFFF'h) 
        ACCESS        read-write 
        STATUS        mandatory 
        DESCRIPTION   "Used to indicate the cost associated with 
                      100Meg Interface(Port)." 
        ::= { rcIpConfOspfDefaultMetric 2 } 
  
rcIpConfOspfDefaultMetric1000MegPort OBJECT-TYPE 
        SYNTAX        INTEGER (1..'FFFF'h) 
        ACCESS        read-write 
        STATUS        mandatory 
        DESCRIPTION   "Used to indicate the cost associated with 
                      1000Meg Interface(Port)." 
        ::= { rcIpConfOspfDefaultMetric 3 } 
 
rcIpConfOspf   OBJECT IDENTIFIER       ::= { rcIpConf 4 } 
 
  
rcIpConfOspfTrapEnable  OBJECT-TYPE 
        SYNTAX        TruthValue 
        ACCESS        read-write 
        STATUS        mandatory 
        DESCRIPTION   "Used to indicate whether Ospf Traps should be sent." 
        ::= { rcIpConfOspf 1 } 
 
rcIpConfOspfAutoVirtLinkEnable  OBJECT-TYPE 
        SYNTAX        TruthValue 
        ACCESS        read-write 
        STATUS        mandatory 
        DESCRIPTION   "Used to indicate whether auto virtual link  
                      creation is enabled or not. If set to true 
                      OSPF will create virtual links between  
                      ABRs whether it is needed or not, but adjacency 
                      will established only when one of the ABR  
                      losses connection to backbone area. If set to 
                      false then it is user resposibity to create 
                      virtual link whenever needed." 
	DEFVAL	      { false } 
        ::= { rcIpConfOspf 2 } 
 
rcIpConfOspfSpfHoldDownTime OBJECT-TYPE 
         SYNTAX   INTEGER (3..60) 
         ACCESS   read-write 
         STATUS   mandatory 
         DESCRIPTION   "The SPF Hold Down Timer value. The SPF will run 
                        at most once per hold down timer value." 
         DEFVAL  { 10 } 
         ::= { rcIpConfOspf 3 } 
 
 
rcIpConfGlobal   OBJECT IDENTIFIER       ::= { rcIpConf 6 } 
 
rcIpConfGlobalRipHoldDownTime OBJECT-TYPE 
        SYNTAX	      INTEGER (0..360) 
        ACCESS        read-write 
        STATUS        mandatory 
        DESCRIPTION   "Used to set the system-wide RIP hold down time 
		      in seconds." 
        DEFVAL        { 180 } 
        ::= { rcIpConfGlobal 1 } 
 
 
-- Ospf Area Table 
  
rcIpConfOspfAreaTable OBJECT-TYPE 
        SYNTAX        SEQUENCE OF RcIpConfOspfAreaEntry 
        ACCESS        not-accessible 
        STATUS        mandatory 
        DESCRIPTION   "A table used to maintain OSPF information 
                      for a particular Area." 
        ::= { rcIpConf 7 } 
  
rcIpConfOspfAreaEntry OBJECT-TYPE 
        SYNTAX        RcIpConfOspfAreaEntry 
        ACCESS        not-accessible 
        STATUS        mandatory 
        DESCRIPTION   "Entry containing OSPF Area configuration  
                      information.  An entry is automatically created  
                      in this table when an area is configured through  
                      ospfAreaTable in (rfc1253rcc.mib)." 
        INDEX         { rcIpConfOspfAreaId } 
        ::= { rcIpConfOspfAreaTable 1 } 
  
RcIpConfOspfAreaEntry ::= SEQUENCE { 
                rcIpConfOspfAreaId              IpAddress, 
                rcIpConfOspfAreaImportSummary   TruthValue, 
                rcIpConfOspfAreaActiveIfCount   INTEGER 
        } 
  
rcIpConfOspfAreaId OBJECT-TYPE 
        SYNTAX        IpAddress 
        ACCESS        read-only 
        STATUS        mandatory 
        DESCRIPTION   "An unique value to identify an area. Area ID 
 		      0.0.0.0 is used for the OSPF backbone." 
        ::= { rcIpConfOspfAreaEntry 1 } 
 
rcIpConfOspfAreaImportSummary OBJECT-TYPE 
        SYNTAX        TruthValue 
        ACCESS        read-write 
        STATUS        mandatory 
        DESCRIPTION   "The area's support for importing Summary  
                      advertisements into a stub area. This field 
                      should be used only if ospfImportASExtern is 
                      set to FALSE" 
        DEFVAL        { true } 
        ::= { rcIpConfOspfAreaEntry 2 } 
  
rcIpConfOspfAreaActiveIfCount OBJECT-TYPE 
        SYNTAX        INTEGER  
        ACCESS        read-only 
        STATUS        mandatory 
        DESCRIPTION   "This variable displays the number of active 
                      interfaces configured in this area. An area 
                      cannot be deleted if this value is > 0." 
        ::= { rcIpConfOspfAreaEntry 3 } 
  
-- IP Address Table 
 
rcIpAddrTable OBJECT-TYPE 
        SYNTAX        SEQUENCE OF RcIpAddrEntry 
        ACCESS        not-accessible 
        STATUS        mandatory 
        DESCRIPTION   "The table of addressing information relevant to 
                      this entity's IP addresses. 
 
                      This table is identical to the ipAddrTable in  
                      MIB2 except the columns rcIpAdEntIfIndex and  
                      rcIpAdEntAddr are reversed.  Also, the table  
                      is indexed by both these variables." 
	::= { rcIp 2 } 
 
rcIpAddrEntry OBJECT-TYPE 
	SYNTAX        RcIpAddrEntry 
	ACCESS 	      not-accessible 
	STATUS 	      mandatory 
	DESCRIPTION   "The addressing information for one of this 
                      entity's IP addresses." 
	INDEX         { rcIpAdEntIfIndex, rcIpAdEntAddr } 
	::= { rcIpAddrTable 1 } 
 
RcIpAddrEntry ::= 
    	SEQUENCE { 
        	rcIpAdEntIfIndex InterfaceIndex, 
	        rcIpAdEntAddr IpAddress, 
	        rcIpAdEntNetMask IpAddress, 
	        rcIpAdEntBcastAddrFormat INTEGER, 
	        rcIpAdEntReasmMaxSize INTEGER (0..65535), 
                rcIpAdEntRowStatus RowStatus  
    	} 
 
rcIpAdEntIfIndex OBJECT-TYPE 
   	SYNTAX        InterfaceIndex 
  	ACCESS        read-only 
  	STATUS        mandatory 
	DESCRIPTION   "The index value which uniquely identifies the 
                      interface to which this entry is applicable.  The 
                      interface identified by a particular value of this 
                      index is the same interface as identified by the 
                      same value of ifIndex." 
	::= { rcIpAddrEntry 1 } 
 
rcIpAdEntAddr OBJECT-TYPE 
	SYNTAX        IpAddress 
        ACCESS        read-only 
        STATUS        mandatory 
        DESCRIPTION   "The IP address to which this entry's addressing 
                      information pertains." 
	::= { rcIpAddrEntry 2 } 
 
rcIpAdEntNetMask OBJECT-TYPE 
        SYNTAX        IpAddress 
        ACCESS        read-write 
        STATUS        mandatory 
        DESCRIPTION   "The subnet mask associated with the IP address of 
                      this entry.  The value of the mask is an IP 
                      address with all the network bits set to 1 and all 
                      the hosts bits set to 0." 
	::= { rcIpAddrEntry 3 } 
 
rcIpAdEntBcastAddrFormat OBJECT-TYPE 
        SYNTAX        INTEGER { 
			 zeros(0),	-- use zeros 
			 ones(1)	-- use ones 
		      } 
        ACCESS        read-only 
        STATUS        mandatory 
        DESCRIPTION   "The IP broadcast address format used on this  
                      interface." 
	::= { rcIpAddrEntry 4 } 
 
rcIpAdEntReasmMaxSize OBJECT-TYPE 
        SYNTAX        INTEGER (0..65535) 
        ACCESS        read-only 
        STATUS        mandatory 
        DESCRIPTION   "The size of the largest IP datagram which this 
                      entity can re-assemble from incoming IP fragmented 
                      datagrams received on this interface." 
        ::= { rcIpAddrEntry 5 } 
 
rcIpAdEntRowStatus OBJECT-TYPE 
        SYNTAX        RowStatus 
        ACCESS        read-write 
        STATUS        mandatory 
        DESCRIPTION   "Used to create/delete entries" 
        ::= { rcIpAddrEntry 6 } 
 
-- FlowContorl Group 
 
rcIpFlowTable OBJECT-TYPE 
        SYNTAX        SEQUENCE OF RcIpFlowEntry 
        ACCESS        not-accessible 
        STATUS        mandatory 
        DESCRIPTION   "IpFlow Table.  This table contain entries that 
		      correspond to RSVP records in the switching 
		      fabric Address Resolution table. 
 
		      A connection that has a matching entry in this  
                      table will be processed with a higher priority  
                      than connections that do not have an entry." 
        ::= { rcIp 3 } 
 
rcIpFlowEntry OBJECT-TYPE 
        SYNTAX        RcIpFlowEntry 
        ACCESS        not-accessible 
        STATUS        mandatory 
        DESCRIPTION   "Proprietary flow control variables." 
        INDEX         { rcIpFlowSrcIpAddress, rcIpFlowSrcIpPort, 
		        rcIpFlowDstIpAddress, rcIpFlowDstIpPort, 
		        rcIpFlowProtocol } 
        ::= { rcIpFlowTable 1 } 
 
RcIpFlowEntry ::= 
        SEQUENCE { 
                rcIpFlowSrcIpAddress IpAddress, 
                rcIpFlowSrcIpPort    INTEGER, 
                rcIpFlowDstIpAddress IpAddress, 
                rcIpFlowDstIpPort    INTEGER, 
		rcIpFlowProtocol     INTEGER, 
		rcIpFlowRowStatus    RowStatus 
        } 
 
rcIpFlowSrcIpAddress OBJECT-TYPE 
        SYNTAX        IpAddress 
        ACCESS        read-only 
        STATUS        mandatory 
        DESCRIPTION   "The source IP address of an IP packet." 
        ::= { rcIpFlowEntry 1 } 
 
rcIpFlowSrcIpPort OBJECT-TYPE 
        SYNTAX        INTEGER (0..65535) 
        ACCESS        read-only 
        STATUS        mandatory 
        DESCRIPTION   "The source port of an IP packet.  A zero value  
                      in this field is used as a wildcard value." 
        DEFVAL 	      { 0 } 
        ::= { rcIpFlowEntry 2 } 
 
rcIpFlowDstIpAddress OBJECT-TYPE 
        SYNTAX        IpAddress 
        ACCESS        read-only 
        STATUS        mandatory 
        DESCRIPTION   "The destination IP address of an IP packet." 
        ::= { rcIpFlowEntry 3 } 
 
rcIpFlowDstIpPort OBJECT-TYPE 
        SYNTAX        INTEGER (0..65535) 
        ACCESS        read-only 
        STATUS        mandatory 
        DESCRIPTION   "The destination port of an IP packet.  A zero 
                      value in this field is used as a wildcard value." 
	DEFVAL	      { 0 } 
        ::= { rcIpFlowEntry 4 } 
 
rcIpFlowProtocol OBJECT-TYPE 
        SYNTAX 	      INTEGER { 
                         ip(4),	        -- ip 
			 tcp(6),	-- tcp 
			 udp(17)	-- udp 
        	      } 
        ACCESS        read-only 
        STATUS        mandatory 
        DESCRIPTION   "The protocol type of an IP packet.  A zero value 
                      in this field is used as a wildcard value." 
	DEFVAL 	      { ip } 
        ::= { rcIpFlowEntry 5 } 
 
rcIpFlowRowStatus OBJECT-TYPE 
        SYNTAX        RowStatus 
        ACCESS        read-write 
        STATUS        mandatory 
        DESCRIPTION   "Status of entry." 
        ::= { rcIpFlowEntry 6 } 
 
 
-- Routing group 
 
rcIpRouting OBJECT IDENTIFIER ::= { rcIp 4 } 
 
 
-- rcIpRouting/rcIpRoutingRedistributeRipToOspf Group 
 
rcIpRoutingRedistributeRipToOspf OBJECT IDENTIFIER ::= {rcIpRouting 1} 
 
rcIpRoutingRedistributeRipToOspfEnable OBJECT-TYPE 
        SYNTAX        TruthValue 
        ACCESS        read-write 
        STATUS        obsolete 
        DESCRIPTION   "Used to indicate whether or not to Redistribute 
                      RIP routes to OSPF." 
        DEFVAL        { false } 
        ::= { rcIpRoutingRedistributeRipToOspf 1 } 
  
rcIpRoutingRedistributeRipToOspfExplicitMetric OBJECT-TYPE 
        SYNTAX        INTEGER (1..'FFFF'h) 
        ACCESS        read-write 
        STATUS        obsolete 
        DESCRIPTION   "Value of metric that is used to translate the 
                      RIP route to OSPF." 
        DEFVAL        { 1 } 
        ::= { rcIpRoutingRedistributeRipToOspf 2 } 
 
rcIpRoutingRedistributeRipToOspfUseExplicitMetric OBJECT-TYPE 
        SYNTAX        TruthValue 
        ACCESS        read-write 
        STATUS        obsolete 
        DESCRIPTION   "Used to indicate whether or not to use the user 
                      specified default metric for redistributing 
                      RIP routes to OSPF." 
        DEFVAL        { false } 
        ::= { rcIpRoutingRedistributeRipToOspf 3 } 
  
rcIpRoutingRedistributeRipToOspfExternalMetricType  OBJECT-TYPE 
        SYNTAX        INTEGER { 
                         type1(1),          -- extenal metric type1 
                         type2(2)           -- extenal metric type2 
                      } 
        ACCESS        read-write 
        STATUS        obsolete 
        DESCRIPTION   "Used to configure the metric type of the 
                      distributed routes to OSPF domain. 
                      type1 means the metric is comparable directly 
                      to the link state metric  
                      (cost = internal cost + external cost).  
                      type2 means the metric is considered larger  
                      than any link state metric (cost = external  
                      cost)." 
        DEFVAL        { type2 } 
        ::= { rcIpRoutingRedistributeRipToOspf 4 } 
 
 
-- rcIpRouting/rcIpRoutingRedistributeOspfToRip Group 
 
rcIpRoutingRedistributeOspfToRip OBJECT IDENTIFIER ::= {rcIpRouting 2} 
 
rcIpRoutingRedistributeOspfToRipEnable OBJECT-TYPE 
        SYNTAX        TruthValue 
        ACCESS        read-write 
        STATUS        obsolete 
        DESCRIPTION   "Used to indicate whether or not to redistribute  
                      OSPF routes to RIP." 
        DEFVAL        { false } 
        ::= { rcIpRoutingRedistributeOspfToRip 1 } 
 
rcIpRoutingRedistributeOspfToRipExplicitMetric OBJECT-TYPE 
        SYNTAX        INTEGER (1..16) 
        ACCESS        read-write 
        STATUS        obsolete 
        DESCRIPTION   "Value of metric that is used to translate the 
                      OSPF route to RIP." 
        DEFVAL        { 1 } 
        ::= { rcIpRoutingRedistributeOspfToRip 2 } 
  
rcIpRoutingRedistributeOspfToRipUseExplicitMetric OBJECT-TYPE 
        SYNTAX        TruthValue 
        ACCESS        read-write 
        STATUS        obsolete 
        DESCRIPTION   "Used to indicate whether or not to use the user 
                      specified default metric for redistributing 
                      OSPF routes to RIP." 
        DEFVAL        { true } 
        ::= { rcIpRoutingRedistributeOspfToRip 3 } 
 
-- rcIpRouting/rcIpRoutingRedistributeDirectToOspf Group 
 
rcIpRoutingRedistributeDirectToOspf OBJECT IDENTIFIER ::= {rcIpRouting 3} 
 
rcIpRoutingRedistributeDirectToOspfEnable  OBJECT-TYPE 
        SYNTAX        TruthValue 
        ACCESS        read-write 
        STATUS        obsolete 
        DESCRIPTION   "Used to indicate whether directly connected 
                      networks through non-ospf interfaces are 
                      distributed to OSPF database or not. If  
                      set to true all the static routes 
                      will be added as external routes to OSPF 
                      routing domain, provided the router is 
                      configured as AS Border router. Also originates 
                      asExtern link LSA." 
        DEFVAL        { false } 
        ::= { rcIpRoutingRedistributeDirectToOspf 1 } 
  
rcIpRoutingRedistributeDirectToOspfMethod OBJECT-TYPE 
        SYNTAX        INTEGER { 
                         usePortSpeed(1),        
                         useExplicitMetric(2)   
                      } 
        ACCESS        read-write 
        STATUS        obsolete 
        DESCRIPTION   "Used to indicate whether or not to use the user 
                      specified default metric for redistributing 
                      direct routes to OSPF." 
        DEFVAL        { usePortSpeed } 
        ::= { rcIpRoutingRedistributeDirectToOspf 2 } 
 
rcIpRoutingRedistributeDirectToOspfExplicitMetric OBJECT-TYPE 
        SYNTAX        INTEGER (1..'FFFF'h) 
        ACCESS        read-write 
        STATUS        obsolete 
        DESCRIPTION   "Value of metric that is used to translate the 
                      routes to directly connected networks to OSPF." 
        DEFVAL        { 1 } 
        ::= { rcIpRoutingRedistributeDirectToOspf 3 } 
  
rcIpRoutingRedistributeDirectToOspfExternalMetricType  OBJECT-TYPE 
        SYNTAX        INTEGER { 
                         type1(1),          -- extenal metric type1 
                         type2(2)           -- extenal metric type2 
                      } 
        ACCESS        read-write 
        STATUS        obsolete 
        DESCRIPTION   "Used to configure the metric type of the 
                      distributed routes to OSPF domain. 
                      type1 means the metric is comparable directly 
                      to the link state metric  
                      (cost = internal cost + external cost).  
                      type2 means the metric is considered larger  
                      than any link state metric (cost = external  
                      cost)." 
        DEFVAL        { type1 } 
        ::= { rcIpRoutingRedistributeDirectToOspf 4 } 
 
 
-- rcIpRouting/rcIpRoutingRedistributeStaticToOspf Group 
 
rcIpRoutingRedistributeStaticToOspf OBJECT IDENTIFIER ::= {rcIpRouting 4} 
 
rcIpRoutingRedistributeStaticToOspfEnable  OBJECT-TYPE 
        SYNTAX        TruthValue 
        ACCESS        read-write 
        STATUS        obsolete 
        DESCRIPTION   "Used to indicate whether static routes (that 
                      are configured locally through management 
                      protocol) are distributed to OSPF database 
                      or not. If set to true all the static routes 
                      will be added as external routes to OSPF 
                      routing domain, provided the router is 
                      configured as AS Border router. Also originates 
                      asExtern link LSA." 
        DEFVAL        { false } 
        ::= { rcIpRoutingRedistributeStaticToOspf 1 } 
  
rcIpRoutingRedistributeStaticToOspfExplicitMetric OBJECT-TYPE 
        SYNTAX        INTEGER (1..'FFFF'h) 
        ACCESS        read-write 
        STATUS        obsolete 
        DESCRIPTION   "Value of metric that is used to translate the 
                      static routes to OSPF." 
        DEFVAL        { 10 } 
        ::= { rcIpRoutingRedistributeStaticToOspf 2 } 
  
rcIpRoutingRedistributeStaticToOspfUseExplicitMetric OBJECT-TYPE 
        SYNTAX        TruthValue 
        ACCESS        read-write 
        STATUS        obsolete 
        DESCRIPTION   "Used to indicate whether or not to use the user 
                      specified default metric for redistributing 
                      static routes to OSPF." 
        DEFVAL        { false } 
        ::= { rcIpRoutingRedistributeStaticToOspf 3 } 
 
rcIpRoutingRedistributeStaticToOspfExternalMetricType  OBJECT-TYPE 
        SYNTAX        INTEGER { 
                         type1(1),          -- extenal metric type1 
                         type2(2)           -- extenal metric type2 
                      } 
        ACCESS        read-write 
        STATUS        obsolete 
        DESCRIPTION   "Used to configure the metric type of the 
                      distributed routes to OSPF domain. 
                      type1 means the metric is comparable directly 
                      to the link state metric  
                      (cost = internal cost + external cost).  
                      type2 means the metric is considered larger  
                      than any link state metric (cost = external  
                      cost)." 
        DEFVAL        { type2 } 
        ::= { rcIpRoutingRedistributeStaticToOspf 4 } 
 
rcIpRoutingRedistributeStaticToOspfAdvertDefRte  OBJECT-TYPE 
        SYNTAX        TruthValue 
        ACCESS        read-write 
        STATUS        obsolete 
        DESCRIPTION   "Used to indicate whether default route (that 
                      are configured locally through management 
                      protocol) should be distributed to OSPF database 
                      or not. If set to true then the default route will  
                      be added as external route to OSPF routing domain,  
                      provided the router is configured as AS Border router.  
                      Also originates asExtern link LSA." 
        DEFVAL        { false } 
        ::= { rcIpRoutingRedistributeStaticToOspf 5 } 
 
-- rcIpRouting/rcIpRoutingRedistributeDirectToRip Group 
 
rcIpRoutingRedistributeDirectToRip OBJECT IDENTIFIER ::= {rcIpRouting 5} 
 
rcIpRoutingRedistributeDirectToRipEnable  OBJECT-TYPE 
        SYNTAX        TruthValue 
        ACCESS        read-write 
        STATUS        obsolete 
        DESCRIPTION   "Used to indicate whether directly connected 
                      networks through non-rip interfaces are 
                      distributed to RIP or not."  
        DEFVAL        { false } 
        ::= { rcIpRoutingRedistributeDirectToRip 1 } 
 
 
-- rcIpRouting/rcIpRoutingRedistributeStaticToRip Group 
 
rcIpRoutingRedistributeStaticToRip OBJECT IDENTIFIER ::= {rcIpRouting 6} 
 
rcIpRoutingRedistributeStaticToRipEnable  OBJECT-TYPE 
        SYNTAX        TruthValue 
        ACCESS        read-write 
        STATUS        obsolete 
        DESCRIPTION   "Used to indicate whether static routes (that 
                      are configured locally through management 
                      protocol) are distributed to RIP database 
                      or not. If set to true all the static routes 
                      will be added as external routes to RIP 
                      routing domain." 
        DEFVAL        { false } 
        ::= { rcIpRoutingRedistributeStaticToRip 1 } 
 
 
rcIpConfIgmpTable OBJECT-TYPE 
        SYNTAX        SEQUENCE OF RcIpConfIgmpEntry 
        ACCESS        not-accessible 
        STATUS        mandatory 
        DESCRIPTION   "A table used to maintain IGMP information 
                      for a particular interface." 
    ::= { rcIp 5 } 
  
rcIpConfIgmpEntry OBJECT-TYPE 
        SYNTAX        RcIpConfIgmpEntry 
        ACCESS        not-accessible 
        STATUS        mandatory 
        DESCRIPTION   "Entry containing IGMP information.  An entry is 
                      automatically created in this table when routing  
                      is enabled for an interface -or- when an ip address  
                      is configured on an interface." 
        INDEX      { rcIpConfIgmpIfIndex } 
        ::= { rcIpConfIgmpTable 1 } 
  
RcIpConfIgmpEntry ::= SEQUENCE { 
        rcIpConfIgmpIfIndex                 INTEGER, 
        rcIpConfIgmpQueryInterval           INTEGER, 
        rcIpConfIgmpVersion                 INTEGER, 
        rcIpConfIgmpQueryMaxResponseTime    INTEGER, 
        rcIpConfIgmpQuerierPresentTimeout   INTEGER, 
        rcIpConfIgmpLeaveEnabled            TruthValue, 
        rcIpConfIgmpRowStatus               RowStatus, 
        rcIpConfIgmpRobustness              INTEGER, 
        rcIpConfIgmpLastMemberQueryInterval INTEGER 
} 
 
rcIpConfIgmpIfIndex OBJECT-TYPE 
        SYNTAX          INTEGER (0..65535) 
        ACCESS          read-only 
        STATUS          mandatory 
        DESCRIPTION     "An unique value to identify a physical  
                        interface or a logical interface (VLAN)." 
        ::= { rcIpConfIgmpEntry 1 } 
 
rcIpConfIgmpQueryInterval OBJECT-TYPE 
         SYNTAX     INTEGER (1..65535) 
         ACCESS     read-write 
         STATUS     mandatory 
         DESCRIPTION "The frequency at which IGMP Host-Query packets are 
                     transmitted on this interface." 
         DEFVAL     { 125 } 
         ::= { rcIpConfIgmpEntry 2 } 
  
rcIpConfIgmpVersion OBJECT-TYPE 
         SYNTAX     INTEGER { version1(1), version2(2) } 
         ACCESS     read-write 
         STATUS     mandatory 
         DESCRIPTION "The version of IGMP which is running on this 
                     interface. This object can be used to configure a 
                     router capable of running either value.  For IGMP 
                     to function correctly, all routers on a LAN must 
                     be configured to run the same version of IGMP on 
                     that LAN." 
         DEFVAL     { version2 } 
         ::= { rcIpConfIgmpEntry 3 } 
  
rcIpConfIgmpQueryMaxResponseTime OBJECT-TYPE 
         SYNTAX     INTEGER (1..255) 
         ACCESS     read-write 
         STATUS     mandatory 
         DESCRIPTION "The maximum query response time advertised in 
                     IGMPv2 queries on this interface.  Smaller values 
                     allow a router to prune groups faster." 
         DEFVAL     { 10 } 
         ::= { rcIpConfIgmpEntry 4 } 
  
rcIpConfIgmpQuerierPresentTimeout OBJECT-TYPE 
         SYNTAX     INTEGER 
         ACCESS     read-write 
         STATUS     mandatory 
         DESCRIPTION "A timeout interval.  If no IGMPv2 queries are 
                     heard on this interface within this timeout 
                     interval, the local router will take over the 
                     Querier on the IP subnet to which this interface 
                     is attached." 
         DEFVAL     { 255 } 
  
         ::= { rcIpConfIgmpEntry 5 } 
  
rcIpConfIgmpLeaveEnabled OBJECT-TYPE 
         SYNTAX     TruthValue 
         ACCESS     read-write 
         STATUS     mandatory 
         DESCRIPTION "An indication of whether the processing of IGMPv2 
                      Leave messages is enabled on this interface." 
         DEFVAL    { true } 
         ::= { rcIpConfIgmpEntry 6 } 
  
rcIpConfIgmpRowStatus OBJECT-TYPE 
        SYNTAX          RowStatus 
        ACCESS          read-write 
        STATUS          mandatory 
        DESCRIPTION     "Status of entry." 
        ::= { rcIpConfIgmpEntry 7 } 
 
rcIpConfIgmpRobustness OBJECT-TYPE 
        SYNTAX          INTEGER (2..255) 
        ACCESS          read-write 
        STATUS          mandatory 
        DESCRIPTION     "lossiness of network." 
        ::= { rcIpConfIgmpEntry 8 } 
 
rcIpConfIgmpLastMemberQueryInterval OBJECT-TYPE 
        SYNTAX          INTEGER (1..255) 
        ACCESS          read-write 
        STATUS          mandatory 
        DESCRIPTION     "max response in GrpSpec Query." 
        ::= { rcIpConfIgmpEntry 9 } 
 
rcIgmpGroupTable OBJECT-TYPE 
        SYNTAX     SEQUENCE OF RcIgmpGroupEntry 
        ACCESS     not-accessible 
        STATUS     mandatory 
        DESCRIPTION "The (conceptual) table listing the multicast  
                    groups configured in the device." 
    ::= { rcIp 6 } 
  
rcIgmpGroupEntry OBJECT-TYPE 
        SYNTAX     RcIgmpGroupEntry 
        ACCESS     not-accessible 
        STATUS     mandatory 
        DESCRIPTION "An entry (conceptual row) representing an 
                    Igmp group." 
        INDEX      { rcIgmpGroupIpAddress, rcIgmpGroupMembers } 
        ::= { rcIgmpGroupTable 1 } 
  
RcIgmpGroupEntry ::= SEQUENCE { 
        rcIgmpGroupIpAddress         IpAddress, 
        rcIgmpGroupMembers           IpAddress, 
        rcIgmpGroupInPort            INTEGER, 
        rcIgmpGroupExpiration        INTEGER  
} 
 
rcIgmpGroupIpAddress OBJECT-TYPE 
        SYNTAX          IpAddress  
        ACCESS          read-only 
        STATUS          mandatory 
        DESCRIPTION     "Multicast group Address (Class D) that others 
                         want to join. A group address can be the same  
                         for many incoming ports." 
        ::= { rcIgmpGroupEntry 1 } 
 
rcIgmpGroupMembers OBJECT-TYPE 
        SYNTAX          IpAddress  
        ACCESS          read-only 
        STATUS          mandatory 
        DESCRIPTION     "IP Address of a source that has sent group  
                         report wishing to join this group." 
        ::= { rcIgmpGroupEntry 2 } 
  
rcIgmpGroupInPort OBJECT-TYPE 
        SYNTAX          INTEGER (0..65535) 
        ACCESS          read-only 
        STATUS          mandatory 
        DESCRIPTION     "An unique value to identify a physical 
                        interface or a logical interface (VLAN), 
                        which has received Group reports from various 
                        sources." 
        ::= { rcIgmpGroupEntry 3 } 
 
rcIgmpGroupExpiration OBJECT-TYPE 
         SYNTAX     INTEGER 
         ACCESS     read-only 
         STATUS     mandatory 
         DESCRIPTION "Time left before the group report expired on this 
                      port. Only one of this variable port. This  
                      variable is updated upon receiving a group report." 
         ::= { rcIgmpGroupEntry 4 } 
 
-- IP Route Table 
 
rcIpRouteTable OBJECT-TYPE  
        SYNTAX          SEQUENCE OF RcIpRouteEntry 
        ACCESS          not-accessible  
        STATUS          mandatory  
        DESCRIPTION     "This entity's IP Routing table." 
    ::= { rcIp 7 } 
 
rcIpRouteEntry OBJECT-TYPE 
	SYNTAX  	RcIpRouteEntry 
        ACCESS  	not-accessible 
        STATUS  	mandatory 
        DESCRIPTION	"A route to a particular destination." 
        INDEX   { rcIpRouteDest, rcIpRouteMask } 
    ::= { rcIpRouteTable 1 } 
 
RcIpRouteEntry ::= 
	SEQUENCE { 
        	rcIpRouteDest IpAddress, 
                rcIpRouteMask IpAddress, 
                rcIpRouteNextHop IpAddress, 
                rcIpRouteMetric  INTEGER, 
                rcIpRouteIfIndex InterfaceIndex, 
                rcIpRouteType INTEGER, 
                rcIpRouteProto INTEGER, 
                rcIpRouteAge INTEGER, 
		rcIpRouteRowStatus RowStatus 
              } 
 
rcIpRouteDest OBJECT-TYPE 
        SYNTAX  	IpAddress 
        ACCESS  	read-only 
        STATUS  	mandatory 
        DESCRIPTION 	"The destination IP address of this route.  An 
                      	entry with a value of 0.0.0.0 is considered a 
                      	default route.  Multiple routes to a single 
                      	destination can appear in the table, but access to 
                      	such multiple entries is dependent on the table- 
                      	access mechanisms defined by the network 
                      	management protocol in use." 
    ::= { rcIpRouteEntry 1 } 
 
rcIpRouteMask OBJECT-TYPE 
        SYNTAX  	IpAddress 
        ACCESS  	read-only 
        STATUS  	mandatory 
        DESCRIPTION	"Indicate the mask to be logical-ANDed with the 
                      	destination address before being compared to the 
                      	value in the rcIpRouteDest field.  For those systems 
                      	that do not support arbitrary subnet masks, an 
                      	agent constructs the value of the rcIpRouteMask by 
                      	determining whether the value of the correspondent 
                      	rcIpRouteDest field belong to a class-A, B, or C 
                      	network, and then using one of: 
 
                           mask           network 
                           255.0.0.0      class-A 
                           255.255.0.0    class-B 
                           255.255.255.0  class-C 
 
                      	If the value of the rcIpRouteDest is 0.0.0.0 (a 
                      	default route), then the mask value is also 
                      	0.0.0.0.  It should be noted that all IP routing 
                      	subsystems implicitly use this mechanism." 
    ::= { rcIpRouteEntry 2 } 
 
rcIpRouteNextHop OBJECT-TYPE 
        SYNTAX  	IpAddress 
        ACCESS  	read-write 
        STATUS  	mandatory 
        DESCRIPTION 	"The IP address of the next hop of this route. 
                      	(In the case of a route bound to an interface 
                      	which is realized via a broadcast media, the value 
                      	of this field is the agent's IP address on that 
                      	interface)." 
    ::= { rcIpRouteEntry 3 } 
 
rcIpRouteMetric OBJECT-TYPE 
        SYNTAX  	INTEGER 
        ACCESS  	read-write 
        STATUS  	mandatory 
        DESCRIPTION 	"The primary routing metric for this route.  The 
                      	semantics of this metric are determined by the 
                      	routing-protocol specified in the route's 
                      	rcIpRouteProto value.  If this metric is not used, 
                      	its value should be set to -1." 
    ::= { rcIpRouteEntry 4 } 
 
rcIpRouteIfIndex OBJECT-TYPE 
        SYNTAX  	InterfaceIndex 
        ACCESS  	read-only 
        STATUS  	mandatory 
        DESCRIPTION 	"The index value which uniquely identifies the 
                      	local interface through which the next hop of this 
                      	route should be reached.  The interface identified 
                      	by a particular value of this index is the same 
                      	interface as identified by the same value of 
                      	ifIndex." 
    ::= { rcIpRouteEntry 5 } 
 
rcIpRouteType OBJECT-TYPE 
        SYNTAX  INTEGER { 
                    other(1),        -- none of the following 
                    direct(3),       -- connected (sub-)network 
 
                                     -- route to a non-local 
                    indirect(4)      -- host/network/sub-network 
               } 
        ACCESS  	read-only 
        STATUS  	mandatory 
        DESCRIPTION 	"The type of route.  Note that the values 
                      	direct(3) and indirect(4) refer to the notion of 
                      	direct and indirect routing in the IP 
                      	architecture." 
    ::= { rcIpRouteEntry 6 } 
 
rcIpRouteProto OBJECT-TYPE 
        SYNTAX  INTEGER { 
                    other(1),       -- none of the following 
 
                                    -- non-protocol information, 
                                    -- e.g., manually configured 
                    local(2),       -- entries 
 
                                    -- set via a network 
                    netmgmt(3),     -- management protocol 
 
                                    -- obtained via ICMP, 
                    icmp(4),        -- e.g., Redirect 
 
                                    -- the remaining values are 
                                    -- all gateway routing 
                                    -- protocols 
                    egp(5), 
                    ggp(6), 
                    hello(7), 
                    rip(8), 
                    is-is(9), 
                    es-is(10), 
                    ciscoIgrp(11), 
                    bbnSpfIgp(12), 
                    ospf(13), 
                    bgp(14) 
                } 
        ACCESS  	read-only 
        STATUS  	mandatory 
        DESCRIPTION	"The routing mechanism via which this route was 
                      	learned.  Inclusion of values for gateway routing 
                      	protocols is not intended to imply that hosts 
                      	should support those protocols." 
    ::= { rcIpRouteEntry 7 } 
 
rcIpRouteAge OBJECT-TYPE 
        SYNTAX  	INTEGER 
        ACCESS  	read-only 
        STATUS  	mandatory 
        DESCRIPTION	"The number of seconds since this route was last 
                      	updated or otherwise determined to be correct. 
                      	Note that no semantics of `too old' can be implied 
                      	except through knowledge of the routing protocol 
                      	by which the route was learned." 
    ::= { rcIpRouteEntry 8 } 
 
rcIpRouteRowStatus OBJECT-TYPE 
        SYNTAX        	RowStatus 
        ACCESS        	read-write 
        STATUS        	mandatory 
        DESCRIPTION   	"Used to create/delete entries" 
    ::= { rcIpRouteEntry 9 } 
 
 
-- Ip Config Dhcp Table 
  
rcIpConfDhcpTable OBJECT-TYPE  
        SYNTAX          SEQUENCE OF RcIpConfDhcpEntry 
        ACCESS          not-accessible  
        STATUS          mandatory  
        DESCRIPTION     "DHCP configuration table" 
    ::= { rcIp 8 } 
 
rcIpConfDhcpEntry OBJECT-TYPE 
        SYNTAX        	RcIpConfDhcpEntry 
        ACCESS        	not-accessible 
        STATUS        	mandatory 
        DESCRIPTION   	"Used to configure DHCP on a particular port.  An 
		      	entry is created automatically when the variable 
		      	rcIpConfDhcpEnable is set to TRUE.   
 
 		      	Once created this entry will only be deleted if the  
		      	rcIpConfDhcpRowStatus is set to 'destroy(6)'.  In 
		      	which case, the rcIpConfDhcpEnable is automatically 
		      	reset to the FALSE setting." 
        INDEX         	{ rcIpConfDhcpIfIndex } 
        ::= { rcIpConfDhcpTable 1 } 
  
RcIpConfDhcpEntry ::= 
        SEQUENCE { 
                rcIpConfDhcpIfIndex   	    InterfaceIndex, 
                rcIpConfDhcpMaxHop    	    INTEGER, 
                rcIpConfDhcpMinSec    	    INTEGER, 
                rcIpConfDhcpMode      	    INTEGER, 
                rcIpConfDhcpRowStatus 	    RowStatus, 
		rcIpConfDhcpNumRequests     Counter, 
		rcIpConfDhcpNumReplies	    Counter, 
		rcIpConfDhcpAlwaysBroadcast TruthValue 
        } 
  
rcIpConfDhcpIfIndex OBJECT-TYPE 
        SYNTAX        	InterfaceIndex (0..4094) 
        ACCESS        	read-only 
        STATUS        	mandatory 
        DESCRIPTION   	"Interface number.  The number can represent either 
		      	a physical or logical(VLAN) interface." 
        ::= { rcIpConfDhcpEntry 1 } 
  
rcIpConfDhcpMaxHop OBJECT-TYPE 
        SYNTAX        	INTEGER (1..16) 
        ACCESS        	read-write 
        STATUS        	mandatory 
        DESCRIPTION   	"Used to indicate the maximum number of hops a  
		      	DHCP packet can take from the source device to  
		      	the destination device (i.e., DHCP client to  
		      	DHCP server)." 
 	DEFVAL        	{ 4 } 
        ::= { rcIpConfDhcpEntry 2 } 
  
rcIpConfDhcpMinSec OBJECT-TYPE 
        SYNTAX        	INTEGER (0..65535) 
        ACCESS        	read-write 
        STATUS        	mandatory 
        DESCRIPTION   	"Used to indicate the minimum number of seconds  
		      	to wait between receiving a DHCP packet and 
		      	actually forwarding the DHCP packet to the  
		      	destination device.  A value of zero(0) indicates 
		      	forwarding should be done immediately without any 
		      	delay." 
	DEFVAL        	{ 0 } 
        ::= { rcIpConfDhcpEntry 3 } 
  
rcIpConfDhcpMode OBJECT-TYPE 
        SYNTAX		INTEGER { 
				none(0), 
				bootp(2), 
				dhcp(3), 
				both(4) 
			} 
        ACCESS     	read-write 
        STATUS        	mandatory 
        DESCRIPTION   	"Used to indicate what type of DHCP packets this 
		      	interface should support.  A value of none(1) will 
		      	result in all incoming DHCP and BOOTP packets to 
		      	be dropped."  
        DEFVAL        	{ both } 
        ::= { rcIpConfDhcpEntry 4 } 
  
rcIpConfDhcpRowStatus OBJECT-TYPE 
        SYNTAX        	RowStatus 
        ACCESS        	read-write 
        STATUS        	mandatory 
        DESCRIPTION   	"An entry is created automatically when the variable 
                      	rcIpConfDhcpEnable is set to TRUE. 
 
                      	Once created this entry will only be deleted if the 
                      	rcIpConfDhcpRowStatus is set to 'destroy(6)'.  In 
                      	which case, the rcIpConfDhcpEnable is automatically 
                      	reset to the FALSE setting." 
        ::= { rcIpConfDhcpEntry 5 } 
 
rcIpConfDhcpNumRequests OBJECT-TYPE 
        SYNTAX        	Counter 
        ACCESS        	read-only 
        STATUS        	mandatory 
        DESCRIPTION   	"The total number of DHCP requests seen on this 
interface." 
        ::= { rcIpConfDhcpEntry 6 } 
 
rcIpConfDhcpNumReplies OBJECT-TYPE 
        SYNTAX        	Counter 
        ACCESS        	read-only 
        STATUS        	mandatory 
        DESCRIPTION   	"The total number of DHCP replies seen on this 
interface." 
        ::= { rcIpConfDhcpEntry 7 } 
 
rcIpConfDhcpAlwaysBroadcast OBJECT-TYPE 
        SYNTAX        	TruthValue 
        ACCESS        	read-write 
        STATUS        	mandatory 
        DESCRIPTION   	"Used to indicate if DHCP Reply packets should be  
		    	broadcast to the DHCP client on this interface." 
	DEFVAL		{ false } 
        ::= { rcIpConfDhcpEntry 8 } 
 
 
-- Ip Dhcp Forward Table 
  
rcIpDhcpForwardTable OBJECT-TYPE  
        SYNTAX	      	SEQUENCE OF RcIpDhcpForwardEntry 
        ACCESS        	not-accessible  
        STATUS        	mandatory  
        DESCRIPTION   	"DHCP forwarding table." 
    ::= { rcIp 9 } 
 
rcIpDhcpForwardEntry OBJECT-TYPE 
        SYNTAX        	RcIpDhcpForwardEntry 
        ACCESS        	not-accessible 
        STATUS        	mandatory 
        DESCRIPTION   	"An entry used represents a DHCP forwarding directive." 
        INDEX         	{ rcIpDhcpForwardAgentAddr, rcIpDhcpForwardServerAddr } 
        ::= { rcIpDhcpForwardTable 1 } 
  
RcIpDhcpForwardEntry ::= 
        SEQUENCE { 
                rcIpDhcpForwardAgentAddr   IpAddress, 
                rcIpDhcpForwardServerAddr  IpAddress, 
                rcIpDhcpForwardEnable      TruthValue, 
                rcIpDhcpForwardMode        INTEGER, 
                rcIpDhcpForwardRowStatus   RowStatus 
        } 
  
rcIpDhcpForwardAgentAddr OBJECT-TYPE 
        SYNTAX        	IpAddress 
        ACCESS        	read-only 
        STATUS        	mandatory 
        DESCRIPTION   	"The IP address configured on an interface 
                      	(i.e., a locally configured IP address)." 
        ::= { rcIpDhcpForwardEntry 1 } 
  
rcIpDhcpForwardServerAddr OBJECT-TYPE 
        SYNTAX        	IpAddress 
        ACCESS        	read-only 
        STATUS        	mandatory 
        DESCRIPTION   	"The IP address of the DHCP server.  If this 
	              	IP address corresponds to a locally configured 
		      	IP network, the DHCP packet is broadcasted out 
	       	      	the interface the IP address is assigned to. 
		      	This behavior is known as 'relay agent' mode. 
 
 		      	If this IP address is a remote address, the DHCP 
		      	packet is sent via unicast to the remote device. 
		      	This behavior is known as 'preferred server' mode." 
        ::= { rcIpDhcpForwardEntry 2 } 
  
rcIpDhcpForwardEnable OBJECT-TYPE 
        SYNTAX        	TruthValue 
        ACCESS        	read-write 
        STATUS        	mandatory 
        DESCRIPTION   	"Used to indicate whether is entry should be used." 
	DEFVAL        	{ true } 
        ::= { rcIpDhcpForwardEntry 3 } 
  
rcIpDhcpForwardMode OBJECT-TYPE 
        SYNTAX        	INTEGER { 
				none(0), 
				bootp(2), 
				dhcp(3), 
				both(4) 
			} 
        ACCESS        	read-write 
        STATUS        	mandatory 
        DESCRIPTION   	"Used to indicate whether this entry pertains to 
		      	BOOTP packets, DHCP packets, or both." 
	DEFVAL        	{ both } 
        ::= { rcIpDhcpForwardEntry 4 } 
  
rcIpDhcpForwardRowStatus OBJECT-TYPE 
        SYNTAX        	RowStatus 
        ACCESS        	read-write 
        STATUS        	mandatory 
        DESCRIPTION   	"Row status of this entry." 
        ::= { rcIpDhcpForwardEntry 5 } 
 
 
-- IP Filter Group 
 
rcIpFilter OBJECT IDENTIFIER ::= { rcIp 10 } 
 
rcIpFilterFilterTableSize OBJECT-TYPE 
        SYNTAX        	INTEGER 
        ACCESS        	read-only 
        STATUS        	mandatory 
        DESCRIPTION   	"Used to indicate the number of entries in the 
                      	rcIpFilterTable." 
        ::= { rcIpFilter 1 } 
 
rcIpFilterGlobalListTableSize OBJECT-TYPE 
        SYNTAX        	INTEGER 
        ACCESS        	read-only 
        STATUS        	mandatory 
        DESCRIPTION   	"Used to indicate the number of entries in the 
                      	rcIpFilterGlobalListTable." 
        ::= { rcIpFilter 2 } 
 
rcIpFilterBaseListTableSize OBJECT-TYPE 
        SYNTAX        	INTEGER 
        ACCESS        	read-only 
        STATUS        	mandatory 
        DESCRIPTION   	"Used to indicate the number of entries in the 
                      	rcIpFilterBaseListTable." 
        ::= { rcIpFilter 3 } 
 
rcIpFilterPortTableSize OBJECT-TYPE 
        SYNTAX        	INTEGER 
        ACCESS        	read-only 
        STATUS        	mandatory 
        DESCRIPTION   	"Used to indicate the number of entries in the 
                      	rcIpFilterPortTable." 
        ::= { rcIpFilter 4 } 
 
rcIpFilterNextAvailFilterId OBJECT-TYPE 
        SYNTAX          INTEGER 
        ACCESS          read-only 
        STATUS          mandatory 
        DESCRIPTION     "next available filter-id in the 
                        rcIpFilterPortTable." 
        ::= { rcIpFilter 5 } 
  
 
-- IP Filter Table 
 
rcIpFilterTable OBJECT-TYPE 
        SYNTAX		SEQUENCE OF RcIpFilterEntry 
        ACCESS        	not-accessible 
        STATUS        	mandatory 
        DESCRIPTION   	"A table containing IP filters." 
        ::= { rcIpFilter 20 } 
 
rcIpFilterEntry OBJECT-TYPE 
	SYNTAX        	RcIpFilterEntry 
        ACCESS        	not-accessible 
        STATUS        	mandatory 
        DESCRIPTION   	"IP filter attributes.   
 
			The system supports a vast array of filter options. 
			Each of these options are supported in this entry. 
			If a particular option is not used, the column 
			should be set to zero." 
        INDEX         	{ rcIpFilterType, rcIpFilterDstAddr, 
			  rcIpFilterDstMask, rcIpFilterSrcAddr, 
			  rcIpFilterSrcMask, rcIpFilterId } 
        ::= { rcIpFilterTable 1 } 
 
RcIpFilterEntry ::= SEQUENCE { 
		rcIpFilterType INTEGER, 
		rcIpFilterDstAddr IpAddress, 
		rcIpFilterDstMask IpAddress, 
		rcIpFilterSrcAddr IpAddress, 
		rcIpFilterSrcMask IpAddress, 
		rcIpFilterId INTEGER (1..4000), 
		rcIpFilterName DisplayString (SIZE (0..15)), 
		rcIpFilterProtocolType INTEGER, 
		rcIpFilterSrcPort INTEGER (0..65535), 
		rcIpFilterSrcOption INTEGER, 
		rcIpFilterDstPort INTEGER (0..65535), 
		rcIpFilterDstOption INTEGER, 
		rcIpFilterCopyToCpu TruthValue, 
		rcIpFilterMirror TruthValue, 
		rcIpFilterHighPriority TruthValue, 
		rcIpFilterTcpConnect TruthValue, 
		rcIpFilterIeeeVlanPriority INTEGER, 
		rcIpFilterUsePktLimit TruthValue, 
		rcIpFilterPktLimit INTEGER, 
		rcIpFilterRowStatus RowStatus, 
                rcIpFilterMode INTEGER 
		} 
 
rcIpFilterType OBJECT-TYPE 
        SYNTAX		INTEGER { 
			   global(1), 
			   destination(2), 
			   source(3) 
			} 
        ACCESS		read-only 
        STATUS		mandatory 
        DESCRIPTION	"Used to indicate a particular type of filter.   
 
                        A 'global' filter is a filter that is applied to 
                        all packets irregardless of the packet's source 
                        or destination IP address. 
  
                        A 'destination' filter is used to match the 
                        destination IP address field of incoming packets. 
                        When a match is found, this filter is applied to 
                        the packet. 
  
                        A 'source' filter is used to match the source 
                        IP address field of incoming packets.  When a 
                        match is found, this filter is applied to the 
                        packet." 
        ::= { rcIpFilterEntry 1 } 
 
rcIpFilterDstAddr OBJECT-TYPE 
        SYNTAX		IpAddress 
        ACCESS		read-only 
        STATUS		mandatory 
        DESCRIPTION	"Destination IP address to filter on." 
        ::= { rcIpFilterEntry 2 } 
 
rcIpFilterDstMask OBJECT-TYPE 
        SYNTAX		IpAddress 
        ACCESS		read-only 
        STATUS		mandatory 
        DESCRIPTION	"Destination IP subnet mask to filter on." 
        ::= { rcIpFilterEntry 3 } 
 
rcIpFilterSrcAddr OBJECT-TYPE 
        SYNTAX		IpAddress 
        ACCESS		read-only 
        STATUS		mandatory 
        DESCRIPTION	"Source IP address to filter on." 
        ::= { rcIpFilterEntry 4 } 
 
rcIpFilterSrcMask OBJECT-TYPE 
        SYNTAX		IpAddress 
        ACCESS		read-only 
        STATUS		mandatory 
        DESCRIPTION	"Source IP subnet mask to filter on." 
        ::= { rcIpFilterEntry 5 } 
 
rcIpFilterId OBJECT-TYPE 
        SYNTAX		INTEGER (1..4000) 
        ACCESS		read-only 
        STATUS		mandatory 
        DESCRIPTION	"This filter's unique identifier(id).  This id 
			is automatically generated by the system when 
			a filter is created.  This id is used in the 
			'rcIpFilterGlobalListTable' and  
			'rcIpFilterBaseListTable' when grouping one 
			or more filters into a filter list." 
        ::= { rcIpFilterEntry 6 } 
 
rcIpFilterName OBJECT-TYPE 
        SYNTAX		DisplayString (SIZE (0..15)) 
        ACCESS		read-write 
        STATUS		mandatory 
        DESCRIPTION	"This filter's name." 
        ::= { rcIpFilterEntry 7 } 
 
rcIpFilterProtocolType OBJECT-TYPE 
        SYNTAX		INTEGER { 
			    ignore(0), 
			    icmp(1), 
			    tcp(6), 
			    udp(17) 
			} 
        ACCESS		read-write 
        STATUS		mandatory 
        DESCRIPTION	"Type of protocol to filter on." 
	DEFVAL		{ ignore } 
        ::= { rcIpFilterEntry 8 } 
 
rcIpFilterSrcPort OBJECT-TYPE 
        SYNTAX		INTEGER (0..65535) 
        ACCESS		read-write 
        STATUS		mandatory 
        DESCRIPTION	"TCP/UDP source port to filter on." 
	DEFVAL		{ 0 } 
        ::= { rcIpFilterEntry 9 } 
 
rcIpFilterSrcOption OBJECT-TYPE 
        SYNTAX		INTEGER { 
                            equal(0), 
                            notEqual(1), 
                            greater(2), 
                            less(3), 
                            ignore(4) 
			} 
        ACCESS		read-write 
        STATUS		mandatory 
        DESCRIPTION	"Type of matching to perform on the field 
			'rcIpFilterSrcPort'. 
			 
			For 'source' and 'destination' filters, this 
			value can only be 'equal(1)'." 
	DEFVAL 		{ ignore } 
        ::= { rcIpFilterEntry 10 } 
 
rcIpFilterDstPort OBJECT-TYPE 
        SYNTAX		INTEGER (0..65535) 
        ACCESS		read-write 
        STATUS		mandatory 
        DESCRIPTION	"TCP/UDP destination port to filter on." 
	DEFVAL		{ 0 } 
        ::= { rcIpFilterEntry 11 } 
 
rcIpFilterDstOption OBJECT-TYPE 
        SYNTAX		INTEGER { 
                            equal(0), 
                            notEqual(1), 
                            greater(2), 
                            less(3), 
                            ignore(4) 
			} 
        ACCESS		read-write 
        STATUS		mandatory 
        DESCRIPTION	"Type of matching to perform on the field 
			'rcIpFilterDstPort'. 
 
			For 'source' and 'destination' filters, this 
			value can only be 'equal(1)'." 
	DEFVAL		{ ignore } 
        ::= { rcIpFilterEntry 12 } 
 
rcIpFilterCopyToCpu OBJECT-TYPE 
        SYNTAX		TruthValue 
        ACCESS		read-write 
        STATUS		mandatory 
        DESCRIPTION	"Used to specify whether a packet matching 
			this filter should be copied to the CPU." 
	DEFVAL		{ false } 
        ::= { rcIpFilterEntry 13 } 
 
rcIpFilterMirror OBJECT-TYPE 
        SYNTAX		TruthValue 
        ACCESS		read-write 
        STATUS		mandatory 
        DESCRIPTION	"Used to specify whether a packet matching 
			this filter should be mirrored to the port 
			specified by 'rcMirrorByPortMirrorPort'." 
	DEFVAL		{ false } 
        ::= { rcIpFilterEntry 14 } 
 
rcIpFilterHighPriority OBJECT-TYPE 
        SYNTAX		TruthValue 
        ACCESS		read-write 
        STATUS		mandatory 
        DESCRIPTION	"Used to specify whether a packet matching 
			this filter should be forwarded with high 
			priority."  
	DEFVAL		{ false } 
        ::= { rcIpFilterEntry 15 } 
 
rcIpFilterTcpConnect OBJECT-TYPE 
        SYNTAX		TruthValue 
        ACCESS		read-write 
        STATUS		mandatory 
        DESCRIPTION	"Used to specify whether a TCP packet matching 
                         this filter should be accepted.  Pass only  
                         those matching TCP packets with either the 
                         ACK bit or RST bit set.  Apply only if the IP  
                         Protocol is set to TCP." 
	DEFVAL		{ false } 
        ::= { rcIpFilterEntry 16 } 
 
rcIpFilterIeeeVlanPriority OBJECT-TYPE 
        SYNTAX		INTEGER (0..7) 
        ACCESS		read-write 
        STATUS		mandatory 
        DESCRIPTION	"Used to specify the priority bits for explicit 
                         IEEE VLAN tag for a packet matching this filter. 
                         If this priority bit field is greater than the 
                         priority field currently in the IEEE tag in the 
                         Packet Header, this priority field will be loaded 
                         into the Packet Header." 
        DEFVAL          { 0 } 
        ::= { rcIpFilterEntry 17 } 
 
rcIpFilterUsePktLimit OBJECT-TYPE 
        SYNTAX		TruthValue 
        ACCESS		read-write 
        STATUS		mandatory 
        DESCRIPTION	"Used to specify whether the 'rcIpFilterPktLimit' 
			field in this entry should be used when applying 
			this filter."  
	DEFVAL		{ false } 
        ::= { rcIpFilterEntry 18 } 
 
rcIpFilterPktLimit OBJECT-TYPE 
        SYNTAX		INTEGER (0..65535) 
        ACCESS		read-write 
        STATUS		mandatory 
        DESCRIPTION	"The maximum packet size limit to filter against." 
	DEFVAL		{ 1500 } 
        ::= { rcIpFilterEntry 19 } 
 
rcIpFilterRowStatus OBJECT-TYPE 
        SYNTAX		RowStatus 
        ACCESS		read-write 
        STATUS		mandatory 
        DESCRIPTION	"Row status of this entry." 
        ::= { rcIpFilterEntry 20 } 
 
rcIpFilterMode OBJECT-TYPE 
        SYNTAX          INTEGER { 
                            useDefaultAction(1), 
                            forward(2), 
                            drop(3) 
                        } 
        ACCESS          read-write 
        STATUS          mandatory 
        DESCRIPTION     "Used to specify the operation mode for this entry. 
			'useDefaultAction' means use the setting specified 
			in the 'rcIpFilterPortDefaultAction' variable.   
 
			'forward' means forward the packet if the packet  
			satisfies this policy.   
 
			'drop' means drop the packet if the packet satisfies  
			this policy. 
 
			This variable setting has higher precedence than the 
			setting in 'rcIpFilterPortDefaultAction'." 
        DEFVAL          { useDefaultAction } 
        ::= { rcIpFilterEntry 21 } 
 
 
-- IP Filter Global List Table 
 
rcIpFilterGlobalListTable OBJECT-TYPE 
        SYNTAX          SEQUENCE OF RcIpFilterGlobalListEntry 
        ACCESS          not-accessible 
        STATUS          mandatory 
        DESCRIPTION     "A table used to store global filter list information. 
			Each row in the table contains a set of individual 
			filters that make up a particular filter list." 
        ::= { rcIpFilter 21 } 
 
rcIpFilterGlobalListEntry OBJECT-TYPE 
        SYNTAX          RcIpFilterGlobalListEntry 
        ACCESS          not-accessible 
        STATUS          mandatory 
        DESCRIPTION     "Global filter list attributes." 
        INDEX           { rcIpFilterGlobalListId }  
        ::= { rcIpFilterGlobalListTable 1 } 
 
RcIpFilterGlobalListEntry ::= SEQUENCE { 
		rcIpFilterGlobalListId INTEGER (1..100), 
		rcIpFilterGlobalListName DisplayString (SIZE(0..15)), 
		rcIpFilterGlobalListFilterIdListSize INTEGER (0..8), 
		rcIpFilterGlobalListFilterIdList IdList(SIZE(16)), 
		rcIpFilterGlobalListRowStatus RowStatus, 
                rcIpFilterGlobalListMemberPorts PortSet 
                } 
 
rcIpFilterGlobalListId OBJECT-TYPE 
        SYNTAX		INTEGER (1..100) 
        ACCESS		read-only 
        STATUS		mandatory 
        DESCRIPTION	"An unique value to identify a particular global 
			filter list."  
        ::= { rcIpFilterGlobalListEntry 1 } 
 
rcIpFilterGlobalListName OBJECT-TYPE 
        SYNTAX		DisplayString (SIZE(0..15))	        	 
        ACCESS		read-write 
        STATUS		mandatory 
        DESCRIPTION	"Name of this filter list." 
        ::= { rcIpFilterGlobalListEntry 2 } 
 
rcIpFilterGlobalListFilterIdListSize OBJECT-TYPE 
        SYNTAX		INTEGER (0..8) 
        ACCESS		read-only 
        STATUS		mandatory 
        DESCRIPTION	"Used to indicate the number of filters are 
			associated with this filter list." 
        ::= { rcIpFilterGlobalListEntry 3 } 
 
rcIpFilterGlobalListFilterIdList OBJECT-TYPE 
        SYNTAX		IdList (SIZE(16))	 
        ACCESS		read-write 
        STATUS		mandatory 
        DESCRIPTION	"Used to indicate zero or more filters that are 
			associated with this filter list.  Each filter 
			identifier is stored as two bytes in this array 
			starting from offset zero.  Any unused bytes 
			should be set to zero." 
        ::= { rcIpFilterGlobalListEntry 4 } 
 
rcIpFilterGlobalListRowStatus OBJECT-TYPE 
        SYNTAX		RowStatus	 
        ACCESS		read-write 
        STATUS		mandatory 
        DESCRIPTION	"Row status of this entry." 
        ::= { rcIpFilterGlobalListEntry 5 } 
 
rcIpFilterGlobalListMemberPorts OBJECT-TYPE 
        SYNTAX          PortSet 
        ACCESS          read-only 
        STATUS          mandatory 
        DESCRIPTION     "Ports filter is used on." 
        ::= { rcIpFilterGlobalListEntry 6 } 
 
 
-- IP Filter Base Table 
 
rcIpFilterBaseListTable OBJECT-TYPE 
        SYNTAX          SEQUENCE OF RcIpFilterBaseListEntry 
        ACCESS          not-accessible 
        STATUS          mandatory 
        DESCRIPTION     "A table used to store base filter list information. 
			Each row in the table contains a set of individual 
			filters that make up a particular filter list." 
        ::= { rcIpFilter 22 } 
 
rcIpFilterBaseListEntry OBJECT-TYPE 
        SYNTAX          RcIpFilterBaseListEntry 
        ACCESS          not-accessible 
        STATUS          mandatory 
        DESCRIPTION     "Base filter list attributes." 
        INDEX           { rcIpFilterBaseListId }  
        ::= { rcIpFilterBaseListTable 1 } 
 
RcIpFilterBaseListEntry ::= SEQUENCE { 
		rcIpFilterBaseListId INTEGER (300..1000), 
		rcIpFilterBaseListName DisplayString (SIZE(0..15)), 
		rcIpFilterBaseListFilterIdListSize INTEGER (0..128), 
		rcIpFilterBaseListFilterIdList IdList (SIZE(256)), 
		rcIpFilterBaseListRowStatus RowStatus, 
                rcIpFilterBaseListMemberPorts PortSet 
                } 
 
rcIpFilterBaseListId OBJECT-TYPE 
        SYNTAX		INTEGER (300..1000) 
        ACCESS		read-only 
        STATUS		mandatory 
        DESCRIPTION     "An unique value to identify a particular base 
                        filter list." 
        ::= { rcIpFilterBaseListEntry 1 } 
 
rcIpFilterBaseListName OBJECT-TYPE 
        SYNTAX		DisplayString (SIZE(0..15))	        	 
        ACCESS		read-write 
        STATUS		mandatory 
        DESCRIPTION	"Name of this filter list." 
        ::= { rcIpFilterBaseListEntry 2 } 
 
rcIpFilterBaseListFilterIdListSize OBJECT-TYPE 
        SYNTAX		INTEGER (0..128) 
        ACCESS		read-only 
        STATUS		mandatory 
        DESCRIPTION     "Used to indicate the number of filters are 
                        associated with this filter list." 
        ::= { rcIpFilterBaseListEntry 3 } 
 
rcIpFilterBaseListFilterIdList OBJECT-TYPE 
        SYNTAX		IdList (SIZE(256))	 
        ACCESS		read-write 
        STATUS		mandatory 
        DESCRIPTION     "Used to indicate zero or more filters that are 
                        associated with this filter list.  Each filter 
                        identifier is stored as two bytes in this array 
                        starting from offset zero.  Any unused bytes 
                        should be set to zero." 
        ::= { rcIpFilterBaseListEntry 4 } 
 
rcIpFilterBaseListRowStatus OBJECT-TYPE 
        SYNTAX		RowStatus	 
        ACCESS		read-write 
        STATUS		mandatory 
        DESCRIPTION	"Row status of this entry." 
        ::= { rcIpFilterBaseListEntry 5 } 
 
rcIpFilterBaseListMemberPorts OBJECT-TYPE 
        SYNTAX          PortSet 
        ACCESS          read-only 
        STATUS          mandatory 
        DESCRIPTION     "Ports filter is used on." 
        ::= { rcIpFilterBaseListEntry 6 } 
  
 
-- IP Filter Port Table 
 
rcIpFilterPortTable OBJECT-TYPE 
        SYNTAX          SEQUENCE OF RcIpFilterPortEntry 
        ACCESS          not-accessible 
        STATUS          mandatory 
        DESCRIPTION     "A table used to store port filtering information." 
        ::= { rcIpFilter 23 } 
 
rcIpFilterPortEntry OBJECT-TYPE 
        SYNTAX          RcIpFilterPortEntry 
        ACCESS          not-accessible 
        STATUS          mandatory 
        DESCRIPTION     "Port entry attributes." 
        INDEX           { rcIpFilterPortIfIndex }  
        ::= { rcIpFilterPortTable 1 } 
 
RcIpFilterPortEntry ::= SEQUENCE { 
			rcIpFilterPortIfIndex InterfaceIndex, 
			rcIpFilterPortFilterListSize INTEGER (0..128), 
			rcIpFilterPortFilterList OCTET STRING (SIZE(256)), 
			rcIpFilterPortMode INTEGER, 
			rcIpFilterPortEnable TruthValue, 
			rcIpFilterPortRowStatus RowStatus, 
			rcIpFilterPortDefaultAction INTEGER, 
                        rcIpFilterPortNumGlobalFilters INTEGER, 
                        rcIpFilterPortNumBaseFilters INTEGER 
	                } 
 
rcIpFilterPortIfIndex OBJECT-TYPE 
        SYNTAX		InterfaceIndex 
        ACCESS		read-only 
        STATUS		mandatory 
        DESCRIPTION	"IfIndex value of a port where filtering is 
			applied." 
        ::= { rcIpFilterPortEntry 1 } 
 
rcIpFilterPortFilterListSize OBJECT-TYPE 
        SYNTAX		INTEGER (0..128) 
        ACCESS		read-only 
        STATUS		mandatory 
        DESCRIPTION	"Used to indicate the number of filter list(s) 
			that are assigned to this port." 
        ::= { rcIpFilterPortEntry 2 } 
 
rcIpFilterPortFilterList OBJECT-TYPE 
        SYNTAX		OCTET STRING (SIZE(256))	 
        ACCESS		read-write 
        STATUS		mandatory 
        DESCRIPTION     "Used to indicate zero or more filter lists that  
			are associated with this port.  Each filter list 
                        identifier is stored as two bytes in this array 
                        starting from offset zero.  Any unused bytes 
                        should be set to zero." 
        ::= { rcIpFilterPortEntry 3 } 
 
rcIpFilterPortMode OBJECT-TYPE 
        SYNTAX		INTEGER { 
			    permit(1), 
			    deny(2), 
                            none(3) 
			}	 
        ACCESS		read-write 
        STATUS		obsolete 
        DESCRIPTION	"Used to indicate when filters applied to this 
			port should be treated as 'permit' or 'deny' 
			filters. 
  
                        When filters are not enabled on the port the mode 
                        is set to none. The port does not block any packet.  
                        Mode None cannot be used when PortEnable is true.  
 
			On a port configured as 'permit',  any packet 
			that satisfies a filter is allowed to be  
			forwarded. 
 
			On a port configured as 'deny', any packet that 
			satisfies a filter is dropped."	 
	DEFVAL		{ none } 
        ::= { rcIpFilterPortEntry 4 } 
 
rcIpFilterPortEnable OBJECT-TYPE 
        SYNTAX		TruthValue	 
        ACCESS		read-write 
        STATUS		mandatory 
        DESCRIPTION	"Used to indicate whether filtering is configured 
			on this port." 
	DEFVAL		{ false } 
        ::= { rcIpFilterPortEntry 5 } 
 
rcIpFilterPortRowStatus OBJECT-TYPE 
        SYNTAX		RowStatus 
        ACCESS		read-write 
        STATUS		mandatory 
        DESCRIPTION	"Row status of this entry." 
        ::= { rcIpFilterPortEntry 6 } 
 
rcIpFilterPortDefaultAction OBJECT-TYPE 
        SYNTAX          INTEGER { 
                            forward(1), 
                            drop(2), 
                            none(3) 
                        } 
        ACCESS          read-write 
        STATUS          mandatory 
        DESCRIPTION     "Used to indicate the default action that should 
			be performed when an IP filter applies to a 
			particular port.    
 
                        When filters are not enabled on the port the action 
                        is set to 'none' which means the port does not block  
			any packet.  'none' cannot be used when PortEnable is  
			true. 
  
                        On a port configured as 'forward',  any packet 
                        that satisfies a filter is allowed to be 
                        forwarded. 
  
                        On a port configured as 'drop', any packet that 
                        satisfies a filter is dropped." 
        DEFVAL          { none } 
        ::= { rcIpFilterPortEntry 7 } 
 
rcIpFilterPortNumGlobalFilters OBJECT-TYPE 
        SYNTAX          INTEGER 
        ACCESS          read-only 
        STATUS          mandatory 
        DESCRIPTION     "# of global filters" 
        ::= { rcIpFilterPortEntry 8 } 
  
rcIpFilterPortNumBaseFilters OBJECT-TYPE 
        SYNTAX          INTEGER 
        ACCESS          read-only 
        STATUS          mandatory 
        DESCRIPTION     "# of base filters" 
        ::= { rcIpFilterPortEntry 9 } 
 
 
-- IP Policy Address Table 
  
rcIpPolicy OBJECT IDENTIFIER ::= { rcIp 11 } 
 
rcIpPolicyAddrTableSize OBJECT-TYPE 
        SYNTAX        INTEGER  
        ACCESS        read-only 
        STATUS        mandatory 
        DESCRIPTION   "Used to indicate the number of entries in the  
		      rcIpPolicyAddrTable." 
        ::= { rcIpPolicy 1 } 
 
rcIpPolicyAddrTable OBJECT-TYPE 
        SYNTAX        SEQUENCE OF RcIpPolicyAddrEntry 
        ACCESS        not-accessible 
        STATUS        mandatory 
        DESCRIPTION   "A table used to store different types list entries. 
                      Each row in the table contains a list entry that is 
                      used by a set of announce policies." 
        ::= { rcIpPolicy 2 } 
  
rcIpPolicyAddrEntry OBJECT-TYPE 
        SYNTAX        RcIpPolicyAddrEntry 
        ACCESS        not-accessible 
        STATUS        mandatory 
        DESCRIPTION   "Route entry attributes." 
        INDEX         {rcIpPolicyAddrIpAddr} 
        ::= { rcIpPolicyAddrTable 1 } 
  
RcIpPolicyAddrEntry ::= SEQUENCE { 
                        rcIpPolicyAddrIpAddr IpAddress, 
                        rcIpPolicyAddrId   INTEGER, 
                        rcIpPolicyAddrAddrListIdListSize INTEGER (0..128), 
                        rcIpPolicyAddrAddrListIdList OCTET STRING (SIZE(256)), 
                        rcIpPolicyAddrRowStatus RowStatus 
                        } 
 
 
rcIpPolicyAddrIpAddr OBJECT-TYPE 
        SYNTAX        IpAddress 
        ACCESS        read-only 
        STATUS        mandatory 
        DESCRIPTION   "The network address for this type of list entry. This  
                      value is required for all types of lists." 
        ::= { rcIpPolicyAddrEntry 1 } 
  
rcIpPolicyAddrId OBJECT-TYPE 
        SYNTAX	      INTEGER  
        ACCESS	      read-only 
        STATUS	      mandatory 
        DESCRIPTION   "Identifier of this entry. Used internally to identify 
		      this entry." 
        ::= { rcIpPolicyAddrEntry 2 } 
 
rcIpPolicyAddrAddrListIdListSize OBJECT-TYPE 
        SYNTAX	      INTEGER (0..128) 
        ACCESS	      read-only 
        STATUS	      mandatory 
        DESCRIPTION   "Used to indicate the number of id(s) in the 
		      rcIpPolicyAddrListIdList variable." 
        ::= { rcIpPolicyAddrEntry 3 } 
 
rcIpPolicyAddrAddrListIdList OBJECT-TYPE 
        SYNTAX	      OCTET STRING (SIZE(256))	 
        ACCESS	      read-only 
        STATUS	      mandatory 
        DESCRIPTION   "Used to indicate zero or more rcIpPolicyAddrListEntry(s) 
		      that are referring to this entry.  Each list-id identifier  
                      is stored as two bytes in this array starting from  
                      offset zero.  Any unused bytes should be set to zero." 
        ::= { rcIpPolicyAddrEntry 4 } 
 
rcIpPolicyAddrRowStatus OBJECT-TYPE 
        SYNTAX		RowStatus 
        ACCESS		read-write 
        STATUS		mandatory 
        DESCRIPTION	"Row status of this entry." 
        ::= { rcIpPolicyAddrEntry 5 } 
 
 
-- Ip Policy Network Table 
 
rcIpPolicyNetTableSize OBJECT-TYPE 
        SYNTAX        INTEGER  
        ACCESS        read-only 
        STATUS        mandatory 
        DESCRIPTION   "Used to indicate the number of entries in the  
		      rcIpPolicyNetTable." 
        ::= { rcIpPolicy 3 } 
 
rcIpPolicyNetTable OBJECT-TYPE 
        SYNTAX        SEQUENCE OF RcIpPolicyNetEntry 
        ACCESS        not-accessible 
        STATUS        mandatory 
        DESCRIPTION   "A table used to store different types list entries. 
                      Each row in the table contains a list entry that is 
                      used by a set of announce policies." 
        ::= { rcIpPolicy 4 } 
  
rcIpPolicyNetEntry OBJECT-TYPE 
        SYNTAX        RcIpPolicyNetEntry 
        ACCESS        not-accessible 
        STATUS        mandatory 
        DESCRIPTION   "Route entry attributes." 
        INDEX         {rcIpPolicyNetAddr, rcIpPolicyNetMask } 
        ::= { rcIpPolicyNetTable 1 } 
  
RcIpPolicyNetEntry ::= SEQUENCE { 
                        rcIpPolicyNetAddr IpAddress, 
                        rcIpPolicyNetMask IpAddress, 
                        rcIpPolicyNetId   INTEGER, 
                        rcIpPolicyNetNetListIdListSize INTEGER (0..128), 
                        rcIpPolicyNetNetListIdList OCTET STRING (SIZE(256)), 
                        rcIpPolicyNetRowStatus RowStatus 
                        } 
 
rcIpPolicyNetAddr OBJECT-TYPE 
        SYNTAX        IpAddress 
        ACCESS        read-only 
        STATUS        mandatory 
        DESCRIPTION   "The network address for this type of list entry. This  
                      value is required for all types of lists." 
        ::= { rcIpPolicyNetEntry 1 } 
  
rcIpPolicyNetMask OBJECT-TYPE 
        SYNTAX        IpAddress 
        ACCESS        read-only 
        STATUS        mandatory 
        DESCRIPTION   "The route mask for this type of list entry. This  
                      value is meaningful only if rcIpPolicyNetEntry  
                      is equal to exactNet(1), rangeNet(2), advertiseNet(3). 
                      For other types it should have the value 0.0.0.0." 
        ::= { rcIpPolicyNetEntry 2 } 
 
rcIpPolicyNetId OBJECT-TYPE 
        SYNTAX	      INTEGER  
        ACCESS	      read-only 
        STATUS	      mandatory 
        DESCRIPTION   "Used internally to recognize this entry." 
        ::= { rcIpPolicyNetEntry 3 } 
 
rcIpPolicyNetNetListIdListSize OBJECT-TYPE 
        SYNTAX	      INTEGER (0..128) 
        ACCESS	      read-only 
        STATUS	      mandatory 
        DESCRIPTION   "Used to indicate the number of id(s) in the  
		      rcIpPolicyNetListIdList variable." 
        ::= { rcIpPolicyNetEntry 4 } 
 
rcIpPolicyNetNetListIdList OBJECT-TYPE 
        SYNTAX	      OCTET STRING (SIZE(256))	 
        ACCESS	      read-only 
        STATUS	      mandatory 
        DESCRIPTION   "Used to indicate zero or more rcIpPolicyNetListEntry(s)   
                      that are referring to this entry.  Each list-id identifier 
                      is stored as two bytes in this array starting from  
                      offset zero.  Any unused bytes should be set to zero." 
        ::= { rcIpPolicyNetEntry 5 } 
 
rcIpPolicyNetRowStatus OBJECT-TYPE 
        SYNTAX		RowStatus 
        ACCESS		read-write 
        STATUS		mandatory 
        DESCRIPTION	"Row status of this entry." 
        ::= { rcIpPolicyNetEntry 6 } 
 
 
-- IP Policy Address List Table 
 
rcIpPolicyAddrListTableSize OBJECT-TYPE 
        SYNTAX        INTEGER 
        ACCESS        read-only 
        STATUS        mandatory 
        DESCRIPTION   "Used to indicate the number of entries in the 
                      rcIpPolicyAddrListTable." 
        ::= { rcIpPolicy 5 } 
  
rcIpPolicyAddrListTable OBJECT-TYPE 
        SYNTAX        SEQUENCE OF RcIpPolicyAddrListEntry 
        ACCESS        not-accessible 
        STATUS        mandatory 
        DESCRIPTION   "A table used to group rcIpPolicyAddrEntry(s)  
                      into a list." 
        ::= { rcIpPolicy 6 } 
 
rcIpPolicyAddrListEntry OBJECT-TYPE 
        SYNTAX        RcIpPolicyAddrListEntry 
        ACCESS        not-accessible 
        STATUS        mandatory 
        DESCRIPTION   "Route entry attributes." 
        INDEX         { rcIpPolicyAddrListId } 
        ::= { rcIpPolicyAddrListTable 1 } 
  
RcIpPolicyAddrListEntry ::= SEQUENCE { 
                  rcIpPolicyAddrListId INTEGER (1..1000), 
                  rcIpPolicyAddrListName DisplayString (SIZE(0..15)), 
                  rcIpPolicyAddrListIdListSize INTEGER (0..128), 
                  rcIpPolicyAddrListIdList OCTET STRING (SIZE(256)), 
                  rcIpPolicyAddrListPolicyIdListSize INTEGER (0..128), 
                  rcIpPolicyAddrListPolicyIdList OCTET STRING (SIZE(256)), 
                  rcIpPolicyAddrListRowStatus RowStatus 
                  } 
 
rcIpPolicyAddrListId OBJECT-TYPE 
        SYNTAX        INTEGER (1..1000) 
        ACCESS        read-only 
        STATUS        mandatory 
        DESCRIPTION   "A value that uniquely identifies this list of  
                       rcIpPolicyAddrListEntry." 
        ::= { rcIpPolicyAddrListEntry 1 } 
  
rcIpPolicyAddrListName OBJECT-TYPE 
        SYNTAX        DisplayString (SIZE (0..15)) 
        ACCESS        read-write 
        STATUS        mandatory 
        DESCRIPTION   "An administratively-assigned name for this list." 
        ::= { rcIpPolicyAddrListEntry 3 } 
  
rcIpPolicyAddrListIdListSize OBJECT-TYPE 
        SYNTAX        INTEGER (0..128) 
        ACCESS        read-only 
        STATUS        mandatory 
        DESCRIPTION   "Used to indicate the number of rcIpPolicyAddrNetEntry  
                      id(s) in the rcIpPolicyAddrListIdList variable." 
        ::= { rcIpPolicyAddrListEntry 4 } 
  
rcIpPolicyAddrListIdList OBJECT-TYPE 
        SYNTAX        OCTET STRING (SIZE(256)) 
        ACCESS        read-write 
        STATUS        mandatory 
        DESCRIPTION   "Used to indicate zero or more AddrListId  that 
                      are associated to this list.  Each AddrList identifier 
                      is stored as two bytes in this array starting from 
                      offset zero.  Any unused bytes should be set to zero." 
        ::= { rcIpPolicyAddrListEntry 5 } 
 
rcIpPolicyAddrListPolicyIdListSize OBJECT-TYPE 
        SYNTAX        INTEGER (0..128) 
        ACCESS        read-only 
        STATUS        mandatory 
        DESCRIPTION   "Used to indicate the number of policy id(s) in the  
                      Policy Id list. That are referring to this list." 
        ::= { rcIpPolicyAddrListEntry 6 } 
 
rcIpPolicyAddrListPolicyIdList OBJECT-TYPE 
        SYNTAX        OCTET STRING (SIZE(256)) 
        ACCESS        read-only 
        STATUS        mandatory 
        DESCRIPTION   "Used to indicate zero or more policies  that 
                      are referring to this entry.  Each policy identifier 
                      is stored as two bytes in this array starting from 
                      offset zero.  Any unused bytes should be set to zero." 
        ::= { rcIpPolicyAddrListEntry 7 } 
 
 
rcIpPolicyAddrListRowStatus OBJECT-TYPE 
        SYNTAX          RowStatus 
        ACCESS          read-write 
        STATUS          mandatory 
        DESCRIPTION     "Row status of this entry." 
        ::= { rcIpPolicyAddrListEntry 8 } 
  
 
-- RIP Announce Policy Table 
 
rcIpPolicyRipAnnounceTableSize OBJECT-TYPE 
        SYNTAX        INTEGER 
        ACCESS        read-only 
        STATUS        mandatory 
        DESCRIPTION   "Used to indicate the number of entries in the 
                      rcIpPolicyRipAnnounceTable." 
        ::= { rcIpPolicy 7 } 
 
rcIpPolicyRipAnnounceTable OBJECT-TYPE 
        SYNTAX        SEQUENCE OF RcIpPolicyRipAnnounceEntry 
        ACCESS        not-accessible 
        STATUS        mandatory 
        DESCRIPTION   "A table used to store set of announce policies  
		      configured for RIP routing protocol. The Number 
                      of entries is given by rcIpPolicyNumRipPolicies." 
        ::= { rcIpPolicy 8 } 
 
rcIpPolicyRipAnnounceEntry OBJECT-TYPE 
        SYNTAX        RcIpPolicyRipAnnounceEntry 
        ACCESS        not-accessible 
        STATUS        mandatory 
        DESCRIPTION   "Entry containing configuration information for a  
                      particular announce policy." 
        INDEX         { rcIpPolicyRipAnnounceId } 
        ::= { rcIpPolicyRipAnnounceTable 1 } 
 
RcIpPolicyRipAnnounceEntry ::= SEQUENCE { 
                rcIpPolicyRipAnnounceId INTEGER (1..1000), 
                rcIpPolicyRipAnnounceName DisplayString (SIZE(0..15)), 
                rcIpPolicyRipAnnounceEnable TruthValue, 
		rcIpPolicyRipAnnounceExactNetListId INTEGER (0..1000), 
		rcIpPolicyRipAnnounceRangeNetListId INTEGER (0..1000), 
		rcIpPolicyRipAnnounceRipGatewayListId INTEGER (0..1000), 
		rcIpPolicyRipAnnounceRipInterfaceListId INTEGER (0..1000), 
		rcIpPolicyRipAnnounceOspfRouterListId INTEGER (0..1000), 
		rcIpPolicyRipAnnounceAnnounceInterfaceListId INTEGER (0..1000), 
                rcIpPolicyRipAnnouncePrecedence INTEGER, 
                rcIpPolicyRipAnnounceRouteSource INTEGER, 
		rcIpPolicyRipAnnounceAdvertiseNetListId INTEGER (0..1000), 
                rcIpPolicyRipAnnounceAction INTEGER, 
                rcIpPolicyRipAnnounceOspfRouteType INTEGER, 
                rcIpPolicyRipAnnounceRipMetric INTEGER (0..15), 
                rcIpPolicyRipAnnounceRowStatus RowStatus  
                } 
 
rcIpPolicyRipAnnounceId OBJECT-TYPE 
        SYNTAX        INTEGER (1..1000) 
        ACCESS        read-only 
        STATUS        mandatory 
        DESCRIPTION   "A value that uniquely identifies the policy 
                      associated with this entry." 
        ::= { rcIpPolicyRipAnnounceEntry 1 } 
 
rcIpPolicyRipAnnounceName OBJECT-TYPE 
        SYNTAX        DisplayString (SIZE (0..15)) 
        ACCESS        read-write 
        STATUS        mandatory 
        DESCRIPTION   "An administratively-assigned name for this policy." 
        ::= { rcIpPolicyRipAnnounceEntry 2 } 
 
rcIpPolicyRipAnnounceEnable OBJECT-TYPE 
        SYNTAX        TruthValue  
        ACCESS        read-write 
        STATUS        mandatory 
        DESCRIPTION   "It indicates whether this policy is enabled or not. 
                      The policy should be applied only if it is set to 
'true'." 
	DEFVAL        {true} 
        ::= { rcIpPolicyRipAnnounceEntry 3 } 
 
rcIpPolicyRipAnnounceExactNetListId OBJECT-TYPE 
        SYNTAX        INTEGER (0..1000) 
        ACCESS        read-write 
        STATUS        mandatory 
        DESCRIPTION   "Used to indicate the number of 'exact' type entries 
                      that are configured for this policy. 
 
 		      An entry with type 'exactNet' or 'rangeNet' represents 
                      the network list.  This indicates which networks will 
                      match a particular announce policy.  
  
                      An entry with a 'exact' type means to only match the 
                      specific network advertisement (netaddr & mask). 
 
                      An 'exact' entry with addr=0.0.0.0 and mask=0.0.0.0 
                      means 'match the default route'. 
 
                      If set to '0', this policy applies to all the routes." 
 
        ::= { rcIpPolicyRipAnnounceEntry 4 } 
 
rcIpPolicyRipAnnounceRangeNetListId OBJECT-TYPE 
        SYNTAX        INTEGER (0..1000) 
        ACCESS        read-write 
        STATUS        mandatory 
        DESCRIPTION   "Used to indicate zero or more 'range' network entries   
                      that are associated with this policy.   
 
                      An entry with a 'range' type means to match any network 
		      number that falls in the range indicated by the addr & 
                      mask. 
 
                      A 'range' entry with addr=0.0.0.0 and mask=0.0.0.0 
                      means 'match any route'. 
 
                      If set to '0', this policy applies to all the routes." 
 
        ::= { rcIpPolicyRipAnnounceEntry 5 } 
 
rcIpPolicyRipAnnounceRipGatewayListId OBJECT-TYPE 
        SYNTAX        INTEGER (0..1000) 
        ACCESS        read-write 
        STATUS        mandatory 
        DESCRIPTION   "Used to identify the RIP-gatewayList in the list  
                      that are associated with this policy.  
 
                      This field has meaning only for RIP sourced routes and  
                      if RIP is included as a RouteSource.  
                      The list contains one or more rip-routers (other side 
                      of the interface) addresses that could send RIP updates  
                      to this router.  If a router  
                      address is included in this list, this policy applies to  
                      RIP advertisements from that router. 
  
                      If set to '0', this policy applies to RIP updates 
                      received from any rip routers/interfaces." 
  
        ::= { rcIpPolicyRipAnnounceEntry 6 } 
 
rcIpPolicyRipAnnounceRipInterfaceListId OBJECT-TYPE 
        SYNTAX        INTEGER (0..1000) 
        ACCESS        read-write 
        STATUS        mandatory 
        DESCRIPTION   "Used to indicate the number of entries in the  
                      ripInterfaceIdList that are configured for this policy. 
 
                      This field has meaning only for RIP sourced routes and 
                      if RIP is included as a RouteSource. The list contains  
                      one or more rip-interface addresses on this router. 
                      If an interface address is incuded in this list, this 
                      policy applies to RIP advertisements received on that 
                      interface. 
 
                      A value of '0' indicates thtat this policy applies to 
                      RIP updates received on any rip-interface." 
 
        ::= { rcIpPolicyRipAnnounceEntry 7 } 
 
rcIpPolicyRipAnnounceOspfRouterListId OBJECT-TYPE 
        SYNTAX        INTEGER (0..1000)  
        ACCESS        read-write 
        STATUS        mandatory 
        DESCRIPTION   "Used to indicate the number of entries in the  
                      OspfRouteIds that are configured for this policy. 
 
                      This field has meaning only for OSPF sourced routes and 
                      if OSPF is included as a RouteSource. The list contains 
                      one or more router IDs of OSPF routers. If a routerId  
                      is included in this list, this policy applies to 
                      OSPF advertisements received from that router. 
 
                      A value of '0' indicates that this policy applies to 
                      any OPSF routes received from any router." 
 
        ::= { rcIpPolicyRipAnnounceEntry 8 } 
 
rcIpPolicyRipAnnounceAnnounceInterfaceListId OBJECT-TYPE 
        SYNTAX        INTEGER (0..1000) 
        ACCESS        read-write 
        STATUS        mandatory 
        DESCRIPTION   "Used to indicate the number of entries in the  
                      AnnounceInterfaceids that are configured for this policy. 
 
                      The list contains one or more outbound interface  
                      addresses. If the outbound interface address in this 
                      list, the policy applies to RIP updates/advertisements 
                      sent through this  interface.  
 
                      A value of '0' indicates that this policy applies to 
                      any outbound RIP interface on this router." 
 
        ::= { rcIpPolicyRipAnnounceEntry 9 } 
 
rcIpPolicyRipAnnouncePrecedence OBJECT-TYPE 
        SYNTAX        INTEGER (0..65535)  
        ACCESS        read-write 
        STATUS        mandatory 
        DESCRIPTION   "Is used while comparing this policy rule with other  
                      policy that a given route may match.  A rule with a  
                      higher precedence value will be chosen over one with  
                      a smaller value. In the case of a tie, the PolicyId is  
                      used (larger wins)." 
        ::= { rcIpPolicyRipAnnounceEntry 10 } 
 
rcIpPolicyRipAnnounceRouteSource OBJECT-TYPE 
        SYNTAX        INTEGER { 
			 direct(1), 
			 static(2), 
			 rip(4), 
			 ospf(8), 
			 any(15)  
		      } 
        ACCESS        read-write 
        STATUS        mandatory 
        DESCRIPTION   "Is represented as bitset to indicate route sources.  
                      It can contain one or more route sources. If the route  
                      source is in this bit map, then a route from that source  
                      that meets the other criteria of this policy will match  
                      the policy." 
        DEFVAL        { any } 
        ::= { rcIpPolicyRipAnnounceEntry 11 } 
 
rcIpPolicyRipAnnounceAdvertiseNetListId OBJECT-TYPE  
        SYNTAX        INTEGER (0..1000) 
        ACCESS        read-write 
        STATUS        mandatory 
        DESCRIPTION   "Used to indicate the number of entries in the 
                      AdvertiseNetList that are configured for this policy. 
 
                      This has meaning only if the Action is set to 'announce'. 
                      It is useful to send or advertise networks that differ  
                      from actual network in the routing table. Also allows  
                      advertisement of an aggregate or default along with the  
                      actual network.  Aggregation is useful if a number of 
                      routes in the table falls in a certain range. Can save 
                      space by sending aggregate route instead of the individual 
                      routes.  
     
                      Actual network/route is included in the update 
                      only if there is a match or there there is an entry 
                      (address & mask pair) 255.255.255.255/255.255.255.255    
                      in the list." 
 
        ::= { rcIpPolicyRipAnnounceEntry 12 } 
 
rcIpPolicyRipAnnounceAction OBJECT-TYPE 
        SYNTAX        INTEGER { 
			 announce(1), 
			 ignore(2) 
		      } 
        ACCESS        read-write 
        STATUS        mandatory 
        DESCRIPTION   "It indicates whether the route should be announced  
                      or not." 
        DEFVAL  { ignore } 
        ::= { rcIpPolicyRipAnnounceEntry 13 } 
 
rcIpPolicyRipAnnounceOspfRouteType OBJECT-TYPE 
        SYNTAX        INTEGER { 
			 type1(1), 
                         type2(2), 
                         external(3), 
                         internal(4), 
                         any(5) 
                      } 
        ACCESS        read-write 
        STATUS        mandatory 
        DESCRIPTION   "Ospf Route type. It applies to OSPF sourced routes only. 
		      'type1' means to apply this policy to only type1 OSPF  
                      external routes. 'type2' means to apply this policy to  
                      only type2 OSPF external routes. 'internal' means 'match  
                      ospf specfic routes'. 'any' means apply this policy to  
                      all OSPF external routes."		 
         DEFVAL  { any } 
        ::= { rcIpPolicyRipAnnounceEntry 14 } 
 
rcIpPolicyRipAnnounceRipMetric OBJECT-TYPE 
        SYNTAX        INTEGER (0..15) 
        ACCESS        read-write 
        STATUS        mandatory 
        DESCRIPTION   "RIP metric. The value is meaningful only if the action  
                      is set to 'announce'. This is optional export metric  
                      to use when advertising a route that matches this policy. 
                      If set to zero, the routing table metric calculated for  
                      RIP is is used." 
        DEFVAL        {0} 
        ::= { rcIpPolicyRipAnnounceEntry 15 } 
 
rcIpPolicyRipAnnounceRowStatus OBJECT-TYPE 
        SYNTAX		RowStatus 
        ACCESS		read-write 
        STATUS		mandatory 
        DESCRIPTION	"Row status of this entry." 
        ::= { rcIpPolicyRipAnnounceEntry 16 } 
 
-- OSPF Announce policy table. 
 
rcIpPolicyOspfAnnounceTableSize OBJECT-TYPE 
        SYNTAX        INTEGER 
        ACCESS        read-only 
        STATUS        mandatory 
        DESCRIPTION   "Used to indicate the number of entries in the 
                      rcIpPolicyOspfAnnounceTable." 
        ::= { rcIpPolicy 9 } 
 
 
rcIpPolicyOspfAnnounceTable OBJECT-TYPE 
        SYNTAX        SEQUENCE OF RcIpPolicyOspfAnnounceEntry 
        ACCESS        not-accessible 
        STATUS        mandatory 
        DESCRIPTION   "A table used to store set of announce policies  
		      configured for OSPF routing protocol. The Number 
                      of entries is given by rcIpPolicyNumOspfPolicies." 
        ::= { rcIpPolicy 10 } 
 
rcIpPolicyOspfAnnounceEntry OBJECT-TYPE 
        SYNTAX        RcIpPolicyOspfAnnounceEntry 
        ACCESS        not-accessible 
        STATUS        mandatory 
        DESCRIPTION   "Entry containing configuration information for a  
                      particular announce policy." 
        INDEX         { rcIpPolicyOspfAnnounceId } 
        ::= { rcIpPolicyOspfAnnounceTable 1 } 
 
RcIpPolicyOspfAnnounceEntry ::= SEQUENCE { 
                rcIpPolicyOspfAnnounceId INTEGER (2001..3000), 
                rcIpPolicyOspfAnnounceName DisplayString (SIZE (0..15)), 
                rcIpPolicyOspfAnnounceEnable TruthValue, 
		rcIpPolicyOspfAnnounceExactNetListId INTEGER (0..1000), 
		rcIpPolicyOspfAnnounceRangeNetListId INTEGER (0..1000), 
		rcIpPolicyOspfAnnounceRipGatewayListId INTEGER (0..1000), 
		rcIpPolicyOspfAnnounceRipInterfaceListId INTEGER (0..1000), 
                rcIpPolicyOspfAnnouncePrecedence INTEGER, 
                rcIpPolicyOspfAnnounceRouteSource INTEGER, 
		rcIpPolicyOspfAnnounceAdvertiseNetListId INTEGER (0..1000), 
                rcIpPolicyOspfAnnounceAction INTEGER, 
                rcIpPolicyOspfAnnounceExtMetricType INTEGER, 
                rcIpPolicyOspfAnnounceExtMetric INTEGER (0..65535), 
                rcIpPolicyOspfAnnounceRowStatus RowStatus  
                } 
 
rcIpPolicyOspfAnnounceId OBJECT-TYPE 
        SYNTAX        INTEGER (2001..3000) 
        ACCESS        read-only 
        STATUS        mandatory 
        DESCRIPTION   "A value that uniquely identifies the policy 
                      associated with this entry." 
        ::= { rcIpPolicyOspfAnnounceEntry 1 } 
 
rcIpPolicyOspfAnnounceName OBJECT-TYPE 
        SYNTAX        DisplayString (SIZE (0..15)) 
        ACCESS        read-write 
        STATUS        mandatory 
        DESCRIPTION   "An administratively-assigned name for this policy." 
        ::= { rcIpPolicyOspfAnnounceEntry 2 } 
 
rcIpPolicyOspfAnnounceEnable OBJECT-TYPE 
        SYNTAX        TruthValue  
        ACCESS        read-write 
        STATUS        mandatory 
        DESCRIPTION   "It indicates whether this policy is enabled or not. 
                      The policy should be applied only if it is set to  
		      'true'." 
	DEFVAL        {true} 
        ::= { rcIpPolicyOspfAnnounceEntry 3 } 
 
rcIpPolicyOspfAnnounceExactNetListId OBJECT-TYPE 
        SYNTAX        INTEGER (0..1000) 
        ACCESS        read-write 
        STATUS        mandatory 
        DESCRIPTION   "Used to indicate the number of 'exact' type entries 
                      that are configured for this policy. 
  
                      An entry with type 'exactNet' or 'rangeNet' represents 
                      the network list.  This indicates which networks will 
                      match a particular announce policy. 
  
                      An entry with a 'exact' type means to only match the 
                      specific network advertisement (netaddr & mask). 
  
                      An 'exact' entry with addr=0.0.0.0 and mask=0.0.0.0 
                      means 'match the default route'. 
  
                      If set to '0', this policy applies to all the routes." 
  
        ::= { rcIpPolicyOspfAnnounceEntry 4 } 
 
rcIpPolicyOspfAnnounceRangeNetListId OBJECT-TYPE 
        SYNTAX        INTEGER (0..1000) 
        ACCESS        read-write 
        STATUS        mandatory 
        DESCRIPTION   "Used to indicate zero or more 'range' network entries 
                      that are associated with this policy. 
  
                      An entry with a 'range' type means to match any network 
                      number that falls in the range indicated by the addr & 
                      mask. 
  
                      A 'range' entry with addr=0.0.0.0 and mask=0.0.0.0 
                      means 'match any route'. 
  
                      If set to '0', this policy applies to all the routes." 
 
        ::= { rcIpPolicyOspfAnnounceEntry 5 } 
 
rcIpPolicyOspfAnnounceRipGatewayListId OBJECT-TYPE 
        SYNTAX        INTEGER (0..1000) 
        ACCESS        read-write 
        STATUS        mandatory 
        DESCRIPTION   "Used to identify the RIP-gatewayList in the list 
                      that are associated with this policy. 
  
                      This field has meaning only for RIP sourced routes and 
                      if RIP is included as a RouteSource. 
                      The list contains one or more rip-routers (other side 
                      of the interface) addresses that could send RIP updates 
                      to this router.  If a router 
                      address is included in this list, this policy applies to 
                      RIP advertisements from that router. 
  
                      If set to '0', this policy applies to RIP updates 
                      received from any rip routers/interfaces." 
 
        ::= { rcIpPolicyOspfAnnounceEntry 6 } 
 
rcIpPolicyOspfAnnounceRipInterfaceListId OBJECT-TYPE 
        SYNTAX        INTEGER (0..1000) 
        ACCESS        read-write 
        STATUS        mandatory 
        DESCRIPTION   "Used to indicate the number of entries in the 
                      ripInterfaceIdList that are configured for this policy. 
  
                      This field has meaning only for RIP sourced routes and 
                      if RIP is included as a RouteSource. The list contains 
                      one or more rip-interface addresses on this router. 
                      If an interface address is incuded in this list, this 
                      policy applies to RIP advertisements received on that 
                      interface. 
  
                      A value of '0' indicates thtat this policy applies to 
                      RIP updates received on any rip-interface." 
 
        ::= { rcIpPolicyOspfAnnounceEntry 7 } 
 
 
rcIpPolicyOspfAnnouncePrecedence OBJECT-TYPE 
        SYNTAX        INTEGER (0..65535)  
        ACCESS        read-write 
        STATUS        mandatory 
        DESCRIPTION   "Is used while comparing this policy rule with other  
                      policy that a given route may match.  A rule with a  
                      higher precedence value will be chosen over one with  
                      a smaller value. In the case of a tie, the PolicyId is  
                      used (larger wins)." 
        ::= { rcIpPolicyOspfAnnounceEntry 8 } 
 
rcIpPolicyOspfAnnounceRouteSource OBJECT-TYPE 
        SYNTAX        INTEGER { 
			 direct(1), 
			 static(2), 
			 rip(4), 
			 any(7)  
		      } 
        ACCESS        read-write 
        STATUS        mandatory 
        DESCRIPTION   "Is represented as bit map to indicate route sources.  
                      It can contain one or more route sources. If the route  
                      source is in this bit map, then a route from that source  
                      that meets the other criteria of this policy will match  
                      the policy." 
        DEFVAL        { any } 
        ::= { rcIpPolicyOspfAnnounceEntry 9 } 
 
rcIpPolicyOspfAnnounceAdvertiseNetListId OBJECT-TYPE  
        SYNTAX        INTEGER (0..1000) 
        ACCESS        read-write 
        STATUS        mandatory 
        DESCRIPTION   "Used to indicate the number of entries in the 
                      AdvertiseNetList that are configured for this policy. 
  
                      This has meaning only if the Action is set to 'announce'. 
                      It is useful to send or advertise networks that differ 
                      from actual network in the routing table. Also allows 
                      advertisement of an aggregate or default along with the 
                      actual network.  Aggregation is useful if a number of 
                      routes in the table falls in a certain range. Can save 
                      space by sending aggregate route instead of the individual 
                      routes. 
  
                      Actual network/route is included in the update 
                      only if there is a match or there there is an entry 
                      (address & mask pair) 255.255.255.255/255.255.255.255 
                      in the list." 
 
        ::= { rcIpPolicyOspfAnnounceEntry 10 } 
 
rcIpPolicyOspfAnnounceAction OBJECT-TYPE 
        SYNTAX        INTEGER { 
			 announce(1), 
			 ignore(2) 
		      } 
        ACCESS        read-write 
        STATUS        mandatory 
        DESCRIPTION   "It indicates whether the route should be announced  
                      or not." 
         DEFVAL  { ignore } 
        ::= { rcIpPolicyOspfAnnounceEntry 11 } 
 
rcIpPolicyOspfAnnounceExtMetricType OBJECT-TYPE 
        SYNTAX        INTEGER { 
			 type1(1), 
                         type2(2) 
                      } 
        ACCESS        read-write 
        STATUS        mandatory 
        DESCRIPTION   "Ospf External metric type. It is used to indicate 
		      what type of the external metric it is. 'type1' means to  
                      the cost is 'internal ospf cost + ExtMetric'.  
                      'type2' means the ospf-metric is equal to 'type2'." 
         DEFVAL  { type2 } 
        ::= { rcIpPolicyOspfAnnounceEntry 12 } 
 
rcIpPolicyOspfAnnounceExtMetric OBJECT-TYPE 
        SYNTAX        INTEGER (0..65535) 
        ACCESS        read-write 
        STATUS        mandatory 
        DESCRIPTION   "OSPF External metric. The value is meaningful only if  
                      the action is set to 'announce'. This is optional export  
                      metric to use when advertising a route that matches this  
                      policy. Value '0' is used to indicate that route's actual 
                      cost is used to announce." 
        DEFVAL        { 0 } 
        ::= { rcIpPolicyOspfAnnounceEntry 13 } 
 
rcIpPolicyOspfAnnounceRowStatus OBJECT-TYPE 
        SYNTAX		RowStatus 
        ACCESS		read-write 
        STATUS		mandatory 
        DESCRIPTION	"Row status of this entry." 
        ::= { rcIpPolicyOspfAnnounceEntry 14 } 
  
-- IP Accept Policy Groups 
 
-- RIP Accept policy table. 
 
rcIpPolicyRipAcceptTableSize OBJECT-TYPE 
        SYNTAX        INTEGER 
        ACCESS        read-only 
        STATUS        mandatory 
        DESCRIPTION   "Used to indicate the number of entries in the 
                      rcIpPolicyRipAcceptTable." 
        ::= { rcIpPolicy 11 } 
 
rcIpPolicyRipAcceptTable OBJECT-TYPE 
        SYNTAX        SEQUENCE OF RcIpPolicyRipAcceptEntry 
        ACCESS        not-accessible 
        STATUS        mandatory 
        DESCRIPTION   "A table used to store set of accept policies  
		      configured for RIP routing protocol. The Number 
                      of entries is given by rcIpPolicyNumRipPolicies." 
        ::= { rcIpPolicy 12 } 
 
rcIpPolicyRipAcceptEntry OBJECT-TYPE 
        SYNTAX        RcIpPolicyRipAcceptEntry 
        ACCESS        not-accessible 
        STATUS        mandatory 
        DESCRIPTION   "Entry containing configuration information for a  
                      particular accept policy." 
        INDEX         { rcIpPolicyRipAcceptId } 
        ::= { rcIpPolicyRipAcceptTable 1 } 
 
RcIpPolicyRipAcceptEntry ::= SEQUENCE { 
                rcIpPolicyRipAcceptId INTEGER (4001..5000), 
                rcIpPolicyRipAcceptName DisplayString (SIZE(0..15)), 
                rcIpPolicyRipAcceptEnable TruthValue, 
		rcIpPolicyRipAcceptExactNetListId INTEGER (0..1000), 
		rcIpPolicyRipAcceptRangeNetListId INTEGER (0..1000), 
		rcIpPolicyRipAcceptRipGatewayListId INTEGER (0..1000), 
		rcIpPolicyRipAcceptRipInterfaceListId INTEGER (0..1000), 
                rcIpPolicyRipAcceptPrecedence INTEGER, 
                rcIpPolicyRipAcceptAction INTEGER, 
		rcIpPolicyRipAcceptInjectNetListId INTEGER (0..1000), 
                rcIpPolicyRipAcceptApplyMask IpAddress, 
                rcIpPolicyRipAcceptRowStatus RowStatus  
                } 
 
rcIpPolicyRipAcceptId OBJECT-TYPE 
        SYNTAX        INTEGER (4001..5000) 
        ACCESS        read-only 
        STATUS        mandatory 
        DESCRIPTION   "A value that uniquely identifies the policy 
                      associated with this entry." 
        ::= { rcIpPolicyRipAcceptEntry 1 } 
 
rcIpPolicyRipAcceptName OBJECT-TYPE 
        SYNTAX        DisplayString (SIZE (0..15)) 
        ACCESS        read-write 
        STATUS        mandatory 
        DESCRIPTION   "An administratively-assigned name for this policy." 
        ::= { rcIpPolicyRipAcceptEntry 2 } 
 
rcIpPolicyRipAcceptEnable OBJECT-TYPE 
        SYNTAX        TruthValue  
        ACCESS        read-write 
        STATUS        mandatory 
        DESCRIPTION   "It indicates whether this policy is enabled or not. 
                      The policy should be applied only if it is set to 'true'." 
	DEFVAL        {true} 
        ::= { rcIpPolicyRipAcceptEntry 3 } 
 
rcIpPolicyRipAcceptExactNetListId OBJECT-TYPE 
        SYNTAX        INTEGER (0..1000) 
        ACCESS        read-write 
        STATUS        mandatory 
        DESCRIPTION   "Used to indicate the number of 'exact' type entries 
                      that are configured for this policy. 
 
 		      An entry with type 'exactNet' or 'rangeNet' represents 
                      the network list.  This indicates which networks will 
                      match a particular accept policy.  
  
                      An entry with a 'exact' type means to only match the 
                      specific network advertisement (netaddr & mask). 
 
                      An 'exact' entry with addr=0.0.0.0 and mask=0.0.0.0 
                      means 'match the default route'." 
        ::= { rcIpPolicyRipAcceptEntry 4 } 
 
rcIpPolicyRipAcceptRangeNetListId OBJECT-TYPE 
        SYNTAX        INTEGER (0..1000) 
        ACCESS        read-write 
        STATUS        mandatory 
        DESCRIPTION   "Used to indicate zero or more 'range' network entries   
                      that are associated with this policy.   
 
                      An entry with a 'range' type means to match any network 
		      number that falls in the range indicated by the addr & 
                      mask. 
 
                      A 'range' entry with addr=0.0.0.0 and mask=0.0.0.0 
                      means 'match any route'. 
 
                      A null list means 'match any route'." 
        ::= { rcIpPolicyRipAcceptEntry 5 } 
 
rcIpPolicyRipAcceptRipGatewayListId OBJECT-TYPE 
        SYNTAX        INTEGER (0..1000) 
        ACCESS        read-write 
        STATUS        mandatory 
        DESCRIPTION   "Used to identify the RIP-gatewayList in the  
                      PolicyListTable that iares associated with this  
                      policy. The list contains the addresses of one or more  
                      routers that could send RIP updates to this router. 
                      If a router address is included in this list, this 
                      policy applies to RIP advertisements from that router. 
  
                      If set to '0', this policy applies to RIP updates 
                      from any router." 
 
        ::= { rcIpPolicyRipAcceptEntry 6 } 
 
rcIpPolicyRipAcceptRipInterfaceListId OBJECT-TYPE 
        SYNTAX        INTEGER (0..1000) 
        ACCESS        read-write 
        STATUS        mandatory 
        DESCRIPTION   "Used to indicate ListId defined for RipInterfaceList 
                      in the rcIpPolicyListTable that is assiciated  
                      with this policy.  
                      The list contains the addresses of one or more interfaces 
                      on this router.  If an interface address is included in  
                      the list, this policy applies to RIP advertisements  
                      received on that interface. 
  
                      If set to '0', this policy applies to RIP updates 
                      received on any interface." 
 
        ::= { rcIpPolicyRipAcceptEntry 7 } 
 
rcIpPolicyRipAcceptPrecedence OBJECT-TYPE 
        SYNTAX        INTEGER (0..65535)  
        ACCESS        read-write 
        STATUS        mandatory 
        DESCRIPTION   "Is used while comparing this policy rule with other  
                      policy that a given route may match.  A rule with a  
                      higher precedence value will be chosen over one with  
                      a smaller value. In the case of a tie, the PolicyId is  
                      used (larger wins)." 
        ::= { rcIpPolicyRipAcceptEntry 8 } 
 
rcIpPolicyRipAcceptAction OBJECT-TYPE 
        SYNTAX        INTEGER { 
			 accept(1), 
			 ignore(2) 
		      } 
        ACCESS        read-write 
        STATUS        mandatory 
        DESCRIPTION   "It indicates whether the route should be acceptd  
                      or not." 
         DEFVAL  { ignore } 
        ::= { rcIpPolicyRipAcceptEntry 9 } 
 
rcIpPolicyRipAcceptInjectNetListId OBJECT-TYPE  
        SYNTAX        INTEGER (0..1000) 
        ACCESS        read-write 
        STATUS        mandatory 
        DESCRIPTION   "Used to indicate the ListId of the InjectNetList 
                      in the rcIpPolicyListTable entry that is assiciated 
                      with for this policy. If teh action is 'accept' and if it 
                      is desired to insert networks into the routing table that 
                      differ from the actual advertised network. For instance, 
                      if a number of networks in a certain range are learned 
                      and an aggregate advertisement could be inserted instead 
                      of the individual networks.  
 
                      Upon receiving a route that matches this policy, all 
                      networks in this list will be considered for inclusion  
                      in the routing table. If the list is empty or if the 
                      value of the ListId is '0' then the actual received 
                      network is considered. 
 
                      An encoding of 255.255.255.255/255.255.255.255 means 
                      'match the actual received network.'. This allows 
                      insertion of an aggregate or default along with the  
                      actual netowrk." 
        ::= { rcIpPolicyRipAcceptEntry 10 } 
 
rcIpPolicyRipAcceptApplyMask OBJECT-TYPE 
        SYNTAX		IpAddress 
        ACCESS		read-write 
        STATUS		mandatory 
        DESCRIPTION	"If the 'action' is set to 'accept' and the actual 
                        received network will be considered, this is an 
                        optional IP address mask that will be applied to the  
                        network number from the RIP update.  This is used to  
                        override the interface's subnet mask in the presence  
                        of networks with variable length subnet masks." 
        ::= { rcIpPolicyRipAcceptEntry 11 } 
 
rcIpPolicyRipAcceptRowStatus OBJECT-TYPE 
        SYNTAX		RowStatus 
        ACCESS		read-write 
        STATUS		mandatory 
        DESCRIPTION	"Row status of this entry." 
        ::= { rcIpPolicyRipAcceptEntry 12 } 
 
-- OSPF Accept policy table. 
  
rcIpPolicyOspfAcceptTableSize OBJECT-TYPE 
        SYNTAX        INTEGER 
        ACCESS        read-only 
        STATUS        mandatory 
        DESCRIPTION   "Used to indicate the number of entries in the 
                      rcIpPolicyOspfAcceptTable." 
        ::= { rcIpPolicy 13 } 
 
rcIpPolicyOspfAcceptTable OBJECT-TYPE 
        SYNTAX        SEQUENCE OF RcIpPolicyOspfAcceptEntry 
        ACCESS        not-accessible 
        STATUS        mandatory 
        DESCRIPTION   "A table used to store set of accept policies  
		      configured for RIP routing protocol. The Number 
                      of entries is given by rcIpPolicyNumRipPolicies." 
        ::= { rcIpPolicy 14 } 
 
rcIpPolicyOspfAcceptEntry OBJECT-TYPE 
        SYNTAX        RcIpPolicyOspfAcceptEntry 
        ACCESS        not-accessible 
        STATUS        mandatory 
        DESCRIPTION   "Entry containing configuration information for a  
                      particular accept policy." 
        INDEX         { rcIpPolicyOspfAcceptId } 
        ::= { rcIpPolicyOspfAcceptTable 1 } 
 
RcIpPolicyOspfAcceptEntry ::= SEQUENCE { 
                rcIpPolicyOspfAcceptId INTEGER (6001..7000), 
                rcIpPolicyOspfAcceptName DisplayString (SIZE(0..15)), 
                rcIpPolicyOspfAcceptEnable TruthValue, 
		rcIpPolicyOspfAcceptExactNetListId INTEGER (0..1000), 
		rcIpPolicyOspfAcceptRangeNetListId INTEGER (0..1000), 
                rcIpPolicyOspfAcceptPrecedence INTEGER, 
                rcIpPolicyOspfAcceptAction INTEGER, 
		rcIpPolicyOspfAcceptInjectNetListId INTEGER (0..1000), 
                rcIpPolicyOspfAcceptExtType INTEGER, 
                rcIpPolicyOspfAcceptRowStatus RowStatus  
                } 
 
rcIpPolicyOspfAcceptId OBJECT-TYPE 
        SYNTAX        INTEGER (6001..7000) 
        ACCESS        read-only 
        STATUS        mandatory 
        DESCRIPTION   "A value that uniquely identifies the policy 
                      associated with this entry." 
        ::= { rcIpPolicyOspfAcceptEntry 1 } 
 
rcIpPolicyOspfAcceptName OBJECT-TYPE 
        SYNTAX        DisplayString (SIZE (0..15)) 
        ACCESS        read-write 
        STATUS        mandatory 
        DESCRIPTION   "An administratively-assigned name for this policy." 
        ::= { rcIpPolicyOspfAcceptEntry 2 } 
 
rcIpPolicyOspfAcceptEnable OBJECT-TYPE 
        SYNTAX        TruthValue  
        ACCESS        read-write 
        STATUS        mandatory 
        DESCRIPTION   "It indicates whether this policy is enabled or not. 
                      The policy should be applied only if it is set to 
'true'." 
	DEFVAL        {true} 
        ::= { rcIpPolicyOspfAcceptEntry 3 } 
 
rcIpPolicyOspfAcceptExactNetListId OBJECT-TYPE 
        SYNTAX        INTEGER (0..1000) 
        ACCESS        read-write 
        STATUS        mandatory 
        DESCRIPTION   "Used to indicate the number of 'exact' type entries 
                      that are configured for this policy. 
 
 		      An entry with type 'exactNet' or 'rangeNet' represents 
                      the network list.  This indicates which networks will 
                      match a particular accept policy.  
  
                      An entry with a 'exact' type means to only match the 
                      specific network advertisement (netaddr & mask). 
 
                      An 'exact' entry with addr=0.0.0.0 and mask=0.0.0.0 
                      means 'match the default route'." 
        ::= { rcIpPolicyOspfAcceptEntry 4 } 
 
rcIpPolicyOspfAcceptRangeNetListId OBJECT-TYPE 
        SYNTAX        INTEGER (0..1000) 
        ACCESS        read-write 
        STATUS        mandatory 
        DESCRIPTION   "Used to indicate zero or more 'range' network entries   
                      that are associated with this policy.   
 
                      An entry with a 'range' type means to match any network 
		      number that falls in the range indicated by the addr & 
                      mask. 
 
                      A 'range' entry with addr=0.0.0.0 and mask=0.0.0.0 
                      means 'match any route'. 
 
                      A null list means 'match any route'." 
        ::= { rcIpPolicyOspfAcceptEntry 5 } 
 
rcIpPolicyOspfAcceptPrecedence OBJECT-TYPE 
        SYNTAX        INTEGER (0..65535)  
        ACCESS        read-write 
        STATUS        mandatory 
        DESCRIPTION   "Is used while comparing this policy rule with other  
                      policy that a given route may match.  A rule with a  
                      higher precedence value will be chosen over one with  
                      a smaller value. In the case of a tie, the PolicyId is  
                      used (larger wins)." 
        ::= { rcIpPolicyOspfAcceptEntry 6 } 
 
rcIpPolicyOspfAcceptAction OBJECT-TYPE 
        SYNTAX        INTEGER { 
			 accept(1), 
			 ignore(2) 
		      } 
        ACCESS        read-write 
        STATUS        mandatory 
        DESCRIPTION   "It indicates whether the route should be acceptd  
                      or not." 
         DEFVAL  { ignore } 
        ::= { rcIpPolicyOspfAcceptEntry 7 } 
 
rcIpPolicyOspfAcceptInjectNetListId OBJECT-TYPE  
        SYNTAX        INTEGER (0..1000) 
        ACCESS        read-write 
        STATUS        mandatory 
        DESCRIPTION   "Used to indicate the ListId of the InjectNetList 
                      in the rcIpPolicyListTable entry that is assiciated 
                      with for this policy. If teh action is 'accept' and if it 
                      is desired to insert networks into the routing table that 
                      differ from the actual advertised network. For instance, 
                      if a number of networks in a certain range are learned 
                      and an aggregate advertisement could be inserted instead 
                      of the individual networks.  
 
                      Upon receiving a route that matches this policy, all 
                      networks in this list will be considered for inclusion  
                      in the routing table. If the list is empty or if the 
                      value of the ListId is '0' then the actual received 
                      network is considered. 
 
                      An encoding of 255.255.255.255/255.255.255.255 means 
                      'match the actual received network.'. This allows 
                      insertion of an aggregate or default along with the  
                      actual netowrk." 
        ::= { rcIpPolicyOspfAcceptEntry 8 } 
 
rcIpPolicyOspfAcceptExtType OBJECT-TYPE 
        SYNTAX		INTEGER { 
                           type1(1), 
                           type2(2), 
                           any(3) 
                        } 
 
        ACCESS		read-write 
        STATUS		mandatory 
        DESCRIPTION     "Used to indicate the ospf external type. This  
                        parameter describes which types of OSPF ASE routes 
                        match this policy.  
                        'any' means 'match either ASE type 1 or 2'.	 
                        'type1' means 'match any external type 1'. 
                        'type2' means 'match any external type 2" 
        ::= { rcIpPolicyOspfAcceptEntry 9 } 
 
rcIpPolicyOspfAcceptRowStatus OBJECT-TYPE 
        SYNTAX		RowStatus 
        ACCESS		read-write 
        STATUS		mandatory 
        DESCRIPTION	"Row status of this entry." 
        ::= { rcIpPolicyOspfAcceptEntry 10 } 
 
 
-- IP Policy Network List Table 
 
rcIpPolicyNetListTableSize OBJECT-TYPE 
        SYNTAX        INTEGER 
        ACCESS        read-only 
        STATUS        mandatory 
        DESCRIPTION   "Used to indicate the number of entries in the 
                      rcIpPolicyNetListTable." 
        ::= { rcIpPolicy 15 } 
  
rcIpPolicyNetListTable OBJECT-TYPE 
        SYNTAX        SEQUENCE OF RcIpPolicyNetListEntry 
        ACCESS        not-accessible 
        STATUS        mandatory 
        DESCRIPTION   "A table used to group rcIpPolicyAddrEntry(s)  
                      into a list." 
        ::= { rcIpPolicy 16 } 
 
rcIpPolicyNetListEntry OBJECT-TYPE 
        SYNTAX        RcIpPolicyNetListEntry 
        ACCESS        not-accessible 
        STATUS        mandatory 
        DESCRIPTION   "Route entry attributes." 
        INDEX         { rcIpPolicyNetListId } 
        ::= { rcIpPolicyNetListTable 1 } 
  
RcIpPolicyNetListEntry ::= SEQUENCE { 
                  rcIpPolicyNetListId INTEGER (1..1000), 
                  rcIpPolicyNetListName DisplayString (SIZE(0..15)), 
                  rcIpPolicyNetListIdListSize INTEGER (0..128), 
                  rcIpPolicyNetListIdList OCTET STRING (SIZE(256)), 
                  rcIpPolicyNetListPolicyIdListSize INTEGER (0..128), 
                  rcIpPolicyNetListPolicyIdList OCTET STRING (SIZE(256)), 
                  rcIpPolicyNetListRowStatus RowStatus 
                  } 
 
rcIpPolicyNetListId OBJECT-TYPE 
        SYNTAX        INTEGER (1..1000) 
        ACCESS        read-only 
        STATUS        mandatory 
        DESCRIPTION   "A value that uniquely identifies this list of  
                       rcIpPolicyNetListEntry." 
        ::= { rcIpPolicyNetListEntry 1 } 
  
rcIpPolicyNetListName OBJECT-TYPE 
        SYNTAX        DisplayString (SIZE (0..15)) 
        ACCESS        read-write 
        STATUS        mandatory 
        DESCRIPTION   "An administratively-assigned name for this list." 
        ::= { rcIpPolicyNetListEntry 3 } 
  
rcIpPolicyNetListIdListSize OBJECT-TYPE 
        SYNTAX        INTEGER (0..128) 
        ACCESS        read-only 
        STATUS        mandatory 
        DESCRIPTION   "Used to indicate the number of rcIpPolicyNetEntry  
                      id(s) in the rcIpPolicyNetListIdList variable." 
        ::= { rcIpPolicyNetListEntry 4 } 
  
rcIpPolicyNetListIdList OBJECT-TYPE 
        SYNTAX        OCTET STRING (SIZE(256)) 
        ACCESS        read-write 
        STATUS        mandatory 
        DESCRIPTION   "Used to indicate zero or more NetListId  that 
                      are associated to this list.  Each NetList identifier 
                      is stored as two bytes in this array starting from 
                      offset zero.  Any unused bytes should be set to zero." 
        ::= { rcIpPolicyNetListEntry 5 } 
 
rcIpPolicyNetListPolicyIdListSize OBJECT-TYPE 
        SYNTAX        INTEGER (0..128) 
        ACCESS        read-only 
        STATUS        mandatory 
        DESCRIPTION   "Used to indicate the number of policy id(s) in the  
                      Policy Id list. That are referring to this list." 
        ::= { rcIpPolicyNetListEntry 6 } 
 
rcIpPolicyNetListPolicyIdList OBJECT-TYPE 
        SYNTAX        OCTET STRING (SIZE(256)) 
        ACCESS        read-only 
        STATUS        mandatory 
        DESCRIPTION   "Used to indicate zero or more policies  that 
                      are referring to this entry.  Each policy identifier 
                      is stored as two bytes in this array starting from 
                      offset zero.  Any unused bytes should be set to zero." 
        ::= { rcIpPolicyNetListEntry 7 } 
 
rcIpPolicyNetListRowStatus OBJECT-TYPE 
        SYNTAX          RowStatus 
        ACCESS          read-write 
        STATUS          mandatory 
        DESCRIPTION     "Row status of this entry." 
        ::= { rcIpPolicyNetListEntry 8 } 
 
  
-- DVMRP Group Extension 
  
rcIpDvmrp OBJECT IDENTIFIER ::= { rcIp 12 } 
  
rcIpDvmrpEnable OBJECT-TYPE 
        SYNTAX        TruthValue 
        ACCESS        read-write 
        STATUS        mandatory 
        DESCRIPTION   "The enabled status of IP Multicast Dvmrp routing 
                      on this router." 
        ::= { rcIpDvmrp 1 } 
 
-- rcIpConfDvmrpTable 
  
rcIpConfDvmrpTable OBJECT-TYPE 
        SYNTAX        SEQUENCE OF RcIpConfDvmrpTableEntry 
        ACCESS        not-accessible 
        STATUS        mandatory 
        DESCRIPTION   "Dvmrp Interface extension table.  This table 
                      augments the standard dvmrpInterfaceTable defined 
                      in <draft-thaler-dvmrp-mib-09.txt>." 
        ::= { rcIpDvmrp 10 } 
  
rcIpConfDvmrpTableEntry OBJECT-TYPE 
        SYNTAX        RcIpConfDvmrpTableEntry 
        ACCESS        not-accessible 
        STATUS        mandatory 
        DESCRIPTION   "Entry containing Proprietary DVMRP interface 
                      information.  An entry is automatically created 
                      in this table when an ip address is configured on 
                      an interface." 
        INDEX         { rcIpConfDvmrpTableIfIndex } 
        ::= { rcIpConfDvmrpTable 1 } 
  
RcIpConfDvmrpTableEntry ::= 
        SEQUENCE { 
                rcIpConfDvmrpTableIfIndex InterfaceIndex, 
                rcIpConfDvmrpTableEnable TruthValue, 
                rcIpConfDvmrpTableMetric INTEGER 
        } 
  
rcIpConfDvmrpTableIfIndex OBJECT-TYPE 
        SYNTAX        InterfaceIndex 
        ACCESS        read-only 
        STATUS        mandatory 
        DESCRIPTION   "The index value which uniquely identifies the 
                      interface to which this entry is applicable. 
                      The interface identified by a particular value 
                      of this index is the same interface as 
                      identified by the same value of ifIndex." 
        ::= { rcIpConfDvmrpTableEntry 1 } 
  
rcIpConfDvmrpTableEnable OBJECT-TYPE 
        SYNTAX         TruthValue 
        ACCESS         read-write 
        STATUS         mandatory 
        DESCRIPTION 
                "The administrative status of DVMRP in the router.  The 
                value 'enabled' denotes that the DVMRP is enableed on 
                the interface; 'disabled' disables it on the interface." 
        ::= { rcIpConfDvmrpTableEntry 2 } 
 
rcIpConfDvmrpTableMetric OBJECT-TYPE 
        SYNTAX         INTEGER (1..31) 
        ACCESS         read-write 
        STATUS         mandatory 
        DESCRIPTION    "Dvmrp cost" 
        ::= { rcIpConfDvmrpTableEntry 3 } 
 
 
-- Ip UDP Protocol Table 
  
rcIpUdp OBJECT IDENTIFIER ::= { rcIp 13 } 
 
rcIpUdpProtocolTableSize OBJECT-TYPE 
        SYNTAX        INTEGER  
        ACCESS        read-only 
        STATUS        mandatory 
        DESCRIPTION   "Used to indicate the number of entries in the  
		      rcIpUdpProtocolTable." 
        ::= { rcIpUdp 1 } 
 
rcIpUdpProtocolTable OBJECT-TYPE  
        SYNTAX          SEQUENCE OF RcIpUdpProtocolEntry 
        ACCESS          not-accessible  
        STATUS          mandatory  
        DESCRIPTION     "list of UDP protocols. Used to determine whether to 
                         forward the UDP broadcast packet or not." 
    ::= { rcIpUdp 2 } 
 
rcIpUdpProtocolEntry OBJECT-TYPE 
        SYNTAX        	RcIpUdpProtocolEntry 
        ACCESS        	not-accessible 
        STATUS        	mandatory 
        DESCRIPTION   	"Used to include a particular UDP port in the table.   
		      	An entry in this table indicates that the box might do  
		      	forwarding of UDP broadcast packets if there is a  
                        matching entry for this packet in the  
                        rcIpUdpPortFwdTable." 
        INDEX         	{ rcIpUdpProtocolPortNumber } 
        ::= { rcIpUdpProtocolTable 1 } 
  
RcIpUdpProtocolEntry ::= 
        SEQUENCE { 
                rcIpUdpProtocolPortNumber      INTEGER, 
                rcIpUdpProtocolName    	       DisplayString, 
                rcIpUdpProtocolRowStatus       RowStatus 
        } 
  
rcIpUdpProtocolPortNumber OBJECT-TYPE 
        SYNTAX        	INTEGER (1..255) 
        ACCESS        	read-only 
        STATUS        	mandatory 
        DESCRIPTION   	"well-known UDP Port number. Pre-assigned port 
                         number for this protocol. Port used by the 
                         server process as its contact port. It cannot  
                         be BOOTP/DHCP port#s 67, 68." 
        ::= { rcIpUdpProtocolEntry 1 } 
  
rcIpUdpProtocolName OBJECT-TYPE 
        SYNTAX          DisplayString (SIZE(1..15)) 
        ACCESS        	read-write 
        STATUS        	mandatory 
        DESCRIPTION   	"Used to indicate the name of the protocol  
		      	that is running on top of UDP protocol.  
                        cannot change the name once created. This  
                        should be set while creating the entry."   
        ::= { rcIpUdpProtocolEntry 2 } 
  
rcIpUdpProtocolRowStatus OBJECT-TYPE 
        SYNTAX        	RowStatus 
        ACCESS        	read-write 
        STATUS        	mandatory 
        DESCRIPTION   	"Rowstatus of this entry." 
        ::= { rcIpUdpProtocolEntry 3 } 
 
 
-- Ip Udp Port Forward Table 
 
rcIpUdpPortFwdTableSize OBJECT-TYPE 
        SYNTAX        INTEGER 
        ACCESS        read-only 
        STATUS        mandatory 
        DESCRIPTION   "Used to indicate the number of entries in the 
                      rcIpUdpPortFwdTable." 
        ::= { rcIpUdp 3 } 
  
rcIpUdpPortFwdTable OBJECT-TYPE  
        SYNTAX	      	SEQUENCE OF RcIpUdpPortFwdEntry 
        ACCESS        	not-accessible  
        STATUS        	mandatory  
        DESCRIPTION   	"Udp forward entry table." 
    ::= { rcIpUdp 4 } 
 
rcIpUdpPortFwdEntry OBJECT-TYPE 
        SYNTAX        	RcIpUdpPortFwdEntry 
        ACCESS        	not-accessible 
        STATUS        	mandatory 
        DESCRIPTION   	"An entry is configured to specify forwarding policy 
                         parameters." 
        INDEX         	{ rcIpUdpPortFwdDestPort, 
                          rcIpUdpPortFwdDestAddr} 
        ::= { rcIpUdpPortFwdTable 1 } 
  
RcIpUdpPortFwdEntry ::= 
        SEQUENCE { 
                rcIpUdpPortFwdDestPort      INTEGER, 
                rcIpUdpPortFwdDestAddr      IpAddress, 
                rcIpUdpPortFwdId            INTEGER, 
                rcIpUdpPortFwdFwdListIdListSize INTEGER (0..32), 
                rcIpUdpPortFwdFwdListIdList IdList(SIZE(16)), 
                rcIpUdpPortFwdNumFwdPackets Counter, 
                rcIpUdpPortFwdNumDropPacketsTtlExpired Counter, 
                rcIpUdpPortFwdNumDropPacketsDestUnreach Counter, 
                rcIpUdpPortFwdRowStatus     RowStatus 
        } 
  
rcIpUdpPortFwdDestPort OBJECT-TYPE 
        SYNTAX        	INTEGER(1..4096) 
        ACCESS        	read-only 
        STATUS        	mandatory 
        DESCRIPTION   	"The well-known port number defined for UDP/TCP  
                        depending on the value of IpProtoType field in this 
                        entry. This port number has to be defined in the 
                        rcIpUdpProtoTable. In order to select this policy the  
                        destination port number has to match the DestPort  
                        value." 
        ::= { rcIpUdpPortFwdEntry 1 } 
  
rcIpUdpPortFwdDestAddr OBJECT-TYPE 
        SYNTAX        	IpAddress 
        ACCESS        	read-only 
        STATUS        	mandatory 
        DESCRIPTION   	"Destination IP address. The IP addres to which the  
                        UDP/TCP broadcast should be forwarded. This IP address  
                        can be any IP server address or subnet broadcast  
                        address.  If the IP address is one of the routable  
                        interface's address on the router, the frame will be  
                        rebroadcast out as a limited broadcast. If the Ip  
                        address is that of a server then the received  
                        broadcast packet will be sent as a unicast packet to  
                        this address." 
        ::= { rcIpUdpPortFwdEntry 2 } 
 
rcIpUdpPortFwdId OBJECT-TYPE 
        SYNTAX        INTEGER 
        ACCESS        read-only 
        STATUS        mandatory 
        DESCRIPTION   "Identifier of this entry. Used internally to identify 
                      this entry." 
        ::= { rcIpUdpPortFwdEntry 3 } 
 
rcIpUdpPortFwdFwdListIdListSize OBJECT-TYPE 
        SYNTAX        INTEGER (0..32) 
        ACCESS        read-only 
        STATUS        mandatory 
        DESCRIPTION   "Used to indicate the number of id(s) in the 
                      rcIpUdpPortFwdListId variable." 
        ::= { rcIpUdpPortFwdEntry 4 } 
 
rcIpUdpPortFwdFwdListIdList OBJECT-TYPE 
        SYNTAX        IdList(SIZE(16)) 
        ACCESS        read-only 
        STATUS        mandatory 
        DESCRIPTION   "Used to indicate zero or more rcIpUdpPortFwdListEntry(s) 
                      that are referring to this entry.  Each list-id identifier 
                      is stored as two bytes in this array starting from 
                      offset zero.  Any unused bytes should be set to zero." 
        ::= { rcIpUdpPortFwdEntry 5 } 
  
rcIpUdpPortFwdNumFwdPackets OBJECT-TYPE 
        SYNTAX        	Counter 
        ACCESS        	read-only 
        STATUS        	mandatory 
        DESCRIPTION   	"The total number of UDP/TCP broadcast packets forwarded 
                        using this policy." 
        ::= { rcIpUdpPortFwdEntry 6 } 
 
rcIpUdpPortFwdNumDropPacketsTtlExpired OBJECT-TYPE 
        SYNTAX        	Counter 
        ACCESS        	read-only 
        STATUS        	mandatory 
        DESCRIPTION   	"The total number of UDP/TCP broadcast packets dropped 
                        because the TTL has expired." 
        ::= { rcIpUdpPortFwdEntry 7 } 
 
rcIpUdpPortFwdNumDropPacketsDestUnreach OBJECT-TYPE 
        SYNTAX        	Counter 
        ACCESS        	read-only 
        STATUS        	mandatory 
        DESCRIPTION   	"The total number of UDP/TCP broadcast packets dropped 
                        because the rcIpUdpPortFwdDestAddr specified in 
                        this policy was unreachable." 
        ::= { rcIpUdpPortFwdEntry 8 } 
 
rcIpUdpPortFwdRowStatus OBJECT-TYPE 
        SYNTAX        	RowStatus 
        ACCESS        	read-write 
        STATUS        	mandatory 
        DESCRIPTION   	"Row status of this entry." 
        ::= { rcIpUdpPortFwdEntry 9 } 
 
-- Udp Port Fwd List Table  
 
rcIpUdpPortFwdListTableSize OBJECT-TYPE 
        SYNTAX        INTEGER 
        ACCESS        read-only 
        STATUS        mandatory 
        DESCRIPTION   "Used to indicate the number of entries in the 
                      rcIpUdpPortFwdListTable." 
        ::= { rcIpUdp 5 } 
 
rcIpUdpPortFwdListTable OBJECT-TYPE 
        SYNTAX        SEQUENCE OF RcIpUdpPortFwdListEntry 
        ACCESS        not-accessible 
        STATUS        mandatory 
        DESCRIPTION   "A table used to group rcIpUdpPortFwdEntry(s)  
                      into a list." 
        ::= { rcIpUdp 6 } 
 
rcIpUdpPortFwdListEntry OBJECT-TYPE 
        SYNTAX        RcIpUdpPortFwdListEntry 
        ACCESS        not-accessible 
        STATUS        mandatory 
        DESCRIPTION   "Route entry attributes." 
        INDEX         { rcIpUdpPortFwdListId } 
        ::= { rcIpUdpPortFwdListTable 1 } 
  
RcIpUdpPortFwdListEntry ::= SEQUENCE { 
                  rcIpUdpPortFwdListId INTEGER (1..1000), 
                  rcIpUdpPortFwdListName DisplayString (SIZE(0..15)), 
                  rcIpUdpPortFwdListFwdIdListSize INTEGER (0..16), 
                  rcIpUdpPortFwdListFwdIdList OCTET STRING (SIZE(32)), 
                  rcIpUdpPortFwdListRowStatus RowStatus 
                  } 
 
rcIpUdpPortFwdListId OBJECT-TYPE 
        SYNTAX        INTEGER (1..1000) 
        ACCESS        read-only 
        STATUS        mandatory 
        DESCRIPTION   "A value that uniquely identifies this list of  
                       rcIpUdpPortFwdListEntry." 
        ::= { rcIpUdpPortFwdListEntry 1 } 
  
rcIpUdpPortFwdListName OBJECT-TYPE 
        SYNTAX        DisplayString (SIZE (0..15)) 
        ACCESS        read-write 
        STATUS        mandatory 
        DESCRIPTION   "An administratively-assigned name for this list." 
        ::= { rcIpUdpPortFwdListEntry 3 } 
  
rcIpUdpPortFwdListFwdIdListSize OBJECT-TYPE 
        SYNTAX        INTEGER (0..16) 
        ACCESS        read-only 
        STATUS        mandatory 
        DESCRIPTION   "Used to indicate the number of rcIpUdpPortFwdNetEntry  
                      id(s) in the rcIpUdpPortFwdListIdList variable." 
        ::= { rcIpUdpPortFwdListEntry 4 } 
  
rcIpUdpPortFwdListFwdIdList OBJECT-TYPE 
        SYNTAX        OCTET STRING (SIZE(32)) 
        ACCESS        read-write 
        STATUS        mandatory 
        DESCRIPTION   "Used to indicate zero or more UdpPortFwd entries  
                      that are associated to this list.  Each entry identifier 
                      is stored as two bytes in this array starting from 
                      offset zero.  Any unused bytes should be set to zero." 
        ::= { rcIpUdpPortFwdListEntry 5 } 
 
rcIpUdpPortFwdListRowStatus OBJECT-TYPE 
        SYNTAX          RowStatus 
        ACCESS          read-write 
        STATUS          mandatory 
        DESCRIPTION     "Row status of this entry." 
        ::= { rcIpUdpPortFwdListEntry 6 } 
  
 
-- Ip Config Broadcast Forwarding Table 
 
rcIpUdpConfBroadcastIntfTableSize OBJECT-TYPE 
        SYNTAX        INTEGER 
        ACCESS        read-only 
        STATUS        mandatory 
        DESCRIPTION   "Used to indicate the number of entries in the 
                      rcIpUdpBroadcastIntfTable." 
        ::= { rcIpUdp 7 } 
  
rcIpUdpConfBroadcastIntfTable OBJECT-TYPE  
        SYNTAX          SEQUENCE OF RcIpUdpConfBroadcastIntfEntry 
        ACCESS          not-accessible  
        STATUS          mandatory  
        DESCRIPTION     "IP broadcast forward configuration table" 
    ::= { rcIpUdp 8 } 
 
rcIpUdpConfBroadcastIntfEntry OBJECT-TYPE 
        SYNTAX        	RcIpUdpConfBroadcastIntfEntry 
        ACCESS        	not-accessible 
        STATUS        	mandatory 
        DESCRIPTION   	"Used to configure UDP broadcast forward on a  
                        particular interface." 
        INDEX         	{ rcIpUdpConfBroadcastIntfLocalIfAddr } 
        ::= { rcIpUdpConfBroadcastIntfTable 1 } 
  
RcIpUdpConfBroadcastIntfEntry ::= 
        SEQUENCE { 
                rcIpUdpConfBroadcastIntfLocalIfAddr   	      IpAddress, 
                rcIpUdpConfBroadcastIntfUdpPortFwdListId          INTEGER (0..100), 
                rcIpUdpConfBroadcastIntfMaxTtl    	              INTEGER (1..16), 
                rcIpUdpConfBroadcastIntfNumRxPkts                 Counter, 
                rcIpUdpConfBroadcastIntfNumFwdPkts                Counter, 
                rcIpUdpConfBroadcastIntfNumDropPktsMaxTtlExpired  Counter, 
                rcIpUdpConfBroadcastIntfNumDropPktsDestUnreach    Counter, 
                rcIpUdpConfBroadcastIntfNumDropPktsUnknownPort    Counter, 
                rcIpUdpConfBroadcastIntfRowStatus 	              RowStatus 
  
        } 
  
rcIpUdpConfBroadcastIntfLocalIfAddr OBJECT-TYPE 
        SYNTAX        	IpAddress  
        ACCESS        	read-only 
        STATUS        	mandatory 
        DESCRIPTION   	"The ip address of the local interface that is 
           	        partipating in the forwarding UDP broadcast packets." 
        ::= { rcIpUdpConfBroadcastIntfEntry 1 } 
  
rcIpUdpConfBroadcastIntfUdpPortFwdListId OBJECT-TYPE 
        SYNTAX        INTEGER (0..100) 
        ACCESS        read-write 
        STATUS        mandatory 
        DESCRIPTION   "Used to indicate the number UDP ports that this  
                      interface is configured to forward. 
 
                      A value of '0' indicates that this interface will not 
                      forward any UDP broadcast packets. This is a required 
                      field to create an entry." 
        ::= { rcIpUdpConfBroadcastIntfEntry 2 } 
 
rcIpUdpConfBroadcastIntfMaxTtl OBJECT-TYPE 
        SYNTAX        	INTEGER (1..16) 
        ACCESS        	read-write 
        STATUS        	mandatory 
        DESCRIPTION   	"Used to indicate the maximum number of hops an  
		      	IP broadcast packet can take from the source  
                        device to the destination device." 
 	DEFVAL        	{ 4 } 
        ::= { rcIpUdpConfBroadcastIntfEntry 3 } 
  
rcIpUdpConfBroadcastIntfNumRxPkts OBJECT-TYPE 
        SYNTAX        	Counter 
        ACCESS        	read-only 
        STATUS        	mandatory 
        DESCRIPTION   	"The total number of UDP/TCP broadcast packets  
                        received by this local interface." 
        ::= { rcIpUdpConfBroadcastIntfEntry 4 } 
 
rcIpUdpConfBroadcastIntfNumFwdPkts OBJECT-TYPE 
        SYNTAX        	Counter 
        ACCESS        	read-only 
        STATUS        	mandatory 
        DESCRIPTION   	"The total number of UDP/TCP broadcast packets  
                        forwarded." 
        ::= { rcIpUdpConfBroadcastIntfEntry 5 } 
 
rcIpUdpConfBroadcastIntfNumDropPktsMaxTtlExpired OBJECT-TYPE 
        SYNTAX        	Counter 
        ACCESS        	read-only 
        STATUS        	mandatory 
        DESCRIPTION   	"The total number of UDP/TCP broadcast packets  
                        dropped because the TTL has expired." 
        ::= { rcIpUdpConfBroadcastIntfEntry 6 } 
 
rcIpUdpConfBroadcastIntfNumDropPktsDestUnreach OBJECT-TYPE 
        SYNTAX        	Counter 
        ACCESS        	read-only 
        STATUS        	mandatory 
        DESCRIPTION   	"The total number of UDP broadcast packets  
                        dropped because the destination was unreachable." 
        ::= { rcIpUdpConfBroadcastIntfEntry 7 } 
 
rcIpUdpConfBroadcastIntfNumDropPktsUnknownPort OBJECT-TYPE 
        SYNTAX        	Counter 
        ACCESS        	read-only 
        STATUS        	mandatory 
        DESCRIPTION   	"The total number of UDP/TCP broadcast packets  
                        dropped because the destination port/protocol  
                        specified has no matching forwarding policy."  
        ::= { rcIpUdpConfBroadcastIntfEntry 8 } 
 
rcIpUdpConfBroadcastIntfRowStatus OBJECT-TYPE 
        SYNTAX        	RowStatus 
        ACCESS        	read-write 
        STATUS        	mandatory 
        DESCRIPTION   	"Entry row status." 
        ::= { rcIpUdpConfBroadcastIntfEntry 9 } 
 
-- ARP Group 
 
rcArpExtLifeTime OBJECT-TYPE 
        SYNTAX        INTEGER 
        ACCESS        read-write 
        STATUS        mandatory 
        DESCRIPTION   "The lifetime in minutues of an ARP entry within the  
                      system." 
        ::= { rcArp 1 } 
 
rcArpExtTable OBJECT-TYPE 
        SYNTAX        SEQUENCE OF RcArpExtEntry 
        ACCESS        not-accessible 
        STATUS        mandatory 
        DESCRIPTION   "ARP extension table.  This table augments the 
		      standard ipNetToMediaTable defined in RFC1213." 
        ::= { rcArp 2 } 
 
rcArpExtEntry OBJECT-TYPE 
        SYNTAX        RcArpExtEntry 
        ACCESS        not-accessible 
        STATUS        mandatory 
        DESCRIPTION   "Entry containing Proprietary ARP information.   
                      An entry is automatically created in this table  
                      when an ip address is configured on an interface."  
        INDEX         { rcArpExtEntIfIndex } 
        ::= { rcArpExtTable 1 } 
 
RcArpExtEntry ::= 
        SEQUENCE { 
                rcArpExtEntIfIndex InterfaceIndex, 
                rcArpExtEntDoProxy INTEGER, 
                rcArpExtEntDoResp INTEGER 
        } 
 
rcArpExtEntIfIndex OBJECT-TYPE 
        SYNTAX        InterfaceIndex 
        ACCESS        read-only 
        STATUS        mandatory 
        DESCRIPTION   "The index value which uniquely identifies the 
                      interface to which this entry is applicable. 
                      The interface identified by a particular value 
                      of this index is the same interface as  
                      identified by the same value of ifIndex." 
        ::= { rcArpExtEntry 1 } 
  
rcArpExtEntDoProxy OBJECT-TYPE 
        SYNTAX        INTEGER { 
		         disable(1), 
			 enable(2) 
		      } 
        ACCESS        read-write 
        STATUS        mandatory 
        DESCRIPTION   "Enable or disable ARP proxy responses on the 
		      specified interface." 
	DEFVAL        { disable } 
        ::= { rcArpExtEntry 2 } 
  
rcArpExtEntDoResp OBJECT-TYPE 
        SYNTAX        INTEGER { 
			 disable(1), 
			 enable(2) 
		      } 
        ACCESS        read-write 
        STATUS        mandatory 
        DESCRIPTION   "Enable or disable the sending of ARP responses 
		      on the specified interface." 
	DEFVAL        { enable } 
        ::= { rcArpExtEntry 3 } 
 
 
-- RIP Group 
 
rcRipExtOperation OBJECT-TYPE 
        SYNTAX        INTEGER	{ 
                         disable(1), 
                         enable(2) 
	 	      } 
        ACCESS        read-write 
        STATUS        mandatory 
        DESCRIPTION   "Enable or disable the operation of RIP on all 
		      Interfaces." 
        ::= { rcRip 1 } 
 
rcRipExtUpdateTime OBJECT-TYPE 
        SYNTAX        INTEGER 
        ACCESS        read-write 
        STATUS        mandatory 
        DESCRIPTION   "The time between transmission of RIP updates 
		      on all interfaces." 
        ::= { rcRip 2 } 
 
rcRipExtTable OBJECT-TYPE 
        SYNTAX        SEQUENCE OF RcRipExtEntry 
        ACCESS        not-accessible 
        STATUS        mandatory 
        DESCRIPTION   "RIP extension table.  This table augments the 
		      standard IfConfTable table in RFC1389." 
        ::= { rcRip 3 } 
 
rcRipExtEntry OBJECT-TYPE 
        SYNTAX        RcRipExtEntry 
        ACCESS        not-accessible 
        STATUS        mandatory 
        DESCRIPTION   "Entry containing Proprietary RIP information.   
	  	      An entry is automatically created in this table  
                      when an ip address is configured on an interface." 
        INDEX         { rcRipExtEntIfIndex } 
        ::= { rcRipExtTable 1 } 
 
RcRipExtEntry ::= 
        SEQUENCE { 
                rcRipExtEntIfIndex InterfaceIndex, 
                rcRipExtEntTalk INTEGER, 
                rcRipExtEntListen INTEGER, 
                rcRipExtEntPoison INTEGER 
        } 
 
rcRipExtEntIfIndex OBJECT-TYPE 
        SYNTAX        InterfaceIndex 
        ACCESS        read-only 
        STATUS        mandatory 
        DESCRIPTION   "The index value which uniquely identifies the 
                      interface to which this entry is applicable. 
                      The interface identified by a particular value 
                      of this index is the same interface as  
                      identified by the same value of ifIndex." 
        ::= { rcRipExtEntry 1 } 
  
rcRipExtEntTalk OBJECT-TYPE 
        SYNTAX       INTEGER { 
                        disable(1), 
                        enable(2) 
		      }	 
        ACCESS        read-write 
        STATUS        mandatory 
        DESCRIPTION   "Enable or disable RIP transmission on the 
		      specified interface." 
	DEFVAL        { enable } 
        ::= { rcRipExtEntry 2 } 
  
rcRipExtEntListen OBJECT-TYPE 
        SYNTAX        INTEGER { 
                         disable(1), 
                         enable(2) 
		      } 
        ACCESS        read-write 
        STATUS        mandatory 
        DESCRIPTION   "Enable or disable RIP reception on the specified 
		      interface." 
	DEFVAL        { enable } 
        ::= { rcRipExtEntry 3 } 
 
rcRipExtEntPoison OBJECT-TYPE 
        SYNTAX        INTEGER { 
                         disable(1), 
                         enable(2) 
                      }  
        ACCESS        read-write 
        STATUS        mandatory 
        DESCRIPTION   "Enable or disable operation of poison reverse 
		      on the specified interface.  If poison is 
		      disabled, split-horizon operation is enabled." 
	DEFVAL        { disable } 
        ::= { rcRipExtEntry 4 } 
 
 
-- Test Group 
 
rcTestExtTable OBJECT-TYPE 
        SYNTAX        SEQUENCE OF RcTestEntry 
        ACCESS        not-accessible 
        STATUS        mandatory 
        DESCRIPTION   "Test extension table.  This table augments the 
                      standard ifTestTable table in RFC1573." 
        ::= { rcTest 1 } 
  
rcTestEntry OBJECT-TYPE 
        SYNTAX        RcTestEntry 
        ACCESS        not-accessible 
        STATUS        mandatory     
        DESCRIPTION   "Proprietary test variables." 
        INDEX         { rcTestExtIfIndex } 
        ::= { rcTestExtTable 1 } 
  
RcTestEntry ::= 
        SEQUENCE { 
                rcTestExtIfIndex InterfaceIndex, 
                rcTestExtPassCount INTEGER,   
                rcTestExtFailCount INTEGER 
        } 
  
rcTestExtIfIndex OBJECT-TYPE 
        SYNTAX        InterfaceIndex 
        ACCESS        read-only 
        STATUS        mandatory 
        DESCRIPTION   "The index value which uniquely identifies the 
                      interface to which this entry is applicable. 
                      The interface identified by a particular value 
                      of this index is the same interface as 
                      identified by the same value of ifIndex." 
        ::= { rcTestEntry 1 } 
 
rcTestExtPassCount OBJECT-TYPE 
	SYNTAX	      INTEGER 
	ACCESS	      read-only 
	STATUS	      mandatory 
	DESCRIPTION   "The number of iterations of the test case that 
		      completed successfully." 
	::= { rcTestEntry 2} 
 
rcTestExtFailCount OBJECT-TYPE 
        SYNTAX        INTEGER 
        ACCESS        read-only 
        STATUS        mandatory 
        DESCRIPTION   "The number of iterations of the test case that 
                      failed." 
        ::= { rcTestEntry 3} 
 
 
rcTestTypes		OBJECT IDENTIFIER	::= { rcTest 2} 
rcTestTypesFabric	OBJECT IDENTIFIER	::= { rcTestTypes 1 } 
rcTestTypesArTable	OBJECT IDENTIFIER	::= { rcTestTypes 2 } 
rcTestTypesExtLoopBack	OBJECT IDENTIFIER	::= { rcTestTypes 3 } 
 
 
rcTestCodes		OBJECT IDENTIFIER	::= { rcTest 3 } 
rcTestCodesNoReceive	OBJECT IDENTIFIER	::= { rcTestCodes 1 } 
rcTestCodesBadSeq	OBJECT IDENTIFIER	::= { rcTestCodes 2 } 
rcTestCodesBadLen	OBJECT IDENTIFIER	::= { rcTestCodes 3 } 
rcTestCodesBadData	OBJECT IDENTIFIER	::= { rcTestCodes 4 } 
 
 
-- Statistics 
 
rcStatTable OBJECT-TYPE 
        SYNTAX        SEQUENCE OF RcStatEntry 
        ACCESS        not-accessible 
        STATUS        mandatory 
        DESCRIPTION   "A table used to store port statistics." 
        ::= { rcStat 1 } 
  
rcStatEntry OBJECT-TYPE 
        SYNTAX        RcStatEntry 
        ACCESS        not-accessible 
        STATUS        mandatory 
        DESCRIPTION   "interface counters" 
        INDEX         { rcStatPortIndex } 
        ::= { rcStatTable 1 } 
  
RcStatEntry ::= SEQUENCE { 
                rcStatPortIndex            	InterfaceIndex, 
                rcStatFrameTooShorts       	Counter, 
 		rcStatBridgeInUnicastFrames	Counter, 
 		rcStatBridgeInMulticastFrames	Counter, 
 		rcStatBridgeInBroadcastFrames	Counter, 
 		rcStatBridgeInDiscards		Counter, 
 		rcStatBridgeOutUnicastFrames	Counter, 
 		rcStatBridgeOutMulticastFrames	Counter, 
 		rcStatBridgeOutBroadcastFrames	Counter, 
 		rcStatRouteInUnicastFrames	Counter, 
 		rcStatRouteInMulticastFrames	Counter, 
 		rcStatRouteInDiscards		Counter, 
 		rcStatRouteOutUnicastFrames	Counter, 
 		rcStatRouteOutMulticastFrames 	Counter, 
		rcStatStgForwardTransitions     Counter, 
		rcStatStgInConfigBpdus          Counter, 
		rcStatStgInTcnBpdus             Counter, 
		rcStatStgInBadBpdus             Counter, 
		rcStatStgOutConfigBpdus         Counter, 
		rcStatStgOutTcnBpdus            Counter 
        } 
  
rcStatPortIndex OBJECT-TYPE 
        SYNTAX        InterfaceIndex 
        ACCESS        read-only 
        STATUS        mandatory 
        DESCRIPTION   "An index value that uniquely identifies a port. 
                      This value is similar to ifIndex in MIB2." 
        ::= { rcStatEntry 1 } 
  
rcStatFrameTooShorts OBJECT-TYPE 
        SYNTAX        Counter 
        ACCESS        read-only 
        STATUS        mandatory 
        DESCRIPTION   "The total number of frames that are too short  
                      that were encountered on this interface." 
        ::= { rcStatEntry 2 } 
 
rcStatBridgeInUnicastFrames OBJECT-TYPE 
        SYNTAX        Counter 
        ACCESS        read-only 
        STATUS        mandatory 
        DESCRIPTION   "The total number of incoming unicast frames that  
		      were bridged." 
        ::= { rcStatEntry 3 } 
 
rcStatBridgeInMulticastFrames OBJECT-TYPE  
        SYNTAX        Counter  
        ACCESS        read-only 
        STATUS        mandatory  
        DESCRIPTION   "The total number of incoming multicast frames that  
                      were bridged." 
        ::= { rcStatEntry 4 } 
 
rcStatBridgeInBroadcastFrames OBJECT-TYPE  
        SYNTAX        Counter  
        ACCESS        read-only 
        STATUS        mandatory  
        DESCRIPTION   "The total number of incoming broadcast frames that  
                      were bridged." 
        ::= { rcStatEntry 5 } 
 
rcStatBridgeInDiscards OBJECT-TYPE  
        SYNTAX        Counter  
        ACCESS        read-only 
        STATUS        mandatory  
        DESCRIPTION   "The total number of frames that were discarded by 
		      the bridging entity." 
        ::= { rcStatEntry 6 } 
 
rcStatBridgeOutUnicastFrames OBJECT-TYPE  
        SYNTAX        Counter  
        ACCESS        read-only 
        STATUS        mandatory  
        DESCRIPTION   "The total number of outgoing unicast frames that  
                      were bridged." 
        ::= { rcStatEntry 7 } 
 
rcStatBridgeOutMulticastFrames OBJECT-TYPE  
        SYNTAX        Counter  
        ACCESS        read-only 
        STATUS        mandatory  
        DESCRIPTION   "The total number of outgoing multicast frames that  
                      were bridged." 
        ::= { rcStatEntry 8 } 
 
rcStatBridgeOutBroadcastFrames OBJECT-TYPE  
        SYNTAX        Counter  
        ACCESS        read-only 
        STATUS        mandatory  
        DESCRIPTION   "The total number of outgoing broadcast frames that  
                      were bridged." 
        ::= { rcStatEntry 9 } 
 
rcStatRouteInUnicastFrames OBJECT-TYPE  
        SYNTAX        Counter  
        ACCESS        read-only 
        STATUS        mandatory  
        DESCRIPTION   "The total number of incoming unicast frames that 
                      were routed." 
        ::= { rcStatEntry 10 } 
 
rcStatRouteInMulticastFrames OBJECT-TYPE  
        SYNTAX        Counter  
        ACCESS        read-only 
        STATUS        mandatory  
        DESCRIPTION   "The total number of incoming multicast frames that 
                      were routed." 
        ::= { rcStatEntry 11 } 
 
rcStatRouteInDiscards OBJECT-TYPE  
        SYNTAX        Counter  
        ACCESS        read-only 
        STATUS        mandatory  
        DESCRIPTION   "The total number of frames that were discarded by 
		      the routing entity." 
        ::= { rcStatEntry 12 } 
 
rcStatRouteOutUnicastFrames OBJECT-TYPE  
        SYNTAX        Counter  
        ACCESS        read-only 
        STATUS        mandatory  
        DESCRIPTION   "The total number of outgoing unicast frames that 
                      were routed." 
        ::= { rcStatEntry 13 } 
 
rcStatRouteOutMulticastFrames OBJECT-TYPE  
        SYNTAX        Counter  
        ACCESS        read-only 
        STATUS        mandatory  
        DESCRIPTION   "The total number of outgoing multicast frames that 
                      were routed." 
        ::= { rcStatEntry 14 } 
 
rcStatStgForwardTransitions OBJECT-TYPE  
        SYNTAX        Counter  
        ACCESS        read-only 
        STATUS        mandatory  
        DESCRIPTION   "" 
        ::= { rcStatEntry 15 } 
 
rcStatStgInConfigBpdus OBJECT-TYPE  
        SYNTAX        Counter  
        ACCESS        read-only 
        STATUS        mandatory  
        DESCRIPTION   "" 
        ::= { rcStatEntry 16 } 
 
rcStatStgInTcnBpdus OBJECT-TYPE  
        SYNTAX        Counter  
        ACCESS        read-only 
        STATUS        mandatory  
        DESCRIPTION   "" 
        ::= { rcStatEntry 17 } 
 
rcStatStgInBadBpdus OBJECT-TYPE  
        SYNTAX        Counter  
        ACCESS        read-only 
        STATUS        mandatory  
        DESCRIPTION   "" 
        ::= { rcStatEntry 18 } 
 
rcStatStgOutConfigBpdus OBJECT-TYPE  
        SYNTAX        Counter  
        ACCESS        read-only 
        STATUS        mandatory  
        DESCRIPTION   "" 
        ::= { rcStatEntry 19 } 
 
rcStatStgOutTcnBpdus OBJECT-TYPE  
        SYNTAX        Counter  
        ACCESS        read-only 
        STATUS        mandatory  
        DESCRIPTION   "" 
        ::= { rcStatEntry 20 } 
 
rcStatGigTable OBJECT-TYPE 
        SYNTAX        SEQUENCE OF RcStatGigEntry 
        ACCESS        not-accessible 
        STATUS        mandatory 
        DESCRIPTION   "A table used to store Gigport error statistics." 
        ::= { rcStat 2 }  
  
rcStatGigEntry OBJECT-TYPE   
        SYNTAX        RcStatGigEntry 
        ACCESS        not-accessible 
        STATUS        mandatory 
        DESCRIPTION   "Gigabit interface error counters" 
        INDEX         { rcStatGigPortIndex } 
        ::= { rcStatGigTable 1 } 
  
RcStatGigEntry ::= SEQUENCE { 
		rcStatGigPortIndex            InterfaceIndex, 
		rcStatGigLinkFailures         Counter, 
		rcStatGigPacketErrors         Counter, 
		rcStatGigCarrierErrors        Counter, 
		rcStatGigLinkInactiveErrors   Counter, 
                rcStatGigInFlowCtrlPkts       Counter, 
                rcStatGigOutFlowCtrlPkts      Counter 
        } 
 
rcStatGigPortIndex OBJECT-TYPE 
        SYNTAX        InterfaceIndex 
        ACCESS        read-only 
        STATUS        mandatory 
        DESCRIPTION   "An index value that uniquely identifies a port. 
                      This value is similar to ifIndex in MIB2." 
        ::= { rcStatGigEntry 1 } 
 
rcStatGigLinkFailures OBJECT-TYPE 
        SYNTAX        Counter 
        ACCESS        read-only 
        STATUS        mandatory 
        DESCRIPTION   "The total number of link failures encountered on  
                      this interface." 
        ::= { rcStatGigEntry 2 } 
 
rcStatGigPacketErrors OBJECT-TYPE 
        SYNTAX        Counter 
        ACCESS        read-only 
        STATUS        mandatory 
        DESCRIPTION   "The total number of packet errors encountered on  
                      this interface." 
        ::= { rcStatGigEntry 3 } 
 
rcStatGigCarrierErrors OBJECT-TYPE 
        SYNTAX        Counter 
        ACCESS        read-only 
        STATUS        mandatory 
        DESCRIPTION   "The total number of carrier errors encountered on  
                      this interface." 
        ::= { rcStatGigEntry 4 } 
 
rcStatGigLinkInactiveErrors OBJECT-TYPE 
        SYNTAX        Counter 
        ACCESS        read-only 
        STATUS        mandatory 
        DESCRIPTION   "The total number of link inactive errors encountered  
                       on this interface." 
        ::= { rcStatGigEntry 5 } 
 
rcStatGigInFlowCtrlPkts OBJECT-TYPE 
        SYNTAX        Counter 
        ACCESS        read-only 
        STATUS        mandatory 
        DESCRIPTION   "The total number of flow control packets received 
                         by this interface." 
        ::= { rcStatGigEntry 6 } 
 
rcStatGigOutFlowCtrlPkts OBJECT-TYPE 
        SYNTAX        Counter 
        ACCESS        read-only 
        STATUS        mandatory 
        DESCRIPTION   "The total number of flow control packets transmitted  
                       by this interface." 
        ::= { rcStatGigEntry 7 } 
 
rcStatOspf   OBJECT IDENTIFIER       ::= { rcStat 3} 
  
rcStatOspfBuffersAllocated OBJECT-TYPE 
        SYNTAX        Counter 
        ACCESS        read-only 
        STATUS        mandatory 
        DESCRIPTION   "Used to indicate the number of buffers 
                      allocated for OSPF." 
        ::= { rcStatOspf 1 } 
  
rcStatOspfBuffersFreed OBJECT-TYPE 
        SYNTAX        Counter 
        ACCESS        read-only 
        STATUS        mandatory 
        DESCRIPTION   "Used to indicate the number of buffers 
                      that are freed by the OSPF." 
        ::= { rcStatOspf 2 } 
  
rcStatOspfBufferAllocFailures OBJECT-TYPE 
        SYNTAX        Counter 
        ACCESS        read-only 
        STATUS        mandatory 
        DESCRIPTION   "Used to indicate the number of times 
                      that OSPF has failed to allocate buffers." 
        ::= { rcStatOspf 3 } 
  
rcStatOspfBufferFreeFailures OBJECT-TYPE 
        SYNTAX        Counter 
        ACCESS        read-only 
        STATUS        mandatory 
        DESCRIPTION   "Used to indicate the number of times 
                      that OSPF has failed to free buffers." 
        ::= { rcStatOspf 4 } 
  
rcStatOspfTxPackets OBJECT-TYPE 
        SYNTAX        Counter 
        ACCESS        read-only 
        STATUS        mandatory 
        DESCRIPTION   "Used to indicate the number of packets 
                      transmitted by OSPF." 
        ::= { rcStatOspf 5 } 
  
  
rcStatOspfRxPackets OBJECT-TYPE 
        SYNTAX        Counter 
        ACCESS        read-only 
        STATUS        mandatory 
        DESCRIPTION   "Used to indicate the number of packets 
                      received by OSPF." 
        ::= { rcStatOspf 6 } 
  
rcStatOspfTxDropPackets OBJECT-TYPE 
        SYNTAX        Counter 
        ACCESS        read-only 
        STATUS        mandatory 
        DESCRIPTION   "Used to indicate the number of packets 
                      dropped before transmitted by OSPF." 
        ::= { rcStatOspf 7 } 
  
  
rcStatOspfRxDropPackets OBJECT-TYPE 
        SYNTAX        Counter 
        ACCESS        read-only 
        STATUS        mandatory 
        DESCRIPTION   "Used to indicate the number of packets 
                      dropped before received by OSPF." 
        ::= { rcStatOspf 8 } 
  
rcStatOspfRxBadPackets OBJECT-TYPE 
        SYNTAX        Counter 
        ACCESS        read-only 
        STATUS        mandatory 
        DESCRIPTION   "Used to indicate the number of packets 
                      received by OSPF that are bad." 
        ::= { rcStatOspf 9 } 
  
rcStatOspfSpfRuns OBJECT-TYPE 
        SYNTAX        Counter 
        ACCESS        read-only 
        STATUS        mandatory 
        DESCRIPTION   "Used to indicate the number of SPF 
                      calculatations performed by OSPF." 
        ::= { rcStatOspf 10 } 
  
rcStatOspfLastSpfRun OBJECT-TYPE 
        SYNTAX        TimeTicks 
        ACCESS        read-only 
        STATUS        mandatory 
        DESCRIPTION   "Used to indicate the time(SysUpTime) since 
                      the last spf calculated by OSPF." 
        ::= { rcStatOspf 11 } 
  
rcStatIgmp   OBJECT IDENTIFIER       ::= { rcStat 4} 
 
rcStatIgmpInMsgs OBJECT-TYPE 
        SYNTAX          Counter 
        ACCESS          read-only 
        STATUS          mandatory 
        DESCRIPTION     "Used to indicate the number of Igmp packets 
                         received by the device." 
        ::= { rcStatIgmp 1 } 
 
rcStatIgmpInErrors OBJECT-TYPE 
        SYNTAX          Counter 
        ACCESS          read-only 
        STATUS          mandatory 
        DESCRIPTION     "Used to indicate the number of Igmp packets 
                         received that are with checksum errors." 
        ::= { rcStatIgmp 2 } 
 
rcStatIgmpInQueries OBJECT-TYPE 
        SYNTAX          Counter 
        ACCESS          read-only 
        STATUS          mandatory 
        DESCRIPTION     "Used to indicate the number of Igmp queries 
                         received by the device." 
        ::= { rcStatIgmp 3 } 
 
rcStatIgmpInReports OBJECT-TYPE 
        SYNTAX          Counter 
        ACCESS          read-only 
        STATUS          mandatory 
        DESCRIPTION     "Used to indicate the number of Igmp reports 
                         received by the device." 
        ::= { rcStatIgmp 4 } 
 
 
rcStatIgmpInLeaves OBJECT-TYPE 
        SYNTAX          Counter 
        ACCESS          read-only 
        STATUS          mandatory 
        DESCRIPTION     "Used to indicate the number of Igmp Leaves 
                         received by the device." 
        ::= { rcStatIgmp 5 } 
 
rcStatIgmpInvalid OBJECT-TYPE 
        SYNTAX          Counter 
        ACCESS          read-only 
        STATUS          mandatory 
        DESCRIPTION     "Used to indicate the number of Igmp packets 
                         received by the device that contained invalid 
                         type." 
        ::= { rcStatIgmp 6 } 
 
rcStatIgmpOutMsgs OBJECT-TYPE 
        SYNTAX          Counter 
        ACCESS          read-only 
        STATUS          mandatory 
        DESCRIPTION     "Used to indicate the number of Igmp queries 
                         sent by the device." 
        ::= { rcStatIgmp 7 } 
 
rcStatOspfLsdbTblSize OBJECT-TYPE 
        SYNTAX        Counter 
        ACCESS        read-only 
        STATUS        mandatory 
        DESCRIPTION   "Used to indicate the number of entries in 
                      the linkstate database table." 
        ::= { rcStatOspf 12 } 
  
  
rcStatOspfIfTable OBJECT-TYPE 
        SYNTAX        SEQUENCE OF RcStatOspfIfEntry 
        ACCESS        not-accessible 
        STATUS        mandatory 
        DESCRIPTION   "A table used to store OSPF interface 
                      statistics." 
        ::= { rcStat 5 } 
  
rcStatOspfIfEntry OBJECT-TYPE 
        SYNTAX        RcStatOspfIfEntry 
        ACCESS        not-accessible 
        STATUS        mandatory 
        DESCRIPTION   "Ospf interface statistics" 
        INDEX         { rcStatOspfIfIndex } 
        ::= { rcStatOspfIfTable 1 } 
  
RcStatOspfIfEntry ::= SEQUENCE { 
                rcStatOspfIfIndex                   InterfaceIndex, 
                rcStatOspfIfRxHellos                Counter, 
                rcStatOspfIfRxDBDescrs              Counter, 
                rcStatOspfIfRxLSUpdates             Counter, 
                rcStatOspfIfRxLSReqs                Counter, 
                rcStatOspfIfRxLSAcks                Counter, 
                rcStatOspfIfTxHellos                Counter, 
                rcStatOspfIfTxDBDescrs              Counter, 
                rcStatOspfIfTxLSUpdates             Counter, 
                rcStatOspfIfTxLSReqs                Counter, 
                rcStatOspfIfTxLSAcks                Counter, 
                rcStatOspfIfVersionMismatches       Counter, 
                rcStatOspfIfAreaMismatches          Counter, 
                rcStatOspfIfAuthTypeMismatches      Counter, 
                rcStatOspfIfAuthFailures            Counter, 
                rcStatOspfIfNetMaskMismatches       Counter, 
                rcStatOspfIfHelloIntervalMismatches Counter, 
                rcStatOspfIfDeadIntervalMismatches  Counter, 
                rcStatOspfIfOptionMismatches        Counter 
        } 
  
rcStatOspfIfIndex OBJECT-TYPE 
        SYNTAX        InterfaceIndex (0..4094) 
        ACCESS        read-only 
        STATUS        mandatory 
        DESCRIPTION   "An unique value that is used to identify a 
                      physical interface." 
        ::= { rcStatOspfIfEntry 1 } 
  
rcStatOspfIfRxHellos OBJECT-TYPE 
        SYNTAX        Counter 
        ACCESS        read-only 
        STATUS        mandatory 
        DESCRIPTION   "Used to indicate the number hello packets 
                      received by this interface." 
        ::= { rcStatOspfIfEntry 2 } 
 
rcStatOspfIfRxDBDescrs OBJECT-TYPE 
        SYNTAX        Counter 
        ACCESS        read-only 
        STATUS        mandatory 
        DESCRIPTION   "Used to indicate the number database descriptor 
                      packets received by this interface." 
        ::= { rcStatOspfIfEntry 3 } 
  
rcStatOspfIfRxLSUpdates OBJECT-TYPE 
        SYNTAX        Counter 
        ACCESS        read-only 
        STATUS        mandatory 
        DESCRIPTION   "Used to indicate the number Link state update 
                      packets received by this interface." 
        ::= { rcStatOspfIfEntry 4 } 
  
rcStatOspfIfRxLSReqs OBJECT-TYPE 
        SYNTAX        Counter 
        ACCESS        read-only 
        STATUS        mandatory 
        DESCRIPTION   "Used to indicate the number Link state request 
                      packets received by this interface." 
        ::= { rcStatOspfIfEntry 5 } 
  
rcStatOspfIfRxLSAcks OBJECT-TYPE 
        SYNTAX        Counter 
        ACCESS        read-only 
        STATUS        mandatory 
        DESCRIPTION   "Used to indicate the number Link state acknowlege 
                      packets received by this interface." 
        ::= { rcStatOspfIfEntry 6 } 
  
rcStatOspfIfTxHellos OBJECT-TYPE 
        SYNTAX        Counter 
        ACCESS        read-only 
        STATUS        mandatory 
        DESCRIPTION   "Used to indicate the number hello packets 
                      transmitted by this interface." 
        ::= { rcStatOspfIfEntry 7 } 
  
rcStatOspfIfTxDBDescrs OBJECT-TYPE 
        SYNTAX        Counter 
        ACCESS        read-only 
        STATUS        mandatory 
        DESCRIPTION   "Used to indicate the number database descriptor 
                      packets transmitted by this interface." 
        ::= { rcStatOspfIfEntry 8 } 
  
rcStatOspfIfTxLSUpdates OBJECT-TYPE 
        SYNTAX        Counter 
        ACCESS        read-only 
        STATUS        mandatory 
        DESCRIPTION   "Used to indicate the number Link state update 
                      packets transmitted by this interface." 
        ::= { rcStatOspfIfEntry 9 } 
  
rcStatOspfIfTxLSReqs OBJECT-TYPE 
        SYNTAX        Counter 
        ACCESS        read-only 
        STATUS        mandatory 
        DESCRIPTION   "Used to indicate the number Link state request 
                      packets transmitted by this interface." 
        ::= { rcStatOspfIfEntry 10 } 
  
rcStatOspfIfTxLSAcks OBJECT-TYPE 
        SYNTAX        Counter 
        ACCESS        read-only 
        STATUS        mandatory 
        DESCRIPTION   "Used to indicate the number Link state acknowlege 
                      packets transmitted by this interface." 
        ::= { rcStatOspfIfEntry 11 } 
 
rcStatOspfIfVersionMismatches OBJECT-TYPE  
        SYNTAX        Counter 
        ACCESS        read-only 
        STATUS        mandatory 
        DESCRIPTION   "Used to indicate the number version 
                      mismatches received by this interface." 
        ::= { rcStatOspfIfEntry 12 } 
 
rcStatOspfIfAreaMismatches OBJECT-TYPE  
        SYNTAX        Counter 
        ACCESS        read-only 
        STATUS        mandatory 
        DESCRIPTION   "Used to indicate the number area 
                      mismatches received by this interface." 
        ::= { rcStatOspfIfEntry 13 } 
 
rcStatOspfIfAuthTypeMismatches OBJECT-TYPE  
        SYNTAX        Counter 
        ACCESS        read-only 
        STATUS        mandatory 
        DESCRIPTION   "Used to indicate the number AuthType  
                      mismatches received by this interface." 
        ::= { rcStatOspfIfEntry 14 } 
 
rcStatOspfIfAuthFailures OBJECT-TYPE  
        SYNTAX        Counter 
        ACCESS        read-only 
        STATUS        mandatory 
        DESCRIPTION   "Used to indicate the number Authentication 
                      failures." 
        ::= { rcStatOspfIfEntry 15 } 
 
rcStatOspfIfNetMaskMismatches OBJECT-TYPE  
        SYNTAX        Counter 
        ACCESS        read-only 
        STATUS        mandatory 
        DESCRIPTION   "Used to indicate the number net mask 
                      mismatches received by this interface." 
        ::= { rcStatOspfIfEntry 16 } 
 
rcStatOspfIfHelloIntervalMismatches OBJECT-TYPE  
        SYNTAX        Counter 
        ACCESS        read-only 
        STATUS        mandatory 
        DESCRIPTION   "Used to indicate the number hello interval 
                      mismatches received by this interface." 
        ::= { rcStatOspfIfEntry 17 } 
 
rcStatOspfIfDeadIntervalMismatches OBJECT-TYPE  
        SYNTAX        Counter 
        ACCESS        read-only 
        STATUS        mandatory 
        DESCRIPTION   "Used to indicate the number dead interval 
                      mismatches received by this interface." 
        ::= { rcStatOspfIfEntry 18 } 
 
rcStatOspfIfOptionMismatches OBJECT-TYPE  
        SYNTAX        Counter 
        ACCESS        read-only 
        STATUS        mandatory 
        DESCRIPTION   "Used to indicate the number options 
                      mismatches received by this interface." 
        ::= { rcStatOspfIfEntry 19 } 
 
-- rcStatMlt Group 
 
rcStatMlt      OBJECT IDENTIFIER ::= { rcStat 6 } 
  
rcStatMltIfExtnTable OBJECT-TYPE 
        SYNTAX        SEQUENCE OF RcStatMltIfExtnEntry 
        ACCESS        not-accessible 
        STATUS        mandatory 
        DESCRIPTION   "A table used to store Mlt interface 
                      statistics." 
        ::= { rcStatMlt 1 } 
  
rcStatMltIfExtnEntry OBJECT-TYPE 
        SYNTAX        RcStatMltIfExtnEntry 
        ACCESS        not-accessible 
        STATUS        mandatory 
        DESCRIPTION   "Mlt interface statistics" 
        INDEX         { rcStatMltIfExtnMltId } 
        ::= { rcStatMltIfExtnTable 1 } 
  
RcStatMltIfExtnEntry ::= SEQUENCE { 
                rcStatMltIfExtnMltId                  INTEGER, 
                rcStatMltIfExtnIfInMulticastPkts      Counter32, 
                rcStatMltIfExtnIfInBroadcastPkts      Counter32, 
                rcStatMltIfExtnIfOutMulticastPkts     Counter32, 
                rcStatMltIfExtnIfOutBroadcastPkts     Counter32, 
                rcStatMltIfExtnIfHCInOctets           Counter64, 
                rcStatMltIfExtnIfHCInUcastPkts        Counter64, 
                rcStatMltIfExtnIfHCInMulticastPkt     Counter64, 
                rcStatMltIfExtnIfHCInBroadcastPkt     Counter64, 
                rcStatMltIfExtnIfHCOutOctets          Counter64, 
                rcStatMltIfExtnIfHCOutUcastPkts       Counter64, 
                rcStatMltIfExtnIfHCOutMulticast       Counter64, 
                rcStatMltIfExtnIfHCOutBroadcast       Counter64 
        } 
  
rcStatMltIfExtnMltId OBJECT-TYPE 
        SYNTAX        INTEGER (1..8) 
        ACCESS        read-only 
        STATUS        mandatory 
        DESCRIPTION   "Mlt Id" 
        ::= { rcStatMltIfExtnEntry 1 } 
  
rcStatMltIfExtnIfInMulticastPkts OBJECT-TYPE 
        SYNTAX        Counter32 
        ACCESS        read-only 
        STATUS        mandatory 
        DESCRIPTION   "multi-pkts to upper" 
        ::= { rcStatMltIfExtnEntry 2 } 
 
rcStatMltIfExtnIfInBroadcastPkts OBJECT-TYPE 
        SYNTAX        Counter32 
        ACCESS        read-only 
        STATUS        mandatory 
        DESCRIPTION   "broad-pkts to upper" 
        ::= { rcStatMltIfExtnEntry 3 } 
  
rcStatMltIfExtnIfOutMulticastPkts OBJECT-TYPE 
        SYNTAX        Counter32 
        ACCESS        read-only 
        STATUS        mandatory 
        DESCRIPTION   "multi-pkts from upper" 
        ::= { rcStatMltIfExtnEntry 4 } 
  
rcStatMltIfExtnIfOutBroadcastPkts OBJECT-TYPE 
        SYNTAX        Counter32 
        ACCESS        read-only 
        STATUS        mandatory 
        DESCRIPTION   "broad-pkts from upper" 
        ::= { rcStatMltIfExtnEntry 5 } 
  
rcStatMltIfExtnIfHCInOctets OBJECT-TYPE 
        SYNTAX        Counter64 
        ACCESS        read-only 
        STATUS        mandatory 
        DESCRIPTION   "~ifInOctets" 
        ::= { rcStatMltIfExtnEntry 6 } 
  
rcStatMltIfExtnIfHCInUcastPkts OBJECT-TYPE 
        SYNTAX        Counter64 
        ACCESS        read-only 
        STATUS        mandatory 
        DESCRIPTION   "~ifInUcastPkts" 
        ::= { rcStatMltIfExtnEntry 7 } 
  
rcStatMltIfExtnIfHCInMulticastPkt OBJECT-TYPE 
        SYNTAX        Counter64 
        ACCESS        read-only 
        STATUS        mandatory 
        DESCRIPTION   "~ifInMulticastPkts" 
        ::= { rcStatMltIfExtnEntry 8 } 
  
rcStatMltIfExtnIfHCInBroadcastPkt OBJECT-TYPE 
        SYNTAX        Counter64 
        ACCESS        read-only 
        STATUS        mandatory 
        DESCRIPTION   "~ifInBroadcastPkts" 
        ::= { rcStatMltIfExtnEntry 9 } 
  
rcStatMltIfExtnIfHCOutOctets OBJECT-TYPE 
        SYNTAX        Counter64 
        ACCESS        read-only 
        STATUS        mandatory 
        DESCRIPTION   "~ifOutOctets" 
        ::= { rcStatMltIfExtnEntry 10 } 
  
rcStatMltIfExtnIfHCOutUcastPkts OBJECT-TYPE 
        SYNTAX        Counter64 
        ACCESS        read-only 
        STATUS        mandatory 
        DESCRIPTION   "~ifOutUcastPkts" 
        ::= { rcStatMltIfExtnEntry 11 } 
 
rcStatMltIfExtnIfHCOutMulticast OBJECT-TYPE  
        SYNTAX        Counter64 
        ACCESS        read-only 
        STATUS        mandatory 
        DESCRIPTION   "~ifOutMulticastPkts" 
        ::= { rcStatMltIfExtnEntry 12 } 
 
rcStatMltIfExtnIfHCOutBroadcast OBJECT-TYPE  
        SYNTAX        Counter64 
        ACCESS        read-only 
        STATUS        mandatory 
        DESCRIPTION   "~ifOutBroadcastPkts" 
        ::= { rcStatMltIfExtnEntry 13 } 
 
-- Mlt Ether table 
 
rcStatMltEtherTable OBJECT-TYPE 
        SYNTAX        SEQUENCE OF RcStatMltEtherEntry 
        ACCESS        not-accessible 
        STATUS        mandatory 
        DESCRIPTION   "A table used to store Mlt Ethernet 
                      statistics." 
        ::= { rcStatMlt 2 } 
  
rcStatMltEtherEntry OBJECT-TYPE 
        SYNTAX        RcStatMltEtherEntry 
        ACCESS        not-accessible 
        STATUS        mandatory 
        DESCRIPTION   "Mlt enternet statistics" 
        INDEX         { rcStatMltEtherMltId } 
        ::= { rcStatMltEtherTable 1 } 
  
RcStatMltEtherEntry ::= SEQUENCE { 
                rcStatMltEtherMltId              INTEGER, 
                rcStatMltEtherAlignmentErrors    Counter, 
                rcStatMltEtherFCSErrors          Counter, 
                rcStatMltEtherSingleCollFrames   Counter, 
                rcStatMltEtherMultipleCollFrames Counter, 
                rcStatMltEtherSQETestError       Counter, 
                rcStatMltEtherDeferredTransmiss  Counter, 
                rcStatMltEtherLateCollisions     Counter, 
                rcStatMltEtherExcessiveCollis    Counter, 
                rcStatMltEtherIMacTransmitError  Counter, 
                rcStatMltEtherCarrierSenseError  Counter, 
                rcStatMltEtherFrameTooLong       Counter, 
                rcStatMltEtherIMacReceiveError   Counter 
        } 
  
rcStatMltEtherMltId OBJECT-TYPE 
        SYNTAX        INTEGER (1..8) 
        ACCESS        read-only 
        STATUS        mandatory 
        DESCRIPTION   "Mlt Id" 
        ::= { rcStatMltEtherEntry 1 } 
  
rcStatMltEtherAlignmentErrors OBJECT-TYPE 
        SYNTAX        Counter 
        ACCESS        read-only 
        STATUS        mandatory 
        DESCRIPTION   "non-integral # of octets" 
        ::= { rcStatMltEtherEntry 2 } 
 
rcStatMltEtherFCSErrors OBJECT-TYPE 
        SYNTAX        Counter 
        ACCESS        read-only 
        STATUS        mandatory 
        DESCRIPTION   "FCS error" 
        ::= { rcStatMltEtherEntry 3 } 
  
rcStatMltEtherSingleCollFrames OBJECT-TYPE 
        SYNTAX        Counter 
        ACCESS        read-only 
        STATUS        mandatory 
        DESCRIPTION   "one collision" 
        ::= { rcStatMltEtherEntry 4 } 
  
rcStatMltEtherMultipleCollFrames OBJECT-TYPE 
        SYNTAX        Counter 
        ACCESS        read-only 
        STATUS        mandatory 
        DESCRIPTION   "multiple collision" 
        ::= { rcStatMltEtherEntry 5 } 
  
rcStatMltEtherSQETestError OBJECT-TYPE 
        SYNTAX        Counter 
        ACCESS        read-only 
        STATUS        mandatory 
        DESCRIPTION   "signal quality error" 
        ::= { rcStatMltEtherEntry 6 } 
  
rcStatMltEtherDeferredTransmiss OBJECT-TYPE 
        SYNTAX        Counter 
        ACCESS        read-only 
        STATUS        mandatory 
        DESCRIPTION   "delay due to media busy" 
        ::= { rcStatMltEtherEntry 7 } 
  
rcStatMltEtherLateCollisions OBJECT-TYPE 
        SYNTAX        Counter 
        ACCESS        read-only 
        STATUS        mandatory 
        DESCRIPTION   "detect after 64 octets" 
        ::= { rcStatMltEtherEntry 8 } 
  
rcStatMltEtherExcessiveCollis OBJECT-TYPE 
        SYNTAX        Counter 
        ACCESS        read-only 
        STATUS        mandatory 
        DESCRIPTION   "excessive collisions" 
        ::= { rcStatMltEtherEntry 9 } 
  
rcStatMltEtherIMacTransmitError OBJECT-TYPE 
        SYNTAX        Counter 
        ACCESS        read-only 
        STATUS        mandatory 
        DESCRIPTION   "internal MAC layer error" 
        ::= { rcStatMltEtherEntry 10 } 
  
rcStatMltEtherCarrierSenseError OBJECT-TYPE 
        SYNTAX        Counter 
        ACCESS        read-only 
        STATUS        mandatory 
        DESCRIPTION   "CSE problem" 
        ::= { rcStatMltEtherEntry 11 } 
 
rcStatMltEtherFrameTooLong OBJECT-TYPE  
        SYNTAX        Counter 
        ACCESS        read-only 
        STATUS        mandatory 
        DESCRIPTION   "> 1518 octets" 
        ::= { rcStatMltEtherEntry 12 } 
 
rcStatMltEtherIMacReceiveError OBJECT-TYPE  
        SYNTAX        Counter 
        ACCESS        read-only 
        STATUS        mandatory 
        DESCRIPTION   "internal MAC layer error" 
        ::= { rcStatMltEtherEntry 13 } 
 
 
-- Mlt Ip table 
 
rcStatMltIpTable OBJECT-TYPE 
        SYNTAX        SEQUENCE OF RcStatMltIpEntry 
        ACCESS        not-accessible 
        STATUS        mandatory 
        DESCRIPTION   "A table used to store Mlt Ip statistics." 
        ::= { rcStatMlt 3 } 
  
rcStatMltIpEntry OBJECT-TYPE 
        SYNTAX        RcStatMltIpEntry 
        ACCESS        not-accessible 
        STATUS        mandatory 
        DESCRIPTION   "Mlt enternet statistics" 
        INDEX         { rcStatMltIpMltId } 
        ::= { rcStatMltIpTable 1 } 
  
RcStatMltIpEntry ::= SEQUENCE { 
                rcStatMltIpMltId            INTEGER, 
                rcStatMltIpInReceives       Counter, 
                rcStatMltIpInHdrErrors      Counter, 
                rcStatMltIpInAddrErrors     Counter, 
                rcStatMltIpForwDatagrams    Counter, 
                rcStatMltIpInUnknownProtos  Counter, 
                rcStatMltIpInDiscards       Counter, 
                rcStatMltIpInDelivers       Counter, 
                rcStatMltIpOutRequest       Counter, 
                rcStatMltIpOutDiscards      Counter, 
                rcStatMltIpOutNoRoutes      Counter, 
                rcStatMltIpReasmReqds       Counter, 
                rcStatMltIpReasmOKs         Counter, 
                rcStatMltIpReasmFails       Counter, 
                rcStatMltIpFragOKs          Counter, 
                rcStatMltIpFragFails        Counter, 
                rcStatMltIpFragCreates      Counter, 
                rcStatMltIpRoutingDiscards  Counter 
        } 
  
rcStatMltIpMltId OBJECT-TYPE 
        SYNTAX        INTEGER (1..8) 
        ACCESS        read-only 
        STATUS        mandatory 
        DESCRIPTION   "Mlt Id" 
        ::= { rcStatMltIpEntry 1 } 
  
rcStatMltIpInReceives OBJECT-TYPE 
        SYNTAX        Counter 
        ACCESS        read-only 
        STATUS        mandatory 
        DESCRIPTION   "all incoming packets" 
        ::= { rcStatMltIpEntry 2 } 
 
rcStatMltIpInHdrErrors OBJECT-TYPE 
        SYNTAX        Counter 
        ACCESS        read-only 
        STATUS        mandatory 
        DESCRIPTION   "hdr errors detected" 
        ::= { rcStatMltIpEntry 3 } 
  
rcStatMltIpInAddrErrors OBJECT-TYPE 
        SYNTAX        Counter 
        ACCESS        read-only 
        STATUS        mandatory 
        DESCRIPTION   "bad dest. ip addr" 
        ::= { rcStatMltIpEntry 4 } 
  
rcStatMltIpForwDatagrams OBJECT-TYPE 
        SYNTAX        Counter 
        ACCESS        read-only 
        STATUS        mandatory 
        DESCRIPTION   "packets forwarded" 
        ::= { rcStatMltIpEntry 5 } 
  
rcStatMltIpInUnknownProtos OBJECT-TYPE 
        SYNTAX        Counter 
        ACCESS        read-only 
        STATUS        mandatory 
        DESCRIPTION   "unsupported protocol" 
        ::= { rcStatMltIpEntry 6 } 
  
rcStatMltIpInDiscards OBJECT-TYPE 
        SYNTAX        Counter 
        ACCESS        read-only 
        STATUS        mandatory 
        DESCRIPTION   "good, but no buffer" 
        ::= { rcStatMltIpEntry 7 } 
  
rcStatMltIpInDelivers OBJECT-TYPE 
        SYNTAX        Counter 
        ACCESS        read-only 
        STATUS        mandatory 
        DESCRIPTION   "pkts delivered to upper" 
        ::= { rcStatMltIpEntry 8 } 
  
rcStatMltIpOutRequest OBJECT-TYPE 
        SYNTAX        Counter 
        ACCESS        read-only 
        STATUS        mandatory 
        DESCRIPTION   "pkts received from upper" 
        ::= { rcStatMltIpEntry 9 } 
  
rcStatMltIpOutDiscards OBJECT-TYPE 
        SYNTAX        Counter 
        ACCESS        read-only 
        STATUS        mandatory 
        DESCRIPTION   "good, but no buffer" 
        ::= { rcStatMltIpEntry 10 } 
  
rcStatMltIpOutNoRoutes OBJECT-TYPE 
        SYNTAX        Counter 
        ACCESS        read-only 
        STATUS        mandatory 
        DESCRIPTION   "no route to destination" 
        ::= { rcStatMltIpEntry 11 } 
 
rcStatMltIpReasmReqds OBJECT-TYPE  
        SYNTAX        Counter 
        ACCESS        read-only 
        STATUS        mandatory 
        DESCRIPTION   "fragments to reassem" 
        ::= { rcStatMltIpEntry 12 } 
 
rcStatMltIpReasmOKs OBJECT-TYPE  
        SYNTAX        Counter 
        ACCESS        read-only 
        STATUS        mandatory 
        DESCRIPTION   "reassembled successfully" 
        ::= { rcStatMltIpEntry 13 } 
 
rcStatMltIpReasmFails OBJECT-TYPE  
        SYNTAX        Counter 
        ACCESS        read-only 
        STATUS        mandatory 
        DESCRIPTION   "reassembly failures" 
        ::= { rcStatMltIpEntry 14 } 
 
rcStatMltIpFragOKs OBJECT-TYPE  
        SYNTAX        Counter 
        ACCESS        read-only 
        STATUS        mandatory 
        DESCRIPTION   "fragment successfully" 
        ::= { rcStatMltIpEntry 15 } 
 
rcStatMltIpFragFails OBJECT-TYPE  
        SYNTAX        Counter 
        ACCESS        read-only 
        STATUS        mandatory 
        DESCRIPTION   "fragment failure" 
        ::= { rcStatMltIpEntry 16 } 
 
rcStatMltIpFragCreates OBJECT-TYPE  
        SYNTAX        Counter 
        ACCESS        read-only 
        STATUS        mandatory 
        DESCRIPTION   "pkts due to fragmenting" 
        ::= { rcStatMltIpEntry 17 } 
 
rcStatMltIpRoutingDiscards OBJECT-TYPE  
        SYNTAX        Counter 
        ACCESS        read-only 
        STATUS        mandatory 
        DESCRIPTION   "Route entries removed" 
        ::= { rcStatMltIpEntry 18 } 
 
-- Spanning Tree Group (STG) 
 
rcStgMaxStgs OBJECT-TYPE 
        SYNTAX        INTEGER 
        ACCESS        read-write 
        STATUS        mandatory 
        DESCRIPTION   "The maximum number of spanning tree groups this 
		      device can support concurrently." 
        ::= { rcStg 1 } 
 
rcStgNumStgs OBJECT-TYPE 
        SYNTAX        INTEGER 
        ACCESS        read-only 
        STATUS        mandatory 
        DESCRIPTION   "The number of spanning tree groups that are 
		      currently defined." 
        ::= { rcStg 2 } 
 
rcStgUnassignedPorts OBJECT-TYPE 
        SYNTAX        PortSet 
        ACCESS        read-only 
        STATUS        mandatory 
        DESCRIPTION   "A bitfield used to identify which ports in 
                      the system currently not assigned to any STG. 
 
                      The bitfield is 32 octets long representing  
                      ports 0 to 255 (inclusive)." 
        ::= { rcStg 3 } 
 
 
-- STG Table 
 
rcStgTable OBJECT-TYPE 
        SYNTAX        SEQUENCE OF RcStgEntry 
        ACCESS        not-accessible 
        STATUS        mandatory 
        DESCRIPTION   "A table used to store Spanning Tree Group (STG) 
		      information.  Each row in the table specifies 
		      a different STG in the device." 
        ::= { rcStg 4 }  
  
rcStgEntry OBJECT-TYPE   
        SYNTAX        RcStgEntry 
        ACCESS        not-accessible 
        STATUS        mandatory 
        DESCRIPTION   "STG attributes" 
        INDEX  { rcStgId } 
        ::= { rcStgTable 1 } 
  
RcStgEntry ::= SEQUENCE { 
		rcStgId INTEGER, 
		rcStgTaggedBpduAddress MacAddress, 
		rcStgTaggedBpduVlanId INTEGER, 
		rcStgBridgeAddress MacAddress, 
		rcStgNumPorts INTEGER, 
		rcStgProtocolSpecification INTEGER, 
		rcStgPriority INTEGER, 
		rcStgTimeSinceTopologyChange TimeTicks, 
		rcStgTopChanges Counter, 
		rcStgDesignatedRoot BridgeId, 
		rcStgRootCost INTEGER, 
		rcStgRootPort INTEGER, 
		rcStgMaxAge Timeout, 
		rcStgHelloTime Timeout, 
		rcStgHoldTime INTEGER, 
		rcStgForwardDelay Timeout, 
		rcStgBridgeMaxAge Timeout, 
		rcStgBridgeHelloTime Timeout, 
		rcStgBridgeForwardDelay Timeout, 
		rcStgEnableStp TruthValue, 
		rcStgStpTrapEnable TruthValue, 
		rcStgPortMembers OCTET STRING, 
		rcStgRowStatus RowStatus 
        } 
 
rcStgId OBJECT-TYPE  
        SYNTAX  	INTEGER (1..25) 
        ACCESS  	read-only 
        STATUS  	mandatory 
        DESCRIPTION 	"An identifier used to identify a STG in the device." 
        ::= { rcStgEntry 1 } 
 
rcStgTaggedBpduAddress OBJECT-TYPE 
        SYNTAX  	MacAddress 
        ACCESS  	read-write 
        STATUS  	mandatory 
        DESCRIPTION 	"The MAC address to be assigned to the destination 
      	       		mac address field in tagged BPDUs.   
 
	       		The default address is the well known multicast  
	       		group address 01-80-c2-00-00-00." 
        DEFVAL          { "01:80:c2:00:00:00" } 
  	::= { rcStgEntry 2 } 
 
rcStgTaggedBpduVlanId OBJECT-TYPE  
        SYNTAX  	INTEGER   
        ACCESS  	read-write  
        STATUS  	mandatory   
        DESCRIPTION 	"The VLAN ID to be used for tagging BPDUs."  
        ::= { rcStgEntry 3 } 
 
rcStgBridgeAddress OBJECT-TYPE 
        SYNTAX  	MacAddress 
        ACCESS  	read-only 
        STATUS  	mandatory 
        DESCRIPTION 	"The MAC address used by this bridge when it must 
		       	be referred to in a unique fashion.   It is 
		       	recommended that this be the numerically smallest 
		       	MAC address of all ports that belong to this 
		       	bridge.  However it is only required to be unique. 
		       	When concatenated with rcStgPriority a unique 
		       	BridgeIdentifier is formed which is used in the 
		       	Spanning Tree Protocol." 
        REFERENCE 	"IEEE 802.1D-1990: Sections 6.4.1.1.3 and 3.12.5" 
        ::= { rcStgEntry 4 } 
 
rcStgNumPorts OBJECT-TYPE 
        SYNTAX  	INTEGER 
        ACCESS  	read-only 
        STATUS  	mandatory 
        DESCRIPTION 	"The number of ports controlled by this bridging entity." 
        REFERENCE 	"IEEE 802.1D-1990: Section 6.4.1.1.3" 
        ::= { rcStgEntry 5 } 
 
rcStgProtocolSpecification OBJECT-TYPE 
        SYNTAX  	INTEGER { 
			      unknown(1), 
			      decLb100(2), 
			      ieee8021d(3) 
		        } 
        ACCESS  	read-only 
        STATUS  	mandatory 
        DESCRIPTION 	"An indication of what version of the Spanning 
                     	Tree Protocol is being run.  The value 
                     	'decLb100(2)' indicates the DEC LANbridge 100 
                     	Spanning Tree protocol.  IEEE 802.1d 
                     	implementations will return 'ieee8021d(3)'.  If 
                     	future versions of the IEEE Spanning Tree Protocol 
                     	are released that are incompatible with the 
                     	current version a new value will be defined." 
        ::= { rcStgEntry 6 } 
 
rcStgPriority OBJECT-TYPE 
        SYNTAX  	INTEGER (0..65535) 
        ACCESS  	read-write 
        STATUS  	mandatory 
        DESCRIPTION 	"The value of the write-able portion of the Bridge 
	      	       	ID, i.e., the first two octets of the (8 octet 
      		       	long) Bridge ID.  The other (last) 6 octets of the 
      	       		Bridge ID are given by the value of rcStgBridgeAddress." 
        REFERENCE 	"IEEE 802.1D-1990: Section 4.5.3.7" 
        DEFVAL          { 32768 } 
        ::= { rcStgEntry 7 } 
 
rcStgTimeSinceTopologyChange OBJECT-TYPE 
        SYNTAX  	TimeTicks 
        ACCESS  	read-only 
        STATUS  	mandatory 
        DESCRIPTION 	"The time (in hundredths of a second) since the 
	       		last time a topology change was detected by the 
	       		bridge entity." 
        REFERENCE 	"IEEE 802.1D-1990: Section 6.8.1.1.3" 
        ::= { rcStgEntry 8 } 
 
rcStgTopChanges OBJECT-TYPE 
        SYNTAX  	Counter 
        ACCESS  	read-only 
        STATUS  	mandatory 
        DESCRIPTION 	"The total number of topology changes detected by 
	       		this bridge since the management entity was last 
	       		reset or initialized." 
        REFERENCE 	"IEEE 802.1D-1990: Section 6.8.1.1.3" 
        ::= { rcStgEntry 9 } 
 
rcStgDesignatedRoot OBJECT-TYPE 
        SYNTAX  	BridgeId 
        ACCESS  	read-only 
        STATUS  	mandatory 
        DESCRIPTION 	"The bridge identifier of the root of the spanning 
	       		tree as determined by the Spanning Tree Protocol 
	       		as executed by this node.  This value is used as 
                        the Root Identifier parameter in all Configuration 
                        Bridge PDUs originated by this node." 
        REFERENCE 	"IEEE 802.1D-1990: Section 4.5.3.1" 
        ::= { rcStgEntry 10 } 
 
rcStgRootCost OBJECT-TYPE 
        SYNTAX  	INTEGER 
        ACCESS  	read-only 
        STATUS  	mandatory 
        DESCRIPTION 	"The cost of the path to the root as seen from 
	       		this bridge." 
        REFERENCE 	"IEEE 802.1D-1990: Section 4.5.3.2" 
        ::= { rcStgEntry 11 } 
 
rcStgRootPort OBJECT-TYPE 
        SYNTAX  	INTEGER 
        ACCESS  	read-only 
        STATUS  	mandatory 
        DESCRIPTION 	"The port number of the port which offers the 
	  		lowest cost path from this bridge to the root 
               		bridge." 
        REFERENCE 	"IEEE 802.1D-1990: Section 4.5.3.3" 
        ::= { rcStgEntry 12 } 
 
rcStgMaxAge OBJECT-TYPE 
        SYNTAX  	Timeout 
        ACCESS  	read-only 
        STATUS  	mandatory 
        DESCRIPTION 	"The maximum age of Spanning Tree Protocol 
	       		information learned from the network on any port 
	       		before it is discarded, in units of hundredths of 
	       		a second.  This is the actual value that this 
	       		bridge is currently using." 
        REFERENCE 	"IEEE 802.1D-1990: Section 4.5.3.4" 
        ::= { rcStgEntry 13 } 
 
rcStgHelloTime OBJECT-TYPE 
        SYNTAX  	Timeout 
        ACCESS  	read-only 
        STATUS  	mandatory 
        DESCRIPTION 	"The amount of time between the transmission of 
	       		Configuration bridge PDUs by this node on any port 
	       		when it is the root of the spanning tree or trying 
	       		to become so, in units of hundredths of a second. 
	       		This is the actual value that this bridge is 
                        currently using." 
        REFERENCE 	"IEEE 802.1D-1990: Section 4.5.3.5" 
        ::= { rcStgEntry 14 } 
 
rcStgHoldTime OBJECT-TYPE 
        SYNTAX  	INTEGER 
        ACCESS  	read-only 
        STATUS  	mandatory 
        DESCRIPTION     "This time value determines the interval length 
	                during which no more than two Configuration bridge 
	                PDUs shall be transmitted by this node, in units 
	             	of hundredths of a second." 
        REFERENCE 	"IEEE 802.1D-1990: Section 4.5.3.14" 
        ::= { rcStgEntry 15 } 
 
rcStgForwardDelay OBJECT-TYPE 
        SYNTAX  	Timeout 
        ACCESS  	read-only 
        STATUS  	mandatory 
        DESCRIPTION 	"This time value, measured in units of hundredths 
	             	of a second, controls how fast a port changes its 
	             	spanning state when moving towards the Forwarding 
	             	state.  The value determines how long the port 
	             	stays in each of the Listening and Learning 
	             	states, which precede the Forwarding state.  This 
	             	value is also used, when a topology change has 
	             	been detected and is underway, to age all dynamic 
	             	entries in the Forwarding Database.  [Note that 
	             	this value is the one that this bridge is 
	             	currently using, in contrast to 
	             	rcStgBridgeForwardDelay which is the value that 
	             	this bridge and all others would start using 
	             	if/when this bridge were to become the root.]" 
        REFERENCE 	"IEEE 802.1D-1990: Section 4.5.3.6" 
        ::= { rcStgEntry 16 } 
 
rcStgBridgeMaxAge OBJECT-TYPE 
        SYNTAX  	Timeout (600..4000) 
        ACCESS  	read-write 
        STATUS  	mandatory 
        DESCRIPTION 	"The value that all bridges use for MaxAge when 
	             	this bridge is acting as the root.  Note that 
	             	802.1D-1990 specifies that the range for this 
	             	parameter is related to the value of 
	             	rcStgBridgeHelloTime. The granularity of this 
	             	timer is specified by 802.1D-1990 to be 1 second. 
	             	An agent may return a badValue error if a set is 
	             	attempted to a value which is not a whole number 
	             	of seconds." 
        REFERENCE 	"IEEE 802.1D-1990: Section 4.5.3.8" 
        DEFVAL          { 2000 } 
        ::= { rcStgEntry 17 } 
 
rcStgBridgeHelloTime OBJECT-TYPE 
        SYNTAX  	Timeout (100..1000) 
        ACCESS  	read-write 
        STATUS  	mandatory 
        DESCRIPTION 	"The value that all bridges use for HelloTime when 
	             	this bridge is acting as the root.  The 
	             	granularity of this timer is specified by 802.1D- 
	             	1990 to be 1 second.  An agent may return a 
	             	badValue error if a set is attempted to a value 
	             	which is not a whole number of seconds." 
        REFERENCE 	"IEEE 802.1D-1990: Section 4.5.3.9" 
        DEFVAL          { 200 } 
        ::= { rcStgEntry 18 } 
 
rcStgBridgeForwardDelay OBJECT-TYPE 
        SYNTAX  	Timeout (400..3000) 
        ACCESS  	read-write 
        STATUS  	mandatory 
        DESCRIPTION 	"The value that all bridges use for ForwardDelay 
	             	when this bridge is acting as the root.  Note that 
	             	802.1D-1990 specifies that the range for this 
	             	parameter is related to the value of 
	             	rcStgBridgeMaxAge.  The granularity of this 
	             	timer is specified by 802.1D-1990 to be 1 second. 
	             	An agent may return a badValue error if a set is 
	             	attempted to a value which is not a whole number 
	             	of seconds." 
        REFERENCE 	"IEEE 802.1D-1990: Section 4.5.3.10" 
        DEFVAL          { 1500 } 
        ::= { rcStgEntry 19 } 
 
rcStgEnableStp OBJECT-TYPE 
        SYNTAX  	TruthValue 
        ACCESS  	read-write 
        STATUS  	mandatory 
        DESCRIPTION 	"Indicate whether the spanning tree protocol  
	       		should be active in this STG." 
        DEFVAL         { true } 
        ::= { rcStgEntry 20 } 
 
rcStgStpTrapEnable OBJECT-TYPE 
        SYNTAX 	 	TruthValue 
        ACCESS  	read-write 
        STATUS  	mandatory 
        DESCRIPTION 	"Indicate whether traps relating to the spanning 
	       		tree protocol should be sent for this STG." 
        DEFVAL         { true } 
        ::= { rcStgEntry 21 } 
 
rcStgPortMembers OBJECT-TYPE 
        SYNTAX          OCTET STRING (SIZE(32)) 
        ACCESS          read-write 
        STATUS          mandatory 
        DESCRIPTION     "A bitfield used to identify which ports in 
		   	the system are members this STG. 
 
		   	The bitfield is 32 octets long representing 
		   	ports 0 to 255 (inclusive)." 
        ::= { rcStgEntry 22 } 
 
rcStgRowStatus OBJECT-TYPE 
        SYNTAX  	RowStatus 
        ACCESS  	read-write 
        STATUS  	mandatory 
        DESCRIPTION 	"Row status." 
        ::= { rcStgEntry 23 } 
 
 
-- STG Port Table 
 
rcStgPortTable OBJECT-TYPE 
        SYNTAX        SEQUENCE OF RcStgPortEntry 
        ACCESS        not-accessible 
        STATUS        mandatory     
        DESCRIPTION   "A table used to store Spanning Tree Group (STG) 
                      port related information.  If a port is  
                      associated with more than one STGs, the port   
                      will have one entry in this table for each STG  
                      it assigned to."  
        ::= { rcStg 5 } 
  
rcStgPortEntry OBJECT-TYPE 
        SYNTAX        RcStgPortEntry 
        ACCESS        not-accessible 
        STATUS        mandatory 
        DESCRIPTION   "STG Port attributes"  
        INDEX         { rcStgPort, rcStgPortStgId } 
        ::= { rcStgPortTable 1 } 
  
RcStgPortEntry ::= SEQUENCE { 
                  rcStgPort InterfaceIndex, 
                  rcStgPortStgId INTEGER, 
                  rcStgPortPriority INTEGER, 
                  rcStgPortState INTEGER, 
                  rcStgPortEnableStp TruthValue, 
                  rcStgPortFastStart TruthValue, 
                  rcStgPortPathCost INTEGER, 
                  rcStgPortDesignatedRoot BridgeId, 
                  rcStgPortDesignatedCost INTEGER, 
                  rcStgPortDesignatedBridge BridgeId, 
                  rcStgPortDesignatedPort OCTET STRING, 
                  rcStgPortForwardTransitions Counter, 
                  rcStgPortInConfigBpdus Counter, 
                  rcStgPortInTcnBpdus Counter, 
                  rcStgPortInBadBpdus Counter, 
                  rcStgPortOutConfigBpdus Counter, 
                  rcStgPortOutTcnBpdus Counter, 
		  rcStgPortRowStatus RowStatus 
              } 
 
rcStgPort OBJECT-TYPE 
        SYNTAX  	InterfaceIndex 
        ACCESS  	read-only 
        STATUS  	mandatory 
        DESCRIPTION 	"The port number of the port for which this entry 
                     	contains Spanning Tree Protocol management 
                     	information." 
        REFERENCE 	"IEEE 802.1D-1990: Section 6.8.2.1.2" 
        ::= { rcStgPortEntry 1 } 
 
rcStgPortStgId OBJECT-TYPE 
        SYNTAX  	INTEGER (1..128) 
        ACCESS  	read-only 
        STATUS  	mandatory 
	DESCRIPTION 	"The STG identifier this port is assigned to." 
        ::= { rcStgPortEntry 2 } 
 
rcStgPortPriority OBJECT-TYPE 
        SYNTAX  	INTEGER (0..255) 
        ACCESS  	read-write 
        STATUS  	mandatory 
        DESCRIPTION 	"The value of the priority field which is 
                     	contained in the first (in network byte order) 
                     	octet of the (2 octet long) Port ID.  The other 
                     	octet of the Port ID is given by the value of 
                     	rcStgPort." 
        REFERENCE 	"IEEE 802.1D-1990: Section 4.5.5.1" 
        DEFVAL          { 128 } 
        ::= { rcStgPortEntry 3 } 
 
rcStgPortState OBJECT-TYPE 
        SYNTAX  	INTEGER { 
	                	disabled(1), 
       		         	blocking(2), 
       	        		listening(3), 
		                learning(4), 
               		 	forwarding(5), 
                		broken(6) 
        		} 
        ACCESS  	read-only 
        STATUS  	mandatory 
        DESCRIPTION 	"The port's current state as defined by 
                     	application of the Spanning Tree Protocol.  This 
                     	state controls what action a port takes on 
                     	reception of a frame.  If the bridge has detected 
                     	a port that is malfunctioning it will place that 
                     	port into the broken(6) state.  For ports which 
                     	are disabled (see rcStgPortEnable), this object 
                     	will have a value of disabled(1)." 
        REFERENCE 	"IEEE 802.1D-1990: Section 4.5.5.2" 
        ::= { rcStgPortEntry 4 } 
 
 
rcStgPortEnableStp OBJECT-TYPE 
        SYNTAX  	TruthValue 
        ACCESS  	read-write 
        STATUS  	mandatory 
        DESCRIPTION 	"The enabled/disabled status of the port." 
        REFERENCE 	"IEEE 802.1D-1990: Section 4.5.5.2" 
        DEFVAL           { true } 
        ::= { rcStgPortEntry 5 } 
 
rcStgPortFastStart OBJECT-TYPE 
        SYNTAX     	TruthValue 
        ACCESS     	read-write 
        STATUS     	mandatory 
        DESCRIPTION 	"When this flag is set, the port is moved  
                     	straight to the forwarding(5) state upon  
                     	being enabled." 
        DEFVAL          { false } 
        ::= { rcStgPortEntry 6 } 
 
rcStgPortPathCost OBJECT-TYPE 
        SYNTAX  	INTEGER (1..65535) 
        ACCESS  	read-write 
        STATUS  	mandatory 
        DESCRIPTION 	"The contribution of this port to the path cost of 
                     	paths towards the spanning tree root which include 
                     	this port.  802.1D-1990 recommends that the 
                     	default value of this parameter be in inverse 
                     	proportion to the speed of the attached LAN." 
        REFERENCE 	"IEEE 802.1D-1990: Section 4.5.5.3" 
        ::= { rcStgPortEntry 7 } 
 
rcStgPortDesignatedRoot OBJECT-TYPE 
        SYNTAX  	BridgeId 
        ACCESS  	read-only 
        STATUS  	mandatory 
        DESCRIPTION 	"The unique Bridge Identifier of the Bridge 
                     	recorded as the Root in the Configuration BPDUs 
                     	transmitted by the Designated Bridge for the 
                     	segment to which the port is attached." 
        REFERENCE 	"IEEE 802.1D-1990: Section 4.5.5.4" 
        ::= { rcStgPortEntry 8 } 
 
rcStgPortDesignatedCost OBJECT-TYPE 
        SYNTAX  	INTEGER 
        ACCESS  	read-only 
        STATUS  	mandatory 
        DESCRIPTION 	"The path cost of the Designated Port of the 
                     	segment connected to this port.  This value is 
                     	compared to the Root Path Cost field in received 
                     	bridge PDUs." 
        REFERENCE 	"IEEE 802.1D-1990: Section 4.5.5.5" 
        ::= { rcStgPortEntry 9 } 
 
rcStgPortDesignatedBridge OBJECT-TYPE 
        SYNTAX  	BridgeId 
        ACCESS  	read-only 
        STATUS  	mandatory 
        DESCRIPTION 	"The Bridge Identifier of the bridge which this 
                     	port considers to be the Designated Bridge for 
                     	this port's segment." 
        REFERENCE 	"IEEE 802.1D-1990: Section 4.5.5.6" 
        ::= { rcStgPortEntry 10 } 
 
rcStgPortDesignatedPort OBJECT-TYPE 
        SYNTAX  	OCTET STRING (SIZE (2)) 
        ACCESS  	read-only 
        STATUS  	mandatory 
        DESCRIPTION 	"The Port Identifier of the port on the Designated 
                     	Bridge for this port's segment." 
        REFERENCE 	"IEEE 802.1D-1990: Section 4.5.5.7" 
        ::= { rcStgPortEntry 11 } 
 
rcStgPortForwardTransitions OBJECT-TYPE 
        SYNTAX  	Counter 
        ACCESS  	read-only 
        STATUS  	mandatory 
        DESCRIPTION 	"The number of times this port has transitioned 
                     	from the Learning state to the Forwarding state." 
        ::= { rcStgPortEntry 12 } 
 
rcStgPortInConfigBpdus OBJECT-TYPE 
        SYNTAX  	Counter 
        ACCESS  	read-only 
        STATUS  	mandatory 
        DESCRIPTION 	"The number of Config BPUDs received by 
                     	this port." 
        ::= { rcStgPortEntry 13 } 
 
rcStgPortInTcnBpdus OBJECT-TYPE 
        SYNTAX  	Counter 
        ACCESS  	read-only 
        STATUS  	mandatory 
        DESCRIPTION 	"The number of Topology Change Notification 
                     	BPUDs received by this port." 
        ::= { rcStgPortEntry 14 } 
 
rcStgPortInBadBpdus OBJECT-TYPE 
        SYNTAX  	Counter 
        ACCESS  	read-only 
        STATUS  	mandatory 
        DESCRIPTION 	"The number of Bad BPUDs received by this port." 
        ::= { rcStgPortEntry 15 } 
 
rcStgPortOutConfigBpdus OBJECT-TYPE 
        SYNTAX  	Counter 
        ACCESS  	read-only 
        STATUS  	mandatory 
        DESCRIPTION 	"The number of Config BPUDs transmitted by this port." 
        ::= { rcStgPortEntry 16 } 
 
 
rcStgPortOutTcnBpdus OBJECT-TYPE 
        SYNTAX  	Counter 
        ACCESS  	read-only 
        STATUS  	mandatory 
        DESCRIPTION 	"The number of Topology Change Notification 
                     	BPUDs transmitted by this port." 
        ::= { rcStgPortEntry 17 } 
 
rcStgPortRowStatus OBJECT-TYPE 
        SYNTAX  	RowStatus 
        ACCESS  	read-write 
        STATUS  	mandatory 
        DESCRIPTION 	"Row status." 
        ::= { rcStgPortEntry 18 } 
 
 
rcStgNotAllowedPorts OBJECT-TYPE  
        SYNTAX        PortSet   
        ACCESS        read-only 
        STATUS        mandatory  
        DESCRIPTION   "A bitfield used to identify which ports in  
                      the system that cannot be assigned to any STG 
                      (i.e., which ports are single routable ports).  
  
                      The bitfield is 32 octets long representing  
                      ports 0 to 255 (inclusive)."  
        ::= { rcStg 6 }  
 
 
-- rcBridge Group 
-- Forwarding Database for Transparent Bridges 
 
rcBridgeFdbTable OBJECT-TYPE 
	SYNTAX  	SEQUENCE OF RcBridgeFdbEntry 
	ACCESS  	not-accessible 
	STATUS  	mandatory 
	DESCRIPTION 	"This table is an replacement to the standard  
                     	dot1dTpFdbTable in rfc1493." 
	::= { rcBridge 1 } 
 
rcBridgeFdbEntry OBJECT-TYPE 
	SYNTAX  	RcBridgeFdbEntry 
	ACCESS  	not-accessible 
	STATUS  	mandatory 
        DESCRIPTION 	"Information about a specific unicast MAC address 
                     	for which the bridge has some forwarding information." 
	INDEX { rcBridgeFdbStatus, rcBridgeFdbAddress } 
	::= { rcBridgeFdbTable 1 } 
 
RcBridgeFdbEntry ::= 
	SEQUENCE { 
                  rcBridgeFdbStatus INTEGER, 
                  rcBridgeFdbAddress MacAddress, 
                  rcBridgeFdbPort InterfaceIndex, 
                  rcBridgeFdbMonitor TruthValue, 
                  rcBridgeFdbPriority INTEGER 
                 } 
  
rcBridgeFdbStatus OBJECT-TYPE 
        SYNTAX  	INTEGER { 
			      other(1), 
			      invalid(2), 
			      learned(3), 
			      self(4), 
			      mgmt(5) 
			  } 
        ACCESS 	 	read-only 
        STATUS 	 	mandatory 
        DESCRIPTION 	"This object indicates the status of this entry." 
        ::= { rcBridgeFdbEntry 1 } 
 
rcBridgeFdbAddress OBJECT-TYPE 
        SYNTAX  	MacAddress 
        ACCESS  	read-only 
        STATUS  	mandatory 
        DESCRIPTION 	"A unicast MAC address for which the bridge  
	             	has forwarding and/or filtering information." 
        REFERENCE "IEEE 802.1D-1990: Section 3.9.1, 3.9.2" 
        ::= { rcBridgeFdbEntry 2 } 
 
rcBridgeFdbPort OBJECT-TYPE 
        SYNTAX  	InterfaceIndex 
        ACCESS  	read-only 
        STATUS  	mandatory 
        DESCRIPTION 	"Either the value '0', or the port number of the 
      	             	port on which a frame having a source address 
		        equal to the value of the corresponding instance 
		        of rcBridgeFdbAddress has been seen.  A value of 
		        '0' indicates that the port number has not been 
		        learned but that the bridge does have some 
		        forwarding/filtering information about this 
		        address (e.g. in the dot1dStaticTable). 
		        Implementors are encouraged to assign the port 
		        value to this object whenever it is learned even 
		        for addresses for which the corresponding value of 
		        rcBridgeFdbStatus is not learned(3)." 
        ::= { rcBridgeFdbEntry 3 } 
 
rcBridgeFdbMonitor OBJECT-TYPE 
        SYNTAX  	TruthValue 
        ACCESS  	read-write 
        STATUS  	mandatory 
        DESCRIPTION 	"Used to indicate whether monitoring should be 
      	             	performed on this unicast MAC address.  If 
	             	monitoring is enabled, any packet received 
	             	with a matching destination MAC address 
	             	will be forwarded to the port configured to 
	             	receive monitor traffic." 
        ::= { rcBridgeFdbEntry 4 } 
 
rcBridgeFdbPriority OBJECT-TYPE 
        SYNTAX  	INTEGER { 
				low(0), 
		            	high(1) 
		        } 
        ACCESS  	read-write 
        STATUS  	mandatory 
        DESCRIPTION   	"Used to indicate the priority of the incoming 
                       	frames with this destination Mac Address." 
        DEFVAL         { low } 
        ::= { rcBridgeFdbEntry 5 } 
 
rcBridgeFdbTblSize OBJECT-TYPE   
        SYNTAX         	INTEGER   
        ACCESS         	read-only   
        STATUS        	mandatory   
        DESCRIPTION   	"Used to indicate the number of entries in  
                       	the bridge forwarding database table."     
        ::= { rcBridge 2 } 
 
 
-- The Static (Destination-Address) Database 
  
rcBridgeStaticTable OBJECT-TYPE 
	SYNTAX  	SEQUENCE OF RcBridgeStaticEntry 
	ACCESS  	not-accessible 
	STATUS  	mandatory 
	DESCRIPTION 	"This table is a proprietary replacement to the standard 
                     	dot1dStaticTable in rfc1493." 
	::= { rcBridge 3 } 
  
rcBridgeStaticEntry OBJECT-TYPE 
	SYNTAX  	RcBridgeStaticEntry 
	ACCESS  	not-accessible 
	STATUS  	mandatory 
   	DESCRIPTION 	"A table containing forwarding information about unicast 
                     	entries configured into the bridge by management. This 
                     	information is used by the transparent bridging function 
                     	in determining how to propagate a received frame." 
	INDEX   { rcBridgeStaticAddress, rcBridgeStaticPort } 
              ::= { rcBridgeStaticTable 1 } 
  
RcBridgeStaticEntry ::= 
SEQUENCE { 
	  rcBridgeStaticAddress  MacAddress, 
	  rcBridgeStaticPort     InterfaceIndex, 
	  rcBridgeStaticMonitor  TruthValue, 
	  rcBridgeStaticPriority INTEGER, 
	  rcBridgeStaticStatus   INTEGER 
	 } 
 
rcBridgeStaticAddress OBJECT-TYPE 
        SYNTAX  	MacAddress 
        ACCESS  	read-only 
        STATUS  	mandatory 
        DESCRIPTION 	"The MAC address of this entry."  
        ::= { rcBridgeStaticEntry 1 } 
 
rcBridgeStaticPort OBJECT-TYPE 
        SYNTAX  	InterfaceIndex 
        ACCESS  	read-only 
        STATUS  	mandatory 
        DESCRIPTION 	"Port on which the MAC address is found." 
        ::= { rcBridgeStaticEntry 2 } 
  
rcBridgeStaticMonitor OBJECT-TYPE 
        SYNTAX  	TruthValue  
        ACCESS  	read-write 
        STATUS  	mandatory 
        DESCRIPTION 	"Used to indicate whether monitoring should be 
		     	performed on incoming packets that match this 
		     	entry." 
        ::= { rcBridgeStaticEntry 3 } 
 
rcBridgeStaticPriority OBJECT-TYPE 
        SYNTAX  	INTEGER { 
           			low(0), 
			        high(1) 
		        } 
        ACCESS  	read-write 
        STATUS  	mandatory 
        DESCRIPTION 	"Used to indicate forwarding priority of incoming  
        	     	packets that match this entry."  
        DEFVAL         { low } 
        ::= { rcBridgeStaticEntry 4 } 
 
rcBridgeStaticStatus OBJECT-TYPE 
       	SYNTAX  	INTEGER { 
			    other(1), 
			    invalid(2), 
			    permanent(3), 
			    deleteOnReset(4), 
			    deleteOnTimeout(5) 
       		        } 
        ACCESS  	read-write 
        STATUS  	mandatory 
        DESCRIPTION   	"This object indicates the status of this  
                       	entry. The default value is permanent(3)." 
        ::= { rcBridgeStaticEntry 5 } 
 
rcBridgeStaticTblSize OBJECT-TYPE   
        SYNTAX        	INTEGER   
        ACCESS        	read-only   
        STATUS        	mandatory   
        DESCRIPTION   	"Used to indicate the number of entries in  
                       	the bridge static table."     
        ::= { rcBridge 4 } 
 
-- The filtering (Destination-Address) Database 
 
rcBridgeFilterTable OBJECT-TYPE 
	SYNTAX  	SEQUENCE OF RcBridgeFilterEntry 
	ACCESS  	not-accessible 
	STATUS  	mandatory 
	DESCRIPTION 	"This table is a proprietary replacement to the standard 
                     	dot1dStaticTable (Filtering information) in rfc1493." 
	::= { rcBridge 5 } 
  
rcBridgeFilterEntry OBJECT-TYPE 
	SYNTAX  	RcBridgeFilterEntry 
	ACCESS  	not-accessible 
	STATUS  	mandatory 
	DESCRIPTION 	"A table containing filtering information configured into 
                     	the bridge by management specifying a destination address 
                     	on a specific port and a set of incoming ports. Frames  
                     	received from one of the incoming ports and containing  
		     	the specific destination addresses are not allowed to be 
		     	forwarded." 
	INDEX   { rcBridgeFilterAddress, rcBridgeFilterPort } 
        ::= { rcBridgeFilterTable 1 } 
  
RcBridgeFilterEntry ::= 
        SEQUENCE { 
	     rcBridgeFilterAddress        MacAddress, 
	     rcBridgeFilterPort           InterfaceIndex, 
	     rcBridgeFilterNotAllowedFrom OCTET STRING, 
	     rcBridgeFilterStatus         INTEGER 
        } 
 
rcBridgeFilterAddress OBJECT-TYPE 
        SYNTAX  	MacAddress 
        ACCESS  	read-only 
        STATUS  	mandatory 
        DESCRIPTION 	"The MAC address of this entry.  This address is used 
		     	to match the destination address of incoming packets." 
        ::= { rcBridgeFilterEntry 1 } 
  
rcBridgeFilterPort OBJECT-TYPE 
        SYNTAX  	InterfaceIndex 
        ACCESS  	read-only 
        STATUS  	mandatory 
        DESCRIPTION 	"Port on which this MAC address is found." 
        ::= { rcBridgeFilterEntry 2 } 
  
rcBridgeFilterNotAllowedFrom OBJECT-TYPE 
        SYNTAX  	OCTET STRING (SIZE(32)) 
        ACCESS  	read-write 
        STATUS  	mandatory 
        DESCRIPTION 	"Used to indicate a set of ports.  Traffic arriving 
		     	on any of the specified ports is not forwarded to this  
                     	MAC address." 
        ::= { rcBridgeFilterEntry 3 } 
 
rcBridgeFilterStatus OBJECT-TYPE 
        SYNTAX  	INTEGER { 
		               other(1), 
       		               invalid(2), 
       		               permanent(3), 
       		               deleteOnReset(4), 
       		               deleteOnTimeout(5) 
       	         	} 
        ACCESS  	read-write 
        STATUS  	mandatory 
        DESCRIPTION 	"This object indicates the status of this  
                     	entry. The default value is permanent(3)." 
        ::= { rcBridgeFilterEntry 4 } 
 
rcBridgeFilterTblSize OBJECT-TYPE   
        SYNTAX        	INTEGER   
        ACCESS        	read-only   
        STATUS        	mandatory   
        DESCRIPTION   	"Used to indicate the number of entries in  
                       	the bridge filter table."     
        ::= { rcBridge 6 } 
 
 
-- rcBoot Group 
rcBootFlashSwVersion OBJECT-TYPE 
        SYNTAX        DisplayString 
        ACCESS        read-only 
        STATUS        obsolete 
        DESCRIPTION   "BootFlashSwVersion indicates the software 
                      version in the Flash." 
        ::= { rcBoot 1 }  
  
rcBootPcmciaSwVersion OBJECT-TYPE 
        SYNTAX        DisplayString 
        ACCESS        read-only 
        STATUS        obsolete 
        DESCRIPTION   "BootPcmciaSwVersion indicate the software 
                      version in the Pcmcia card." 
        ::= { rcBoot 2 }  
  
 
rcBootLastBootSource OBJECT-TYPE 
        SYNTAX        DisplayString 
        ACCESS        read-only 
        STATUS        obsolete 
        DESCRIPTION   "Indicates the boot source of the last 
                      the system boot." 
        ::= { rcBoot 3 }  
  
rcBootPrimary OBJECT-TYPE 
        SYNTAX          INTEGER { 
                           flash(1), 
                           pcmcia(2), 
                           net(3), 
                           skip(4) 
                        } 
        ACCESS        	read-write 
        STATUS        	obsolete 
        DESCRIPTION   	"BootPrimary is indicator for the 
                     	primary source to boot the system." 
	DEFVAL 		{ flash } 
        ::= { rcBoot 4 }  
  
rcBootSecondary OBJECT-TYPE 
        SYNTAX          INTEGER { 
                           flash(1), 
                           pcmcia(2), 
                           net(3), 
                           skip(4) 
                        } 
        ACCESS        	read-write 
        STATUS        	obsolete 
        DESCRIPTION   	"BootSecondary indicates the second choice 
                        of the boot source." 
	DEFVAL 		{ pcmcia } 
        ::= { rcBoot 5 }  
  
rcBootTertiary OBJECT-TYPE 
        SYNTAX          INTEGER { 
                           flash(1), 
                           pcmcia(2), 
                           net(3), 
                           skip(4) 
                        } 
        ACCESS        	read-write 
        STATUS        	obsolete 
        DESCRIPTION   	"BootTertiary indicates the third choice  
                        of boot source." 
	DEFVAL 		{ net } 
        ::= { rcBoot 6 }  
  
 
-- rcDevice Group 
rcDeviceLastBootSource OBJECT-TYPE 
        SYNTAX          DisplayString 
        ACCESS          read-only 
        STATUS          mandatory 
        DESCRIPTION     "Used to indicate the source of the software 
                         image the system was last booted with." 
        ::= { rcDevice 1 }  
  
rcDevicePrimarySource OBJECT-TYPE 
        SYNTAX          INTEGER { 
                           flash(1), 
                           pcmcia(2), 
                           net(3), 
                           skip(4) 
                        } 
        ACCESS        	read-write 
        STATUS        	mandatory 
        DESCRIPTION   	"Used to indicate the primary choice to get 
                         a system software image." 
        ::= { rcDevice 2 }  
  
rcDevicePrimarySourceFileName OBJECT-TYPE 
        SYNTAX          DisplayString (SIZE(0..31)) 
        ACCESS          read-write 
        STATUS          mandatory 
        DESCRIPTION     "Used to indicate a file number, if applicable." 
        ::= { rcDevice 3 }  
 
rcDeviceSecondarySource OBJECT-TYPE 
        SYNTAX          INTEGER { 
                           flash(1), 
                           pcmcia(2), 
                           net(3), 
                           skip(4) 
                        } 
        ACCESS        	read-write 
        STATUS        	mandatory 
        DESCRIPTION   	"Used to indicate the secondary choice to get 
                         a system software image." 
        ::= { rcDevice 4 }  
  
rcDeviceSecondarySourceFileName OBJECT-TYPE 
        SYNTAX          DisplayString (SIZE(0..31)) 
        ACCESS          read-write 
        STATUS          mandatory 
        DESCRIPTION     "Used to indicate a file name, if applicable." 
        ::= { rcDevice 5 }  
 
rcDeviceTertiarySource OBJECT-TYPE 
        SYNTAX          INTEGER { 
                           flash(1), 
                           pcmcia(2), 
                           net(3), 
                           skip(4) 
                        } 
        ACCESS        	read-write 
        STATUS        	mandatory 
        DESCRIPTION   	"Used to indicate the tertiary choice to get 
                         a system software image." 
        ::= { rcDevice 6 }  
  
rcDeviceTertiarySourceFileName OBJECT-TYPE 
        SYNTAX          DisplayString (SIZE(0..31)) 
        ACCESS          read-write 
        STATUS          mandatory 
        DESCRIPTION     "Used to indicate a file name, if applicable." 
        ::= { rcDevice 7 }  
 
rcDeviceConfigSource OBJECT-TYPE 
        SYNTAX          INTEGER { 
                           flash(1), 
                           pcmcia(2), 
			   nvram(5) 
                        } 
        ACCESS        	read-write 
        STATUS        	mandatory 
        DESCRIPTION   	"Used to indicate the location to get a system  
			configuration file during system boot." 
        ::= { rcDevice 8 }  
  
rcDeviceConfigSourceFileName OBJECT-TYPE 
        SYNTAX          DisplayString (SIZE(0..31)) 
        ACCESS          read-write 
        STATUS          mandatory 
        DESCRIPTION     "Used to indicate a file name, if applicable." 
        ::= { rcDevice 9 }  
 
rcDeviceFlashBytesUsed OBJECT-TYPE 
        SYNTAX          INTEGER 
        ACCESS          read-only 
        STATUS          mandatory 
        DESCRIPTION     "Used to indicate the number of bytes used in the 
                         system's configuration flash device." 
        ::= { rcDevice 10 }  
 
rcDeviceFlashBytesFree OBJECT-TYPE 
        SYNTAX          INTEGER 
        ACCESS          read-only 
        STATUS          mandatory 
        DESCRIPTION     "Used to indicate the number of bytes available in 
                         the system's configuration flash device." 
        ::= { rcDevice 11 }  
 
rcDevicePcmciaBytesUsed OBJECT-TYPE 
        SYNTAX          INTEGER 
        ACCESS          read-only 
        STATUS          mandatory 
        DESCRIPTION     "Used to indicate the number of bytes used in the 
                         system's PCMCIA device." 
        ::= { rcDevice 12 }  
 
rcDevicePcmciaBytesFree OBJECT-TYPE 
        SYNTAX          INTEGER 
        ACCESS          read-only 
        STATUS          mandatory 
        DESCRIPTION     "Used to indicate the number of bytes available in  
                         the system's PCMCIA device." 
        ::= { rcDevice 13 }  
 
rcDeviceAction OBJECT-TYPE 
        SYNTAX          INTEGER { 
			    none(1), 
                            squeezeFlash(2), 
                            squeezePcmcia(3), 
                            formatFlash(4), 
                            formatPcmcia(5), 
                            recoverFlash(6),  
                            recoverPcmcia(7)  
                        } 
        ACCESS        	read-write 
        STATUS        	mandatory 
        DESCRIPTION   	"Used to specify a particular action to perform on 
                         one of the system's device." 
        ::= { rcDevice 14 }  
  
rcDeviceResult OBJECT-TYPE 
        SYNTAX          INTEGER { 
                            none(1), 
                            inProgress(2), 
                            success(3), 
                            fail(4) 
                        } 
        ACCESS        	read-only 
        STATUS        	mandatory 
        DESCRIPTION   	"Used to indicate the result of the last action 
                         performed on one of the system's device." 
        ::= { rcDevice 15 }  
  
rcDeviceFlashNumFiles OBJECT-TYPE 
        SYNTAX          INTEGER (0..128) 
        ACCESS          read-only 
        STATUS          mandatory 
        DESCRIPTION     "Used to indicate the number of files available in 
                         the system's configuration flash device." 
        ::= { rcDevice 16 } 
  
rcDevicePcmciaNumFiles OBJECT-TYPE 
        SYNTAX          INTEGER (0..128) 
        ACCESS          read-only 
        STATUS          mandatory 
        DESCRIPTION     "Used to indicate the number of files available in 
                         the system's PCMCIA device." 
        ::= { rcDevice 17 } 
  
 
-- The Device Flash Table 
 
rcDeviceFlashTable OBJECT-TYPE 
	SYNTAX  	SEQUENCE OF RcDeviceFlashEntry 
	ACCESS  	not-accessible 
	STATUS  	mandatory 
	DESCRIPTION 	"Flash table." 
	::= { rcDevice 25 } 
  
rcDeviceFlashEntry OBJECT-TYPE 
	SYNTAX  	RcDeviceFlashEntry 
	ACCESS  	not-accessible 
	STATUS  	mandatory 
	DESCRIPTION 	"An entry in the system's flash table." 
	INDEX   { rcDeviceFlashFileNum } 
        ::= { rcDeviceFlashTable 1 } 
  
RcDeviceFlashEntry ::= 
        SEQUENCE { 
	     rcDeviceFlashFileNum     INTEGER, 
	     rcDeviceFlashFileName    DisplayString, 
	     rcDeviceFlashFileVersion DisplayString, 
	     rcDeviceFlashFileType    INTEGER, 
	     rcDeviceFlashFileMode    INTEGER, 
	     rcDeviceFlashFileSize    INTEGER, 
	     rcDeviceFlashFileCrc     INTEGER, 
	     rcDeviceFlashFileStatus  INTEGER, 
	     rcDeviceFlashRowStatus   RowStatus 
        } 
 
rcDeviceFlashFileNum OBJECT-TYPE 
        SYNTAX  	INTEGER (0..128) 
        ACCESS  	read-only 
        STATUS  	mandatory 
        DESCRIPTION 	"Used to indicate a particular file in flash." 
        ::= { rcDeviceFlashEntry 1 } 
  
rcDeviceFlashFileName OBJECT-TYPE 
        SYNTAX  	DisplayString 
        ACCESS  	read-only 
        STATUS  	mandatory 
        DESCRIPTION 	"Used to indicate a flash file's name." 
        ::= { rcDeviceFlashEntry 2 } 
  
rcDeviceFlashFileVersion OBJECT-TYPE 
        SYNTAX  	DisplayString 
        ACCESS  	read-only 
        STATUS  	mandatory 
        DESCRIPTION 	"Used to indicate the flash file's version." 
        ::= { rcDeviceFlashEntry 3 } 
  
rcDeviceFlashFileType OBJECT-TYPE 
        SYNTAX  	INTEGER { 
                           config(1), 
                           log(2), 
                           trace(3), 
                           executable(4) 
                        } 
        ACCESS  	read-only 
        STATUS  	mandatory 
        DESCRIPTION     "Used to indicate the flash file's type." 
        ::= { rcDeviceFlashEntry 4 } 
  
rcDeviceFlashFileMode OBJECT-TYPE 
        SYNTAX  	INTEGER { 
                           compressed(1), 
                           uncompressed(2) 
                        } 
        ACCESS  	read-only 
        STATUS  	mandatory 
        DESCRIPTION     "Used to indicate the flash file's mode." 
        ::= { rcDeviceFlashEntry 5 } 
  
rcDeviceFlashFileSize OBJECT-TYPE 
        SYNTAX  	INTEGER 
        ACCESS  	read-only 
        STATUS  	mandatory 
        DESCRIPTION     "Used to indicate the flash file's size." 
        ::= { rcDeviceFlashEntry 6 } 
  
rcDeviceFlashFileCrc OBJECT-TYPE 
        SYNTAX  	INTEGER 
        ACCESS  	read-only 
        STATUS  	mandatory 
        DESCRIPTION     "Used to indicate the flash file's CRC." 
        ::= { rcDeviceFlashEntry 7 } 
  
rcDeviceFlashFileStatus OBJECT-TYPE 
        SYNTAX  	INTEGER { 
                           active(1), 
                           deleted(2) 
                        } 
        ACCESS  	read-only 
        STATUS  	mandatory 
        DESCRIPTION     "Used to indicate the flash file's status. 
                         A file that has been marked for deletion, but   
                         who's space has not been reclaimed yet is marked 
                         as 'deleted'." 
        ::= { rcDeviceFlashEntry 8 } 
  
rcDeviceFlashRowStatus OBJECT-TYPE 
        SYNTAX  	RowStatus 
        ACCESS  	read-write 
        STATUS  	mandatory 
        DESCRIPTION 	"Row status." 
        ::= { rcDeviceFlashEntry 9 } 
 
 
-- The Device Pcmcia Table 
 
rcDevicePcmciaTable OBJECT-TYPE 
	SYNTAX  	SEQUENCE OF RcDevicePcmciaEntry 
	ACCESS  	not-accessible 
	STATUS  	mandatory 
	DESCRIPTION 	"PCMCIA table." 
	::= { rcDevice 26 } 
  
rcDevicePcmciaEntry OBJECT-TYPE 
	SYNTAX  	RcDevicePcmciaEntry 
	ACCESS  	not-accessible 
	STATUS  	mandatory 
        DESCRIPTION     "An entry in the system's PCMCIA table." 
	INDEX   { rcDevicePcmciaFileNum } 
        ::= { rcDevicePcmciaTable 1 } 
  
RcDevicePcmciaEntry ::= 
        SEQUENCE { 
	     rcDevicePcmciaFileNum     INTEGER, 
	     rcDevicePcmciaFileName    DisplayString, 
	     rcDevicePcmciaFileVersion DisplayString, 
	     rcDevicePcmciaFileType    INTEGER, 
	     rcDevicePcmciaFileMode     INTEGER, 
	     rcDevicePcmciaFileSize    INTEGER, 
	     rcDevicePcmciaFileCrc     INTEGER, 
	     rcDevicePcmciaFileStatus  INTEGER, 
	     rcDevicePcmciaRowStatus   RowStatus 
        } 
 
rcDevicePcmciaFileNum OBJECT-TYPE 
        SYNTAX  	INTEGER (0..128) 
        ACCESS  	read-only 
        STATUS  	mandatory 
        DESCRIPTION     "Used to indicate a particular file in PCMCIA." 
        ::= { rcDevicePcmciaEntry 1 } 
  
rcDevicePcmciaFileName OBJECT-TYPE 
        SYNTAX  	DisplayString 
        ACCESS  	read-only 
        STATUS  	mandatory 
        DESCRIPTION     "Used to indicate the PCMCIA file's name." 
        ::= { rcDevicePcmciaEntry 2 } 
  
rcDevicePcmciaFileVersion OBJECT-TYPE 
        SYNTAX  	DisplayString 
        ACCESS  	read-only 
        STATUS  	mandatory 
        DESCRIPTION     "Used to indicate the PCMCIA file's version." 
        ::= { rcDevicePcmciaEntry 3 } 
  
rcDevicePcmciaFileType OBJECT-TYPE 
        SYNTAX  	INTEGER { 
                           config(1), 
                           log(2), 
                           trace(3), 
                           executable(4) 
                        } 
        ACCESS  	read-only 
        STATUS  	mandatory 
        DESCRIPTION     "Used to indicate the PCMCIA file's type." 
        ::= { rcDevicePcmciaEntry 4 } 
  
rcDevicePcmciaFileMode OBJECT-TYPE 
        SYNTAX  	INTEGER { 
                           compressed(1), 
                           uncompressed(2) 
                        } 
        ACCESS  	read-only 
        STATUS  	mandatory 
        DESCRIPTION     "Used to indicate a particular file in mode." 
        ::= { rcDevicePcmciaEntry 5 } 
  
rcDevicePcmciaFileSize OBJECT-TYPE 
        SYNTAX  	INTEGER 
        ACCESS  	read-only 
        STATUS  	mandatory 
        DESCRIPTION     "Used to indicate the PCMCIA file's size." 
        ::= { rcDevicePcmciaEntry 6 } 
  
rcDevicePcmciaFileCrc OBJECT-TYPE 
        SYNTAX  	INTEGER 
        ACCESS  	read-only 
        STATUS  	mandatory 
        DESCRIPTION     "Used to indicate the PCMCIA file's CRC." 
        ::= { rcDevicePcmciaEntry 7 } 
  
rcDevicePcmciaFileStatus OBJECT-TYPE 
        SYNTAX  	INTEGER { 
                           active(1), 
                           deleted(2) 
                        } 
        ACCESS  	read-only 
        STATUS  	mandatory 
        DESCRIPTION     "Used to indicate the PCMCIA file's status. 
                         A file that has been marked for deletion, but 
                         who's space has not been reclaimed yet is marked 
                         as 'deleted'." 
        ::= { rcDevicePcmciaEntry 8 } 
  
rcDevicePcmciaRowStatus OBJECT-TYPE 
        SYNTAX  	RowStatus 
        ACCESS  	read-write 
        STATUS  	mandatory 
        DESCRIPTION 	"Row status." 
        ::= { rcDevicePcmciaEntry 9 } 
 
 
-- Multi-Link Trunking Table 
 
rcMltNumMlts OBJECT-TYPE 
        SYNTAX        	INTEGER 
        ACCESS        	read-only 
        STATUS        	mandatory 
        DESCRIPTION   	"The number of MLTs currently defined in the switch." 
        ::= { rcMlt 1 } 
 
rcMltPotentialMembers OBJECT-TYPE 
        SYNTAX        	PortSet 
        ACCESS        	read-only 
        STATUS        	mandatory 
        DESCRIPTION   	"The set of ports that are not members of any MLT." 
        ::= { rcMlt 2 } 
 
rcMltTable OBJECT-TYPE 
        SYNTAX        	SEQUENCE OF RcMltEntry 
        ACCESS        	not-accessible 
        STATUS        	mandatory 
        DESCRIPTION   	"A list of Multi-Link Trunk entries. The number of  
                      	entries is given by rcMltNumMlts." 
        ::= { rcMlt 10 } 
 
rcMltEntry OBJECT-TYPE 
        SYNTAX        	RcMltEntry 
        ACCESS        	not-accessible 
        STATUS        	mandatory 
        DESCRIPTION   	"Entry containing configuration information for a  
                      	particular Multi-Link Trunk." 
        INDEX         	{ rcMltId } 
        ::= { rcMltTable 1 } 
 
RcMltEntry ::= SEQUENCE { 
                rcMltId	                    INTEGER, 
                rcMltName                   DisplayString, 
                rcMltPortMembers            PortSet, 
		rcMltPortType               INTEGER,	 
		rcMltNumVlanIds             INTEGER, 
		rcMltVlanIds                IdList, 
                rcMltRowStatus              RowStatus, 
		rcMltEnable                 TruthValue, 
		rcMltLoadBalance            TruthValue, 
		rcMltDistributionAlgorithm  INTEGER, 
		rcMltIfIndex		    InterfaceIndex 
        } 
 
rcMltId OBJECT-TYPE 
        SYNTAX        	INTEGER (1..8) 
        ACCESS        	read-only 
        STATUS        	mandatory 
        DESCRIPTION   	"A value that uniquely identifies the Multi-Link  
                      	Trunk associated with this entry." 
        ::= { rcMltEntry 1 } 
 
rcMltName OBJECT-TYPE 
        SYNTAX        	DisplayString (SIZE (0..20)) 
        ACCESS        	read-write 
        STATUS        	mandatory 
        DESCRIPTION   	"An administratively-assigned name for this MLT." 
        ::= { rcMltEntry 2 } 
 
rcMltPortMembers OBJECT-TYPE 
        SYNTAX        	PortSet 
        ACCESS        	read-write 
        STATUS        	mandatory 
        DESCRIPTION   	"The set of ports that are members of this MLT."  
        ::= { rcMltEntry 3 } 
 
rcMltPortType OBJECT-TYPE 
        SYNTAX        	INTEGER { 
                        	access(1),     -- access port type 
                         	trunk(2)       -- trunk port type 
                      	} 
        ACCESS        	read-write 
        STATUS        	mandatory 
        DESCRIPTION   	"The type of MLT port: access(1) or trunk(2)." 
		DEFVAL 			{ access } 
        ::= { rcMltEntry 4 } 
  
rcMltNumVlanIds OBJECT-TYPE 
        SYNTAX        	INTEGER 
        ACCESS        	read-only 
        STATUS        	mandatory 
        DESCRIPTION   	"Used to indicate the number of VLAN IDs that 
                      	are stored in the rcMltVlanIds variable." 
        ::= { rcMltEntry 5 } 
 
rcMltVlanIds OBJECT-TYPE 
        SYNTAX        	IdList (SIZE (250)) 
        ACCESS        	read-write 
        STATUS        	mandatory 
        DESCRIPTION   	"An array used to identify which VLANs this MLT  
                      	is associated with.  Each VLAN ID is stored as a  
		      	two octet value. The first octet in the pair holds 
                      	bits 15-8 of the VLAN ID, while the second octet 
                      	holds bits 7-0 of the VLAN ID." 
        ::= { rcMltEntry 6 } 
 
rcMltRowStatus OBJECT-TYPE 
        SYNTAX        	RowStatus 
        ACCESS        	read-write 
        STATUS        	mandatory 
        DESCRIPTION   	"Used to create/delete entries in the rcMltTable." 
        ::= { rcMltEntry 7 } 
 
rcMltEnable OBJECT-TYPE 
        SYNTAX        	TruthValue 
        ACCESS        	read-write 
        STATUS        	mandatory 
        DESCRIPTION   	"Enable the entry." 
		DEFVAL 			{ true } 
        ::= { rcMltEntry 8 } 
 
rcMltLoadBalance OBJECT-TYPE 
        SYNTAX        	TruthValue 
        ACCESS        	read-write 
        STATUS        	mandatory 
        DESCRIPTION   	"Perform load balance?" 
		DEFVAL			{ false } 
        ::= { rcMltEntry 9 } 
 
rcMltDistributionAlgorithm OBJECT-TYPE 
        SYNTAX        	INTEGER { 
                        	none(1) 
                      	} 
        ACCESS        	read-write 
        STATUS        	mandatory 
        DESCRIPTION   	"none(1), ...  It will be fill later" 
		DEFVAL			{ none } 
        ::= { rcMltEntry 10 } 
 
rcMltIfIndex OBJECT-TYPE 
        SYNTAX        InterfaceIndex 
        ACCESS        read-only 
        STATUS        mandatory 
        DESCRIPTION   "Used to indicate the 'logical' ifIndex assigned to 
                      this MLT." 
        ::= { rcMltEntry 11 } 
 
 
-- rcWeb related information 
 
rcWebEnableServer OBJECT-TYPE 
        SYNTAX        TruthValue 
        ACCESS        read-write 
        STATUS        mandatory 
        DESCRIPTION   "Control whether the web server should be enabled. 
		      Setting this variable to true will make the server 
		      operational.  Setting this variable to false will 
		      disable server." 
        DEFVAL        { false } 
        ::= { rcWeb 1 } 
 
rcWebRWAUserName OBJECT-TYPE 
        SYNTAX        DisplayString (SIZE (1..20)) 
        ACCESS        read-write 
        STATUS        mandatory 
        DESCRIPTION   "User name for the read-write-all web-server account." 
        ::= { rcWeb 2 } 
 
rcWebRWAPassword OBJECT-TYPE 
        SYNTAX        DisplayString (SIZE (0..20)) 
        ACCESS        read-write 
        STATUS        mandatory 
        DESCRIPTION   "Password for the read-write-all web-server account." 
        ::= { rcWeb 3 } 
 
rcWebRWUserName OBJECT-TYPE 
        SYNTAX        DisplayString (SIZE (1..20)) 
        ACCESS        read-write 
        STATUS        mandatory 
        DESCRIPTION   "User name for the read-write web-server account." 
        ::= { rcWeb 4 } 
  
rcWebRWPassword OBJECT-TYPE  
        SYNTAX        DisplayString (SIZE (0..20))  
        ACCESS        read-write  
        STATUS        mandatory  
        DESCRIPTION   "Password for the read-write web-server account."  
        ::= { rcWeb 5 }  
 
rcWebROUserName OBJECT-TYPE 
        SYNTAX        DisplayString (SIZE (1..20)) 
        ACCESS        read-write 
        STATUS        mandatory 
        DESCRIPTION   "User name for the read-only web-server account." 
        ::= { rcWeb 6 } 
  
rcWebROPassword OBJECT-TYPE  
        SYNTAX        DisplayString (SIZE (0..20)) 
        ACCESS        read-write  
        STATUS        mandatory  
        DESCRIPTION   "Password for the read-only web-server account."  
        ::= { rcWeb 7 }  
 
rcWebLastChange OBJECT-TYPE  
        SYNTAX        TimeTicks  
        ACCESS        read-only  
        STATUS        mandatory  
        DESCRIPTION   "Last web-browser initiated configuration 
                      change since sysUpTime." 
        ::= { rcWeb 8 } 
  
rcWebNumHits OBJECT-TYPE 
        SYNTAX        INTEGER 
        ACCESS        read-only 
        STATUS        mandatory 
        DESCRIPTION   "Number of hits to the web-server" 
	::= { rcWeb 9 }  
 
rcWebNumAccessChecks OBJECT-TYPE 
        SYNTAX        INTEGER 
        ACCESS        read-only 
        STATUS        mandatory 
        DESCRIPTION   "Number of access checks performed by the web-server" 
        ::= { rcWeb 10 } 
 
rcWebNumAccessBlocks OBJECT-TYPE 
        SYNTAX        INTEGER 
        ACCESS        read-only 
        STATUS        mandatory 
        DESCRIPTION   "Number of accesses blocked by the web-server" 
        ::= { rcWeb 11 } 
 
rcWebNumRxErrors OBJECT-TYPE  
        SYNTAX        INTEGER  
        ACCESS        read-only  
        STATUS        mandatory  
        DESCRIPTION   "Number of receive errors encountered by the 
web-server"  
        ::= { rcWeb 12 } 
 
rcWebNumTxErrors OBJECT-TYPE  
        SYNTAX        INTEGER  
        ACCESS        read-only  
        STATUS        mandatory  
        DESCRIPTION   "Number of transmit errors encountered by the 
web-server"  
        ::= { rcWeb 13 } 
 
rcWebNumSetRequest OBJECT-TYPE  
        SYNTAX        INTEGER  
        ACCESS        read-only  
        STATUS        mandatory  
        DESCRIPTION   "Number of set-request to the web-server"  
        ::= { rcWeb 14 } 
 
 
-- rcCli related information 
 
rcCliRWAUserName OBJECT-TYPE 
        SYNTAX        DisplayString (SIZE (1..20)) 
        ACCESS        read-write 
        STATUS        mandatory 
        DESCRIPTION   "User name for the read-write-all CLI account." 
        ::= { rcCli 1 } 
 
rcCliRWAPassword OBJECT-TYPE 
        SYNTAX        DisplayString (SIZE (0..20)) 
        ACCESS        read-write 
        STATUS        mandatory 
        DESCRIPTION   "Password for the read-write-all CLI account." 
        ::= { rcCli 2 } 
 
rcCliRWUserName OBJECT-TYPE 
        SYNTAX        DisplayString (SIZE (1..20)) 
        ACCESS        read-write 
        STATUS        mandatory 
        DESCRIPTION   "User name for the read-write CLI account." 
        ::= { rcCli 3 } 
  
rcCliRWPassword OBJECT-TYPE  
        SYNTAX        DisplayString (SIZE (0..20))  
        ACCESS        read-write  
        STATUS        mandatory  
        DESCRIPTION   "Password for the read-write CLI account."  
        ::= { rcCli 4 }  
 
rcCliRWL3UserName OBJECT-TYPE 
        SYNTAX        DisplayString (SIZE (1..20)) 
        ACCESS        read-write 
        STATUS        mandatory 
        DESCRIPTION   "User name for the read-write layer-3 CLI account." 
        ::= { rcCli 5 } 
 
rcCliRWL3Password OBJECT-TYPE 
        SYNTAX        DisplayString (SIZE (0..20)) 
        ACCESS        read-write 
        STATUS        mandatory 
        DESCRIPTION   "Password for the read-write layer-3 CLI account." 
        ::= { rcCli 6 } 
 
rcCliRWL2UserName OBJECT-TYPE 
        SYNTAX        DisplayString (SIZE (1..20)) 
        ACCESS        read-write 
        STATUS        mandatory 
        DESCRIPTION   "User name for the read-write layer-2 CLI account."    
        ::= { rcCli 7 }   
  
rcCliRWL2Password OBJECT-TYPE 
        SYNTAX        DisplayString (SIZE (0..20)) 
        ACCESS        read-write 
        STATUS        mandatory 
        DESCRIPTION   "Password for the read-write layer-2 CLI account." 
        ::= { rcCli 8 } 
 
rcCliROUserName OBJECT-TYPE 
        SYNTAX        DisplayString (SIZE (1..20)) 
        ACCESS        read-write 
        STATUS        mandatory 
        DESCRIPTION   "User name for the read-only CLI account." 
        ::= { rcCli 9 } 
  
rcCliROPassword OBJECT-TYPE  
        SYNTAX        DisplayString (SIZE (0..20)) 
        ACCESS        read-write  
        STATUS        mandatory  
        DESCRIPTION   "Password for the read-only CLI account."  
        ::= { rcCli 10 }  
 
rcCliMaxTelnetSessions OBJECT-TYPE  
        SYNTAX        INTEGER (0..8) 
        ACCESS        read-write 
        STATUS        mandatory 
        DESCRIPTION   "Used to indicate the maximum number of telnet 
		      sessions the system will support." 
	DEFVAL	      { 8 } 
	::= { rcCli 11 }  
 
rcCliMaxRloginSessions OBJECT-TYPE 
        SYNTAX        INTEGER (0..8) 
        ACCESS        read-write   
        STATUS        mandatory 
        DESCRIPTION   "Used to indicate the maximum number of rlogin 
                      sessions the system will support." 
	DEFVAL	      { 8 } 
        ::= { rcCli 12 } 
 
rcCliTimeout OBJECT-TYPE 
        SYNTAX        INTEGER (30..65535) 
        ACCESS        read-write 
        STATUS        mandatory 
        DESCRIPTION   "Used to indicate the amount of idle time, in 
     		      seconds to wait before timing out telnet and  
		      rlogin sessions." 
	DEFVAL        { 900 } 
        ::= { rcCli 13 } 
 
rcCliNumAccessViolations OBJECT-TYPE 
        SYNTAX        INTEGER 
        ACCESS        read-only 
        STATUS        mandatory 
        DESCRIPTION   "Used to indicate the number of CLI access 
		      violations detected by the system." 
        ::= { rcCli 14 } 
 
 
-- Error Group 
  
rcErrorLevel OBJECT-TYPE 
        SYNTAX        INTEGER 
        ACCESS        read-only 
        STATUS        mandatory 
        DESCRIPTION   "Error level indicator for the last error 
                      reported in the system.  The meaning of 
		      this value are : 
 
			0 = Informative Information 
			1 = Warning Condition 
			2 = Error Condition 
			3 = Manufacturing Information 
			4 = Fatal Condition 
		      " 
        ::= { rcError 1 }  
  
rcErrorCode OBJECT-TYPE 
        SYNTAX        INTEGER 
        ACCESS        read-only 
        STATUS        mandatory 
        DESCRIPTION   "Error code indicator for the last error 
                      reported in the system.  This is an encoded 
		      value that identifies the software module 
		      that generated the error message as well as 
                      a specific error condition within that module. 
		      This value is transparent to the user.  This 
		      value is intended to help Accelar support and 
		      development staff to isolate system problems." 
        ::= { rcError 2 } 
 
rcErrorText OBJECT-TYPE 
        SYNTAX        DisplayString 
        ACCESS        read-only 
        STATUS        mandatory 
        DESCRIPTION   "Error string of the last error reported  
                      in the system." 
        ::= { rcError 3 } 
 
rcErrorReturnCode OBJECT-TYPE 
        SYNTAX        INTEGER { 
			 none(100), 
			 resourceNotAvailable(101), 
			 operationNotAllowed(102), 
			 operationInProgress(103), 
			 invalidPortNumber(104), 
			 invalidSubnetAddress(105), 
			 invalidSubnetMask(106), 
			 invalidVlanId(107), 
			 invalidVlanName(108), 
			 invalidVlanType(109), 
			 invalidStgId(110), 
			 invalidProtocolId(111), 
			 invalidPortMembers(112), 
			 invalidStaticMembers(113), 
			 invalidNotAllowedMembers(114), 
			 destinationNotReachable(115), 
			 tableIsFull(116), 
			 nondualConnectorGigPort(117), 
			 testIdNotPresent(118), 
			 invalidTestId(119), 
			 invalidStatusChange(120), 
			 invalidCpuCard(121), 
			 invalidSrcPortChoice(122), 
			 dstPortUnspecified(123), 
			 srcPortOneUnspecified(124), 
			 srcPortTwoUnspecified(125), 
			 notSupported(126), 
			 userNameIsNonUnique(127), 
			 invalidName(128), 
                         cannotModifyThisField(130), 
                         invalidUserPasswordLength(131), 
                         thisUsernameExists(132), 
                         invalidIpAddress(133), 
                         invalidMacAddress(134), 
                         nosuchEntry(135), 
			 anotherLoopBackTestAlreadyRunning(136), 
			 protocolIdNotRoutable(137), 
			 autoNegotiateIsOn(138), 
			 noActionSpecified(139), 
			 invalidActionSpecified(140), 
                         cannotModifyAutoNegotiateIsOn(141), 
                         cannotModifyAutoPortIsFiber(142), 
                         autoNegotiationNotSupported(143), 
                         cannotSetAdminSpeed(144), 
                         cannotSetAdminDuplex(145), 
                         ospfRtrDeadIntIsnotMultOfHelloInt(146), 
                         ospfRtrDeadIntLessThan4TimesHelloInt(147), 
                         notUsed1(148), 
                         ospfBadAuthValue(149), 
                         ospfEnabled(150), 
                         ospfAreaNotFound(151), 
                         ospfBackboneArea(152), 
                         notInTestMode(153), 
                         ospfInvalidAreaRangeMask(154), 
                         ospfDuplicateEntry(155), 
                         ospfRangeNotAllocated(156), 
                         ospfAreaRangeNotFound(157), 
                         testRunning(158), 
			 nvramLimitExceeded(159), 
			 flowAlreadyExist(160), 
			 flowNotFound(161), 
		 	 duplicateIpAddress(163), 
		 	 conflictingIpAddress(164), 
			 invalidRouteCost(165), 
			 invalidNextHop(166), 
			 duplicateRoute(167), 
			 cannotFindRoute(168), 
			 cannotDeleteLocalRoute(169), 
			 badDhcpMinSec(170), 
			 badDhcpMaxHop(171), 
			 badDhcpMode(172), 
			 badAgentAddress(173), 
			 dhcpNotEnabled(174), 
			 dhcpForwardNotFound(175), 
			 dhcpDuplicateForward(176), 
			 dhcpMaxForward(177), 
			 dhcpBadEnable(178), 
			 invalidDeviceFileNumber(179), 
			 notExecutableDeviceFile(180), 
			 deletedDeviceFile(181), 
			 pcmciaNotPresent(182), 
			 pcmciaWriteProtected(183), 
			 discontiguousSubnetMask(184), 
			 invalidOspfMetric(185), 
			 ospfHostRouteNotFound(186), 
			 invalidMltId(187), 
			 invalidMltName(188), 
			 onlyOnePortInMlt(189), 
			 moreThan4PortsInMlt(190), 
			 portsInDifferentQuid(191), 
			 portAlreadyInAnotherMlt(192), 
			 invalidVlan(193), 
			 nonExistIpMcastAddriess(194), 
			 invalidIpMulticastAddress(195), 
			 portIsLocked(196), 
			 accessRestriction(197), 
                         invalidDeviceFileLength(198), 
                         duplicateAccessPolicyId(199), 
                         noDesiredAccessPolicyItem(200), 
                         ipfFilterNonExist(201), 
                         ipfInvalidVlanPriority(202), 
                         ipfInvalidDestinationAddress(203), 
                         ipfInvalidSourceAddress(204), 
                         ipfFilterDuplicate(205), 
                         ipfGlobalListDuplicate(206), 
                         ipfGlobalListNonExist(207), 
                         ipfBaseListDuplicate(208), 
                         ipfBaseListNonExist(209), 
                         ipfPortDuplicate(210), 
                         ipfPortNonExist(211), 
                         ipfListNonExist(212), 
                         snmpSnoopDisabled(213), 
                         invalidHostIpAddress(214), 
                         snoopStaticGroupExist(215), 
			 ripAnnouncePolicyNotFound(216), 
			 duplicateRipAnnouncePolicy(217), 
			 ospfAnnouncePolicyNotFound(218), 
			 duplicateOspfAnnouncePolicy(219), 
			 policyMatchNetEntryNotFound(220), 
			 duplicatePolicyNetEntry(221), 
			 policyAddrListEntryNotFound(222), 
			 duplicatePolicyAddrListEntry(223), 
			 policyAddrListIdNotFound(224), 
			 policyExactNetListNotFound(225), 
			 policyRangeNetListNotFound(226), 
			 policyRipGatewayListNotFound(227), 
			 policyRipInterfaceListNotFound(228), 
			 policyOspfRtrIdListNotFound(229), 
			 policyAnnounceInterfaceListNotFound(230), 
			 policyAdvertiseNetListNotFound(231), 
			 policyInjectNetListNotFound(232), 
			 invalidPolicyListIdListSize(233), 
			 policyAddrEntryNotFound(234), 
			 duplicatePolicyAddrEntry(235), 
			 disableThisPortFirst(236), 
			 mutinettingNotSupported(237), 
			 addingGlobalFilterToNonGlobalList(238), 
			 addingNonGlobalFilterToGlobalList(239), 
			 setFilteredPortMode(240), 
			 setFilteredPortEnableValue(241), 
			 invalidModeType(242), 
                         duplicateRipAcceptPolicy(243), 
                         ripAccepPolicyNotFound(244), 
                         duplicateOspfAcceptPolicy(245), 
                         ospfAccepPolicyNotFound(246), 
                         invalidAccessPolicyName(247), 
                         invalidAccessPolicyPolicyEnable(248), 
                         invalidAccessPolicyMode(249), 
                         invalidAccessPolicyService(250), 
                         invalidAccessPolicyPrecedence(251), 
                         invalidAccessPolicyNetAddress(252), 
                         invalidAccessPolicyTrustedHostAddress(253), 
                         invalidAccessPolicyTrustedHostUserName(254), 
                         invalidAccessPolicyAccessLevel(255), 
                         invalidAccessPolicyLogSetting(256), 
                         invalidAccessPolicyPolicyId(257), 
			 invalidAreaOptions(258), 
			 cannotDeleteAreaIfCountIsNotZero(259), 
			 ospfInterfaceNotFound(260), 
			 ospfIfAreaIdConflictsWithConfiguredAreaRange(261), 
                         applyingDuplicateGlobalFilterToPort(262), 
                         differentMltPortTypes(263), 
                         addPortToMltFailed(264), 
                         removePortFromMltFailed(265), 
                         mirrorPortInMlt(266), 
                         invalidDhcpAlwaysBroadcast(267), 
                         interfaceIsSetToTransmitRipV1(268), 
                         ripInterfaceDoesnotExist(269), 
                         interfaceIsNotRunningRip(270), 
                         cannotCreateVirtLinksThroughStubArea(271), 
			 invalidSyslogEnableSetting(272), 
			 invalidSyslogHostIpAddr(274), 
			 invalidSyslogHostUdpPort(275), 
			 invalidSyslogHostFacility(276), 
 			 invalidSyslogModuleId(277), 
			 invalidSyslogSeverity(278), 
			 invalidSyslogMapInfoSeverity(279), 
			 invalidSyslogMapWarningSeverity(280), 
			 invalidSyslogMapErrorSeverity(281), 
			 invalidSyslogMapMfgSeverity(282), 
			 invalidSyslogMapFatalSeverity(283), 
			 invalidSyslogMapTraceMsgSetting(284), 
			 invalidSyslogMapTrapMsgSetting(285), 
			 invalidSyslogLogTraceMsgSetting(286), 
			 invalidSyslogLogTrapMsgSetting(287), 
			 invalidSyslogEntryEnableSetting(288), 
			 invalidSyslogMaxHostSetting(289), 
			 invalidSyslogHostId(290), 
			 duplicateSyslogEntry(291), 
			 syslogHostTableIsFull(292), 
			 invalidHoldDownTime(294), 
  			 incompatibleAruHardware(295), 
  			 invalidVrid(296), 
  			 duplicateVrrpEntry(297), 
  			 noVrrpIpAddressSpecified(298), 
  			 invalidVrrpControlValue(299), 
			 invalidVrrpPriority(300), 
			 invalidVrrpAdvertisementInterval(301), 
			 maxNumOfVrrpsEntriesExceeded(302), 
			 policyNetListEntryNotFound(303), 
			 duplicatePolicyNetListEntry(304), 
			 policyNetListIdNotFound(305), 
                         filterOnAnEnabledPort(306), 
                         listOnAnEnabledPort(307), 
                         invalidIpFilterSrcOption(308), 
                         invalidIpFilterDstOption(309), 
                         invalidOspfAreaImportextOption(310), 
                         invalidOspfInterfaceMd5KeyIdLength(311), 
                         invalidOspfInterfaceMd5KeyLength(312), 
                         invalidIPXNetworkNumber(313), 
                         ipxCircuitAlreadyExists(314), 
                         ipxCircuitDoesNotExist(315), 
                         encapsulationIsNotAllowedOnSameSegment(316), 
                         encapsulationDoesNotMatchProtocolBasedVLAN(317), 
                         invalidDvmrpIfTblEnableValue(318), 
                         invalidDvmrpIfTblMetricValue(319), 
                         ipHostPartForSubnetAddrIsNonZero(320), 
                         globalMulticastNotEnabled(321), 
                         metricFieldIsCreatedButModified(322), 
                         invalidIpMRouteInterfaceTblTtlValue(323), 
                         invalidUdpPortNumber(324), 
                         invalidUdpProtocolNameLength(325), 
                         cannotModifyUdpProtocolName(326), 
                         udpProtocolEntryDoesnotexists(327), 
                         duplicateUdpProtocolEntry(328), 
                         cannotDelUdpProtocolEntryFwdEntriesExists(329), 
                         udpBroadcastIntfEntryDoesnotExists(330), 
                         duplicateUdpBroadcastIntfEntry(331), 
                         invalidUdpConfBroacastInterface(332), 
                         updConfIntfEntryNotEnabledForUdpBcastForwarding(333), 
                         udpPortFwdEntryDoesnotExists(334), 
                         duplicateUdpPortFwdEntryDoesnotExists(335), 
                         udpPortFwdEntryUdpPortInterfaceDoesnotExists(336), 
                         udpPortFwdListEntryDoesnotExists(337), 
                         duplicateUdpPortFwdListEntryDoesnotExists(338), 
                         udpPortFwdListEntryPortFwdIdDoesnotExists(339), 
                         udpPortFwdListEntryinvalidFwdIdListSize(340), 
 
			cannotDeleteUdpPortFwdListEntryInterfaceUsingThisList(341) 
 
		      } 
        ACCESS        read-only 
        STATUS        mandatory 
 	DESCRIPTION   "This variable is used primarily as an enumeration 
		      to list the proprietary return codes that this 
		      device can send to a management station in 
		      response to a failed SNMP operation." 
	DEFVAL	      { none } 
        ::= { rcError 4 } 
 
rcErrorSendTrap OBJECT-TYPE 
        SYNTAX        TruthValue 
        ACCESS        read-write 
        STATUS        mandatory 
        DESCRIPTION   "Indicates whether to send trap upon receiving an 
                      error in the system." 
	DEFVAL	      { true } 
        ::= { rcError 5 } 
 
 
-- TRAPS 
 
rcCardDown NOTIFICATION-TYPE 
        OBJECTS      { rcCardIndex, rcCardAdminStatus, rcCardOperStatus } 
        STATUS       current 
        DESCRIPTION  "A rcCardDown trap signifies that the SNMPv2 entity, 
                     acting in an agent role, has detected that the 
                     rcCardOperStatus object for one of its cards  
                     is about to transition into the down state." 
        ::= { rcTraps 1 } 
 
rcCardUp NOTIFICATION-TYPE 
        OBJECTS       { rcCardIndex, rcCardAdminStatus, rcCardOperStatus } 
        STATUS        current 
        DESCRIPTION   "A rcCardUp trap signifies that the SNMPv2 entity, 
                      acting in an agent role, has detected that the 
                      rcCardOperStatus object for one of its cards  
                      is about to transition into the up state." 
        ::= { rcTraps 2 } 
 
rcErrorNotification NOTIFICATION-TYPE 
        OBJECTS       { rcErrorLevel, rcErrorCode, rcErrorText } 
        STATUS        current 
        DESCRIPTION   "A rcErrorNotification trap signifies that the  
                      SNMPv2 entity, acting in an agent role, has  
                      detected that an error condition has occured." 
        ::= { rcTraps 3 } 
  
rcStpNewRoot NOTIFICATION-TYPE 
        OBJECTS       { rcStgId } 
        STATUS        current 
        DESCRIPTION   "A rcStpNewRoot trap signifies that the 
                      SNMPv2 entity, acting in an agent role, has 
                      detected the Spanning Tree Protocol has declared 
                      the device to be the new root of the spanning  
       		      tree."  
        ::= { rcTraps 4 } 
 
rcStpTopologyChange NOTIFICATION-TYPE 
       OBJECTS        { rcStgId, rcPortIndex } 
       STATUS         current    
       DESCRIPTION    "A rcStpTopologyChange trap signifies that the  
                      SNMPv2 entity, acting in an agent role, has  
                      detected the Spanning Tree Protocol has gone due 
                      a topology change event." 
       ::= { rcTraps 5 } 
 
rcChasPowerSupplyDown NOTIFICATION-TYPE 
        OBJECTS       { rcChasPowerSupplyId, rcChasPowerSupplyOperStatus} 
        STATUS        current 
        DESCRIPTION   "A rcChasPowerSupplyDown trap signifies that the  
                      SNMPv2 entity, acting in an agent role, has  
                      detected that the rcChasPowerSupplyOperStatus  
                      object for one of its power supply unit is  
                      about to transition into the down state." 
        ::= { rcTraps 6 } 
 
rcChasFanDown NOTIFICATION-TYPE 
        OBJECTS       { rcChasFanId, rcChasFanOperStatus} 
        STATUS        current 
        DESCRIPTION   "A rcChasFanDown trap signifies that the  
                      SNMPv2 entity, acting in an agent role, has  
                      detected that the rcChasFanOperStatus object  
                      for one of its power supply unit is about to  
                      transition into the down state." 
        ::= { rcTraps 7 } 
 
rcLinkOscillation NOTIFICATION-TYPE 
        OBJECTS          { rcPortIndex } 
        STATUS             current 
        DESCRIPTION   "A rcLinkOscillation trap signifies that the 
                       SNMPv2 entity, acting in an agent role, has 
                       detected an excessive number of link state 
                       transitions on the specified port." 
        ::= { rcTraps 8 } 
 
-- Syslog Group 
  
rcSyslogGlobal      OBJECT IDENTIFIER ::= { rcSyslog 1 } 
 
rcSyslogGlobalEnable OBJECT-TYPE 
        SYNTAX        TruthValue 
        ACCESS        read-write 
        STATUS        mandatory 
        DESCRIPTION   "Enable/disable sysLog." 
	DEFVAL	      { true } 
        ::= { rcSyslogGlobal 1 } 
 
rcSyslogGlobalMaxHosts OBJECT-TYPE 
        SYNTAX        INTEGER (0..10) 
        ACCESS        read-write 
        STATUS        mandatory 
        DESCRIPTION   "Maximun number of remote hosts considered 'active' 
                       and able to receive messages from the Syslog service 
                       on the router." 
        DEFVAL        { 5 } 
        ::= { rcSyslogGlobal 2 } 
 
rcSyslogGlobalOperState OBJECT-TYPE 
        SYNTAX        INTEGER { 
                         active(1), 
                         inactive(2), 
                         emptyHostTbl(3), 
                         allHostDisabled(4) 
                      } 
        ACCESS        read-only 
        STATUS        mandatory 
        DESCRIPTION   "The operational state of the syslog service 
                       on the router." 
        DEFVAL        { active } 
        ::= { rcSyslogGlobal 3 } 
 
rcSyslogHostTbl OBJECT-TYPE 
        SYNTAX        SEQUENCE OF RcSyslogHostEntry 
        ACCESS        not-accessible 
        STATUS        mandatory 
        DESCRIPTION   "Table of remote host destinations for syslog." 
        ::= { rcSyslog 2 } 
 
rcSyslogHostEntry OBJECT-TYPE 
        SYNTAX        RcSyslogHostEntry 
        ACCESS        not-accessible 
        STATUS        mandatory 
        DESCRIPTION   "Entry containing information for a particular 
                       entry in rcSyslogHostTable." 
        INDEX         { rcSyslogHostId } 
        ::= { rcSyslogHostTbl 1 } 
 
RcSyslogHostEntry ::= SEQUENCE { 
                rcSyslogHostId                  INTEGER, 
                rcSyslogHostIpAddr              IpAddress, 
                rcSyslogHostUdpPort             INTEGER, 
		rcSyslogHostFacility            INTEGER,	 
		rcSyslogHostModuleId            INTEGER, 
		rcSyslogHostModuleId2           INTEGER, 
		rcSyslogHostSeverity            INTEGER, 
		rcSyslogHostMapInfoSeverity     INTEGER, 
		rcSyslogHostMapWarningSeverity  INTEGER, 
		rcSyslogHostMapErrorSeverity    INTEGER, 
		rcSyslogHostMapMfgSeverity      INTEGER, 
		rcSyslogHostMapFatalSeverity    INTEGER, 
		rcSyslogHostMapTraceMsg         INTEGER, 
		rcSyslogHostMapTrapMsg          INTEGER, 
		rcSyslogHostLogTraceMsgs        TruthValue, 
		rcSyslogHostLogTrapMsgs         TruthValue, 
		rcSyslogHostEnable              TruthValue, 
                rcSyslogHostRowStatus           RowStatus 
        } 
 
rcSyslogHostId OBJECT-TYPE 
        SYNTAX        INTEGER (1..10) 
        ACCESS        read-only 
        STATUS        mandatory 
        DESCRIPTION   "Host Id." 
        ::= { rcSyslogHostEntry 1 } 
 
rcSyslogHostIpAddr OBJECT-TYPE 
        SYNTAX        IpAddress 
        ACCESS        read-write 
        STATUS        mandatory 
        DESCRIPTION   "Host Ip Address" 
        ::= { rcSyslogHostEntry 2 } 
 
rcSyslogHostUdpPort OBJECT-TYPE 
        SYNTAX        INTEGER (514..530) 
        ACCESS        read-write 
        STATUS        mandatory 
        DESCRIPTION   "Specifies the UDP port to use to send syslog  
                      messages to the host."  
        DEFVAL        { 514 } 
        ::= { rcSyslogHostEntry 3 } 
 
rcSyslogHostFacility OBJECT-TYPE 
        SYNTAX        INTEGER { 
                         local0(128), 
                         local1(136), 
                         local2(144), 
                         local3(152), 
                         local4(160), 
                         local5(168), 
                         local6(176), 
                         local7(184) 
                      } 
        ACCESS        read-write 
        STATUS        mandatory 
        DESCRIPTION   "Specifies the UNIX facility used in messages 
 		      to the syslog host.  Default is LOCAL7." 
        DEFVAL        { local7 } 
        ::= { rcSyslogHostEntry 4 } 
  
rcSyslogHostModuleId OBJECT-TYPE 
        SYNTAX        INTEGER { 
                         common         (1), 
                         snmp           (2), 
                         rmon           (4), 
                         portmgr        (8), 
                         chasmgr       (16), 
                         bridge        (32), 
                         ospf          (64), 
                         hwif         (128), 
                         sim          (256), 
                         cpp          (512), 
                         netdrv      (1024), 
                         vlanmgr     (2048), 
                         cli         (4096), 
                         main        (8192), 
                         p2ip       (16384), 
                         rcip       (32768), 
                         rompager   (65536), 
                         acif      (131072), 
                         gbip      (262144), 
                         wdt       (524288), 
                         tdp      (1048576), 
                         mandiag  (2097152), 
                         mantest  (4194304), 
                         igmp     (8388608), 
                         ipfil   (16777216), 
                         mlt     (33554432), 
                         ippolicy(67108864), 
                         ipmc   (134217728), 
                         syslog (268435456) 
                      } 
        ACCESS        read-write 
        STATUS        mandatory 
        DESCRIPTION   "Specifies for which modules/tasks syslog messages 
		       should be sent.  Default is all modules/tasks." 
        ::= { rcSyslogHostEntry 5 } 
 
rcSyslogHostModuleId2 OBJECT-TYPE 
        SYNTAX        INTEGER 
        ACCESS        read-write 
        STATUS        mandatory 
        DESCRIPTION   "" 
        ::= { rcSyslogHostEntry 6 } 
 
rcSyslogHostSeverity OBJECT-TYPE 
        SYNTAX        INTEGER { 
                         info(1), 
                         warning(2), 
                         error(4), 
                         mfg(8), 
                         fatal(16) 
                      } 
        ACCESS        read-write 
        STATUS        mandatory 
        DESCRIPTION   "Specifies the severity level for which syslog messages 
		       should be sent for the modules specifies in  
                       'SyslogHostModule'." 
        DEFVAL        { info } 
        ::= { rcSyslogHostEntry 7 } 
 
rcSyslogHostMapInfoSeverity OBJECT-TYPE 
        SYNTAX        INTEGER { 
                         emergency(1), 
                         alert(2), 
                         critical(3), 
                         error(4), 
                         warning(5), 
                         notice(6), 
                         info(7), 
                         debug(8) 
                      } 
        ACCESS        read-write 
        STATUS        mandatory 
        DESCRIPTION   "Specifies the syslog severity to use for Accelar 
		       INFO messages.  Default is INFO." 
        DEFVAL        { info } 
        ::= { rcSyslogHostEntry 8 } 
 
rcSyslogHostMapWarningSeverity OBJECT-TYPE 
        SYNTAX        INTEGER { 
                         emergency(1), 
                         alert(2), 
                         critical(3), 
                         error(4), 
                         warning(5), 
                         notice(6), 
                         info(7), 
                         debug(8) 
                      } 
        ACCESS        read-write 
        STATUS        mandatory 
        DESCRIPTION   "Specifies the syslog severity to use for Accelar 
                       WARNING messages.  Default is WARNING.  Should be 
                       <= INFO." 
        DEFVAL        { warning } 
        ::= { rcSyslogHostEntry 9 } 
 
rcSyslogHostMapErrorSeverity OBJECT-TYPE 
        SYNTAX        INTEGER { 
                         emergency(1), 
                         alert(2), 
                         critical(3), 
                         error(4), 
                         warning(5), 
                         notice(6), 
                         info(7), 
                         debug(8) 
                      } 
        ACCESS        read-write 
        STATUS        mandatory 
        DESCRIPTION   "Specifies the syslog severity to use for Accelar 
                       ERROR messages.  Default is ERROR.  Should be 
		       <= WARNING." 
        DEFVAL        { error } 
        ::= { rcSyslogHostEntry 10 } 
 
rcSyslogHostMapMfgSeverity OBJECT-TYPE 
        SYNTAX        INTEGER { 
                         emergency(1), 
                         alert(2), 
                         critical(3), 
                         error(4), 
                         warning(5), 
                         notice(6), 
                         info(7), 
                         debug(8) 
                      } 
        ACCESS        read-write 
        STATUS        mandatory 
        DESCRIPTION   "Specifies the syslog severity to use for Accelar 
                       Manufactoring messages.  Dafault is ERROR." 
        DEFVAL        { error } 
        ::= { rcSyslogHostEntry 11 } 
 
rcSyslogHostMapFatalSeverity OBJECT-TYPE 
        SYNTAX        INTEGER { 
                         emergency(1), 
                         alert(2), 
                         critical(3), 
                         error(4), 
                         warning(5), 
                         notice(6), 
                         info(7), 
                         debug(8) 
                      } 
        ACCESS        read-write 
        STATUS        mandatory 
        DESCRIPTION   "Specifies the syslog severity to use for Accelar 
                       FATAL messages.  Default is EMERGENCY.  Should be 
		       <= ERROR." 
        DEFVAL        { emergency } 
        ::= { rcSyslogHostEntry 12 } 
 
rcSyslogHostMapTraceMsg OBJECT-TYPE 
        SYNTAX        INTEGER { 
                         emergency(1), 
                         alert(2), 
                         critical(3), 
                         error(4), 
                         warning(5), 
                         notice(6), 
                         info(7), 
                         debug(8) 
                      } 
        ACCESS        read-write 
        STATUS        mandatory 
        DESCRIPTION   "Specifies the syslog severity to use for syslog 
		       trace messages.  Default is DEBUG." 
        ::= { rcSyslogHostEntry 13 } 
 
rcSyslogHostMapTrapMsg OBJECT-TYPE 
        SYNTAX        INTEGER { 
                         emergency(1), 
                         alert(2), 
                         critical(3), 
                         error(4), 
                         warning(5), 
                         notice(6), 
                         info(7), 
                         debug(8) 
                      } 
        ACCESS        read-write 
        STATUS        mandatory 
        DESCRIPTION   "Specifies the UNIX severity code to use for syslog 
		       messages for SNMP traps sent to the syslog host. 
                       Default is INFO." 
        ::= { rcSyslogHostEntry 14 } 
 
rcSyslogHostLogTraceMsgs OBJECT-TYPE 
        SYNTAX        TruthValue 
        ACCESS        read-write 
        STATUS        mandatory 
        DESCRIPTION   "Indicate whether to activate the host to log the  
                       syslog trace messages." 
        ::= { rcSyslogHostEntry 15 } 
 
rcSyslogHostLogTrapMsgs OBJECT-TYPE 
        SYNTAX        TruthValue 
        ACCESS        read-write 
        STATUS        mandatory 
        DESCRIPTION   "Indicate whether to activate the host to log the 
	               syslog messages for SNMP traps." 
        ::= { rcSyslogHostEntry 16 } 
 
rcSyslogHostEnable OBJECT-TYPE 
        SYNTAX        TruthValue 
        ACCESS        read-write 
        STATUS        mandatory 
        DESCRIPTION   "Enable/Disable messages to be sent to syslog host." 
        DEFVAL        { false } 
        ::= { rcSyslogHostEntry 17 } 
 
rcSyslogHostRowStatus OBJECT-TYPE 
        SYNTAX        RowStatus 
        ACCESS        read-write 
        STATUS        mandatory 
        DESCRIPTION   "Used to create/delete entries in the rcSyslogTable." 
        ::= { rcSyslogHostEntry 18 } 
 
 
-- Diag Mirror by port Table 
 
rcDiagMirrorByPortTable OBJECT-TYPE 
        SYNTAX        SEQUENCE OF RcDiagMirrorByPortEntry 
        ACCESS        not-accessible 
        STATUS        mandatory 
        DESCRIPTION   "Diag Mirror by port Table" 
        ::= { rcDiag 1 } 
 
rcDiagMirrorByPortEntry OBJECT-TYPE 
        SYNTAX        RcDiagMirrorByPortEntry 
        ACCESS        not-accessible 
        STATUS        mandatory 
        DESCRIPTION   "Entry containing mirror by port infomation." 
        INDEX         { rcDiagMirrorByPortId } 
        ::= { rcDiagMirrorByPortTable 1 } 
 
RcDiagMirrorByPortEntry ::= SEQUENCE { 
                rcDiagMirrorByPortId            INTEGER, 
                rcDiagMirrorByPortMirroredPort  InterfaceIndex, 
                rcDiagMirrorByPortMirroringPort InterfaceIndex, 
                rcDiagMirrorByPortMode          INTEGER, 
                rcDiagMirrorByPortEnable        TruthValue, 
                rcDiagMirrorByPortRowStatus     RowStatus 
        } 
 
rcDiagMirrorByPortId OBJECT-TYPE 
        SYNTAX        INTEGER 
        ACCESS        read-only 
        STATUS        mandatory 
        DESCRIPTION   "entry id." 
        ::= { rcDiagMirrorByPortEntry 1 } 
 
rcDiagMirrorByPortMirroredPort OBJECT-TYPE 
        SYNTAX        InterfaceIndex 
        ACCESS        read-write 
        STATUS        mandatory 
        DESCRIPTION   "ingress port." 
        ::= { rcDiagMirrorByPortEntry 2 } 
 
rcDiagMirrorByPortMirroringPort OBJECT-TYPE 
        SYNTAX        InterfaceIndex 
        ACCESS        read-write 
        STATUS        mandatory 
        DESCRIPTION   "egress port." 
        ::= { rcDiagMirrorByPortEntry 3 } 
 
rcDiagMirrorByPortMode OBJECT-TYPE 
        SYNTAX        INTEGER { 
                         tx(1), 
                         rx(2), 
                         both(3) 
                      } 
        ACCESS        read-write 
        STATUS        mandatory 
        DESCRIPTION   "mirror mode" 
	DEFVAL	      { rx } 
        ::= { rcDiagMirrorByPortEntry 4 } 
 
rcDiagMirrorByPortEnable OBJECT-TYPE 
        SYNTAX        TruthValue 
        ACCESS        read-write 
        STATUS        mandatory 
        DESCRIPTION   "Enable this entry." 
	DEFVAL	      { true } 
        ::= { rcDiagMirrorByPortEntry 5 } 
 
rcDiagMirrorByPortRowStatus OBJECT-TYPE 
        SYNTAX        RowStatus 
        ACCESS        read-write 
        STATUS        mandatory 
        DESCRIPTION   "Used to create/delete entries in the 
rcDiagMirrorByPortTable." 
        ::= { rcDiagMirrorByPortEntry 6 } 
 
 
-- Diag Port Conv Steering Table 
 
rcDiagPortConvSteeringTable OBJECT-TYPE 
        SYNTAX        SEQUENCE OF RcDiagPortConvSteeringEntry 
        ACCESS        not-accessible 
        STATUS        mandatory 
        DESCRIPTION   "Diag Port Conv Steering Table" 
        ::= { rcDiag 2 } 
 
rcDiagPortConvSteeringEntry OBJECT-TYPE 
        SYNTAX        RcDiagPortConvSteeringEntry 
        ACCESS        not-accessible 
        STATUS        mandatory 
        DESCRIPTION   "Entry containing infomation of Diag Port Conv 
			Steering." 
        INDEX         { rcDiagPortConvSteeringId } 
        ::= { rcDiagPortConvSteeringTable 1 } 
 
RcDiagPortConvSteeringEntry ::= SEQUENCE { 
                rcDiagPortConvSteeringId           INTEGER, 
                rcDiagPortConvSteeringPortOne      INTEGER, 
                rcDiagPortConvSteeringPortTwo      INTEGER, 
                rcDiagPortConvSteeringMode         INTEGER, 
                rcDiagPortConvSteeringForwardPort  INTEGER, 
                rcDiagPortConvSteeringEnable       TruthValue, 
                rcDiagPortConvSteeringRowStatus    RowStatus 
        } 
 
rcDiagPortConvSteeringId OBJECT-TYPE 
        SYNTAX        INTEGER 
        ACCESS        read-only 
        STATUS        mandatory 
        DESCRIPTION   "entry id." 
        ::= { rcDiagPortConvSteeringEntry 1 } 
 
rcDiagPortConvSteeringPortOne OBJECT-TYPE 
        SYNTAX        INTEGER 
        ACCESS        read-write 
        STATUS        mandatory 
        DESCRIPTION   "ifIndex" 
        ::= { rcDiagPortConvSteeringEntry 2 } 
 
rcDiagPortConvSteeringPortTwo OBJECT-TYPE 
        SYNTAX        INTEGER 
        ACCESS        read-write 
        STATUS        mandatory 
        DESCRIPTION   "ifIndex" 
        ::= { rcDiagPortConvSteeringEntry 3 } 
 
rcDiagPortConvSteeringMode OBJECT-TYPE 
        SYNTAX        INTEGER { 
                         oneToTwo(1), 
                         twoToOne(2), 
                         both(3) 
                      } 
        ACCESS        read-write 
        STATUS        mandatory 
        DESCRIPTION   "" 
        ::= { rcDiagPortConvSteeringEntry 4 } 
 
rcDiagPortConvSteeringForwardPort OBJECT-TYPE 
        SYNTAX        INTEGER 
        ACCESS        read-write 
        STATUS        mandatory 
        DESCRIPTION   "ifIndex" 
        ::= { rcDiagPortConvSteeringEntry 5 } 
 
rcDiagPortConvSteeringEnable OBJECT-TYPE 
        SYNTAX        TruthValue 
        ACCESS        read-write 
        STATUS        mandatory 
        DESCRIPTION   "Enable this entry." 
	DEFVAL	      { true } 
        ::= { rcDiagPortConvSteeringEntry 6 } 
 
rcDiagPortConvSteeringRowStatus OBJECT-TYPE 
        SYNTAX        RowStatus 
        ACCESS        read-write 
        STATUS        mandatory 
        DESCRIPTION   "Used to create/delete entries in the 
rcDiagMirrorByPortTable." 
        ::= { rcDiagPortConvSteeringEntry 7 } 
 
 
-- Diag Mac Conv Steering Table 
 
rcDiagMacConvSteeringTable OBJECT-TYPE 
        SYNTAX        SEQUENCE OF RcDiagMacConvSteeringEntry 
        ACCESS        not-accessible 
        STATUS        mandatory 
        DESCRIPTION   "Diag Mac Conv Steering Table" 
        ::= { rcDiag 3 } 
 
rcDiagMacConvSteeringEntry OBJECT-TYPE 
        SYNTAX        RcDiagMacConvSteeringEntry 
        ACCESS        not-accessible 
        STATUS        mandatory 
        DESCRIPTION   "Entry containing infomation of Diag Mac Conv Steering." 
        INDEX         { rcDiagMacConvSteeringId } 
        ::= { rcDiagMacConvSteeringTable 1 } 
 
RcDiagMacConvSteeringEntry ::= SEQUENCE { 
                rcDiagMacConvSteeringId          INTEGER, 
                rcDiagMacConvSteeringSrcMac      MacAddress, 
                rcDiagMacConvSteeringDstMac      MacAddress, 
                rcDiagMacConvSteeringInPort      INTEGER, 
                rcDiagMacConvSteeringForwardPort INTEGER, 
                rcDiagMacConvSteeringEnable      TruthValue, 
                rcDiagMacConvSteeringRowStatus   RowStatus 
        } 
 
rcDiagMacConvSteeringId OBJECT-TYPE 
        SYNTAX        INTEGER 
        ACCESS        read-only 
        STATUS        mandatory 
        DESCRIPTION   "entry id." 
        ::= { rcDiagMacConvSteeringEntry 1 } 
 
rcDiagMacConvSteeringSrcMac OBJECT-TYPE 
        SYNTAX        MacAddress 
        ACCESS        read-write 
        STATUS        mandatory 
        DESCRIPTION   "source Mac" 
        ::= { rcDiagMacConvSteeringEntry 2 } 
 
rcDiagMacConvSteeringDstMac OBJECT-TYPE 
        SYNTAX        MacAddress 
        ACCESS        read-write 
        STATUS        mandatory 
        DESCRIPTION   "dest Mac" 
        ::= { rcDiagMacConvSteeringEntry 3 } 
 
rcDiagMacConvSteeringInPort OBJECT-TYPE 
        SYNTAX        INTEGER 
        ACCESS        read-write 
        STATUS        mandatory 
        DESCRIPTION   "ifIndex" 
        ::= { rcDiagMacConvSteeringEntry 4 } 
 
rcDiagMacConvSteeringForwardPort OBJECT-TYPE 
        SYNTAX        INTEGER 
        ACCESS        read-write 
        STATUS        mandatory 
        DESCRIPTION   "ifIndex" 
        ::= { rcDiagMacConvSteeringEntry 5 } 
 
rcDiagMacConvSteeringEnable OBJECT-TYPE 
        SYNTAX        TruthValue 
        ACCESS        read-write 
        STATUS        mandatory 
        DESCRIPTION   "Enable this entry." 
	DEFVAL	      { true } 
        ::= { rcDiagMacConvSteeringEntry 6 } 
 
rcDiagMacConvSteeringRowStatus OBJECT-TYPE 
        SYNTAX        RowStatus 
        ACCESS        read-write 
        STATUS        mandatory 
        DESCRIPTION   "Used to create/delete entries in the 
rcDiagMirrorByPortTable." 
        ::= { rcDiagMacConvSteeringEntry 7 } 
 
 
rcDiagSaveConfig OBJECT-TYPE 
        SYNTAX        TruthValue 
        ACCESS        read-write 
        STATUS        mandatory 
        DESCRIPTION   "save config info." 
        ::= { rcDiag 10 } 
 
rcDiagMirrorByPortTblSize OBJECT-TYPE 
        SYNTAX        INTEGER 
        ACCESS        read-only 
        STATUS        mandatory 
        DESCRIPTION   "table size." 
        ::= { rcDiag 11 } 
 
rcDiagPortConvSteeringTblSize OBJECT-TYPE 
        SYNTAX        INTEGER 
        ACCESS        read-only 
        STATUS        mandatory 
        DESCRIPTION   "table size." 
        ::= { rcDiag 12 } 
 
rcDiagMacConvSteeringTblSize OBJECT-TYPE 
        SYNTAX        INTEGER 
        ACCESS        read-only 
        STATUS        mandatory 
        DESCRIPTION   "table size." 
        ::= { rcDiag 13 } 
 
-- RCIPX 
-- IPX  
-- IPX Routing Enable 
 
rcIpxRoutingEnable OBJECT-TYPE 
   	SYNTAX        TruthValue 
  	ACCESS        read-write 
  	STATUS        mandatory 
	DESCRIPTION   "Global Ipx Routing control variable" 
	DEFVAL { false } 
	::= { rcIpx 1 } 
 
-- IPX Address Table 
 
rcIpxAddrTable OBJECT-TYPE 
        SYNTAX        SEQUENCE OF RcIpxAddrEntry 
        ACCESS        not-accessible 
        STATUS        mandatory 
        DESCRIPTION   "The table of addressing information relevant to 
                      this entity's IPX addresses.  This table is used 
                      for associating IfIndex and IPX network number." 
	::= { rcIpx 2 } 
 
rcIpxAddrEntry OBJECT-TYPE 
	SYNTAX        RcIpxAddrEntry 
	ACCESS 	      not-accessible 
	STATUS 	      mandatory 
	DESCRIPTION   "The addressing information for one of this 
                      entity's IP addresses." 
	INDEX         { rcIpxAddrVlanId, rcIpxAddrNetAddr, rcIpxAddrEncap } 
	::= { rcIpxAddrTable 1 } 
 
RcIpxAddrEntry ::= 
    	SEQUENCE { 
           	rcIpxAddrVlanId          INTEGER, 
	        rcIpxAddrNetAddr         OCTET STRING (SIZE(4)), 
            rcIpxAddrEncap           INTEGER, 
           	rcIpxAddrEntryStatus RowStatus 
    	} 
 
rcIpxAddrVlanId OBJECT-TYPE 
   	SYNTAX        INTEGER (1..4094) 
  	ACCESS        read-write 
  	STATUS        mandatory 
	DESCRIPTION   "The index value which uniquely identifies the 
                      interface to which this entry is applicable.  The 
                      interface identified by a particular value of this 
                      index is the same interface as identified by the 
                      same value of ifIndex." 
	::= { rcIpxAddrEntry 1 } 
 
rcIpxAddrNetAddr       OBJECT-TYPE 
        SYNTAX         OCTET STRING (SIZE(4)) 
        ACCESS         read-write 
        STATUS         mandatory 
        DESCRIPTION    "IPX Network address." 
        ::= { rcIpxAddrEntry 2 } 
 
rcIpxAddrEntryStatus OBJECT-TYPE 
        SYNTAX        RowStatus 
        ACCESS        read-write 
        STATUS        mandatory 
        DESCRIPTION   "Used to create/delete entries in the rcIpxAddrEntry." 
        ::= { rcIpxAddrEntry 4 } 
 
rcIpxAddrEncap OBJECT-TYPE   
        SYNTAX        INTEGER { 
                         none(0), 
                         ethernetii(1), 
                         snap(2), 
                         llc(3), 
                         raw(4) 
                      } 
        ACCESS        read-write 
        STATUS        mandatory 
        DESCRIPTION   "Specify IPX encapsulation format.  It is relevent 
                       if the VLAN is port based.  But it's always nice to have it." 
        DEFVAL { none } 
        ::= { rcIpxAddrEntry 3 } 
 
-- RCIPX 
 
END
