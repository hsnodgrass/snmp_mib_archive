RFC1215-MIB DEFINITIONS ::= BEGIN

        IMPORTS
            mib-2, ifIndex, egpNeighAddr 	FROM RFC1213-MIB;

        snmp   OBJECT IDENTIFIER ::= { mib-2 11 }


          coldStart TRAP-TYPE
              ENTERPRISE  snmp
              DESCRIPTION
                          "A coldStart trap signifies that the sending
                          protocol entity is reinitializing itself such
                          that the agent's configuration or the protocol
                          entity implementation may be altered."
        --#TYPE "Cold Start"
        --#SUMMARY "Cold Start."
        --#ARGUMENTS {0}
        --#SEVERITY INFORMATIONAL
        --#TIMEINDEX 99
              ::= 0

          warmStart TRAP-TYPE
              ENTERPRISE  snmp
              DESCRIPTION
                          "A warmStart trap signifies that the sending
                          protocol entity is reinitializing itself such
                          that neither the agent configuration nor the
                          protocol entity implementation is altered."
        --#TYPE "Warm Start"
        --#SUMMARY "Warm Start."
        --#ARGUMENTS {0}
        --#SEVERITY INFORMATIONAL
        --#TIMEINDEX 99

              ::= 1

          linkDown TRAP-TYPE
              ENTERPRISE  snmp
              VARIABLES   { ifIndex }
              DESCRIPTION
                          "A linkDown trap signifies that the sending
                          protocol entity recognizes a failure in one of
                          the communication links represented in the
                          agent's configuration."
        --#TYPE "Link Down"
        --#SUMMARY "Link Down."
        --#ARGUMENTS {0}
        --#SEVERITY INFORMATIONAL
        --#TIMEINDEX 99
              ::= 2

          linkUp TRAP-TYPE
              ENTERPRISE  snmp
              VARIABLES   { ifIndex }
              DESCRIPTION
                          "A linkUp trap signifies that the sending
                          protocol entity recognizes that one of the
                          communication links represented in the agent's
                          configuration has come up."
        --#TYPE "Link Up"
        --#SUMMARY "Link Up."
        --#ARGUMENTS {0}
        --#SEVERITY INFORMATIONAL
        --#TIMEINDEX 99
              ::= 3

          authenticationFailure TRAP-TYPE
              ENTERPRISE  snmp
              DESCRIPTION
                          "An authenticationFailure trap signifies that
                          the sending protocol entity is the addressee
                          of a protocol message that is not properly
                          authenticated.  While implementations of the
                          SNMP must be capable of generating this trap,
                          they must also be capable of suppressing the
                          emission of such traps via an implementation-
                          specific mechanism."
        --#TYPE "Authentication Failure"
        --#SUMMARY "Authentication Failure."
        --#ARGUMENTS {0}
        --#SEVERITY INFORMATIONAL
        --#TIMEINDEX 99
              ::= 4

          egpNeighborLoss TRAP-TYPE
              ENTERPRISE  snmp
              VARIABLES   { egpNeighAddr }
              DESCRIPTION
                          "An egpNeighborLoss trap signifies that an EGP
                          neighbor for whom the sending protocol entity
                          was an EGP peer has been marked down and the
                          peer relationship no longer obtains."
        --#TYPE "EGP Neighbor Loss"
        --#SUMMARY "EGP Neighbor Loss."
        --#ARGUMENTS {0}
        --#SEVERITY INFORMATIONAL
        --#TIMEINDEX 99
              ::= 5

	END
