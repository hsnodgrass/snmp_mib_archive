-- ================================================================
-- = OPENGEAR-SMI: Enterprise structure of management information =
-- =                                                              =
-- = (c) Copyright 2005-2009 Opengear Inc.                        =
-- ================================================================

OPENGEAR-SMI DEFINITIONS ::= BEGIN

IMPORTS
    enterprises
        FROM SNMPv2-SMI;
        
--   opengear MODULE-IDENTITY
--       LAST-UPDATED "0502240100Z"
--       ORGANIZATION "Opengear Inc."
--       CONTACT-INFO
--               "Opengear Inc.
--                630 West 9560 South,
--                Sandy, UT 84070
--                support@opengear.com"
--       DESCRIPTION
--               "Opengear Structure of Management Information MIB"
--       ::= { enterprises 25049 }

-- =============================================================
-- Top Level for Opengear Enterprise        
opengear       OBJECT IDENTIFIER ::= { enterprises 25049 }

-- =============================================================
-- Devices
cm             OBJECT IDENTIFIER ::= { opengear 10 }
sd             OBJECT IDENTIFIER ::= { opengear 11 }
im             OBJECT IDENTIFIER ::= { opengear 12 }

ogProducts     OBJECT IDENTIFIER ::= { opengear 13 }

-- =============================================================
-- Subsystems
console       OBJECT IDENTIFIER ::= { cm 10 }
sensor        OBJECT IDENTIFIER ::= { cm 11 }

-- =============================================================
-- Subsystems
host          OBJECT IDENTIFIER ::= { im 10 }
interface     OBJECT IDENTIFIER ::= { im 11 }
ups           OBJECT IDENTIFIER ::= { im 12 }

-- =============================================================
-- console
connection    OBJECT IDENTIFIER ::= { console 10 }
signal        OBJECT IDENTIFIER ::= { console 11 }
pattern       OBJECT IDENTIFIER ::= { console 12 }

-- =============================================================
-- host
connect       OBJECT IDENTIFIER ::= { host 10 }

-- =============================================================
-- interface
failover      OBJECT IDENTIFIER ::= { interface 10 }

-- =============================================================
-- ups
status        OBJECT IDENTIFIER ::= { ups 10 }

-- ============================================================
-- sensor
status        OBJECT IDENTIFIER ::= { sensor 10 }

END
