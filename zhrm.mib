------------------------------------------------------------------
--                                                              --
-- Tandem SNMP Host Resources Subagent MIB definitions.         --
--                                                              --
------------------------------------------------------------------


SNMP-HMSA-MIB DEFINITIONS ::= BEGIN

   IMPORTS
           enterprises, Gauge, Counter
               FROM RFC1155-SMI
           OBJECT-TYPE
               FROM RFC-1212
           TRAP-TYPE
               FROM RFC-1215
           DisplayString
               FROM RFC1213-MIB;

   --  HMSA-MIB

   tandem         OBJECT IDENTIFIER ::= { enterprises 169 }

   nonstopsystems OBJECT IDENTIFIER ::= { tandem 3 }

   zhrm           OBJECT IDENTIFIER ::= { nonstopsystems 180 }

   -- groups in HMSA-MIB

   zhrmTableInfo  OBJECT IDENTIFIER ::= { zhrm 1 }

   zhrmThreshold  OBJECT IDENTIFIER ::= { zhrm 2 }

   zhrmDevUnavail OBJECT IDENTIFIER ::= { zhrm 3 }

   zhrmSaProcess  OBJECT IDENTIFIER ::= { zhrm 4 }

   zhrmRefresh    OBJECT IDENTIFIER ::= { zhrm 5 }

   zhrmTraps      OBJECT IDENTIFIER ::= { zhrm 7 }

   ------------------------------------------------------------------
   --                                                              --
   -- zhrmTableInfo: the Table Information group                   --
   --                                                              --
   ------------------------------------------------------------------

   zhrmInfStorTable     OBJECT IDENTIFIER ::= { zhrmTableInfo 1 }
   zhrmInfDevTable      OBJECT IDENTIFIER ::= { zhrmTableInfo 2 }
   zhrmInfCpuTable      OBJECT IDENTIFIER ::= { zhrmTableInfo 3 }
   zhrmInfNetTable      OBJECT IDENTIFIER ::= { zhrmTableInfo 4 }
   zhrmInfPrnTable      OBJECT IDENTIFIER ::= { zhrmTableInfo 5 }
   zhrmInfDiskTable     OBJECT IDENTIFIER ::= { zhrmTableInfo 6 }
   zhrmInfPartTable     OBJECT IDENTIFIER ::= { zhrmTableInfo 7 }
   zhrmInfFSTable       OBJECT IDENTIFIER ::= { zhrmTableInfo 8 }

   ------------------------------------------------------------------
   -- Information on the Storage Table                             --
   ------------------------------------------------------------------
   zhrmInfStorEntries   OBJECT-TYPE
      SYNTAX Gauge
      ACCESS read-only
      STATUS mandatory
      DESCRIPTION
         "The current number of entries in the hrStorageTable.

         VALUE:  Integer without leading 0s.

         DERIVATION:  Computed by Host Resources Subagent."
      ::= { zhrmInfStorTable 1 }

   zhrmInfStorFirstIndex   OBJECT-TYPE
      SYNTAX INTEGER (1..65535 )
      ACCESS read-only
      STATUS mandatory
      DESCRIPTION
         "The lowest value of hrStorageIndex.

         VALUE:  Integer without leading 0s.

         DERIVATION:  hrStorageTable."
      ::= { zhrmInfStorTable 2 }

   zhrmInfStorLastIndex OBJECT-TYPE
      SYNTAX INTEGER (1..65535 )
      ACCESS read-only
      STATUS mandatory
      DESCRIPTION
         "The highest value of hrStorageIndex.

         VALUE:  Integer without leading 0s.

         DERIVATION:  hrStorageTable."
      ::= { zhrmInfStorTable 3 }

   zhrmInfStorLastDynamRefresh   OBJECT-TYPE
      SYNTAX DisplayString
      ACCESS read-only
      STATUS mandatory
      DESCRIPTION
         "The system time at which hrStorageTable values
         controlled by the -d startup parameter or the
         zhrmDynamRefreshNow object were last refreshed.

         VALUE:  month DD, YYYY HH:MM:SS.

         DERIVATION:  Guardian procedure JULIANTIMESTAMP."
      ::= { zhrmInfStorTable 4 }

   zhrmInfStorLastStableRefresh  OBJECT-TYPE
      SYNTAX DisplayString
      ACCESS read-only
      STATUS mandatory
      DESCRIPTION
         "The system time at which hrStorageTable values
         controlled by the -s startup parameter or the
         zhrmStableRefreshNow object were last refreshed.

         VALUE:  month DD, YYYY HH:MM:SS.

         DERIVATION:  Guardian procedure JULIANTIMESTAMP."
      ::= { zhrmInfStorTable 5 }

   zhrmInfStorGetCounter   OBJECT-TYPE
      SYNTAX Counter
      ACCESS read-only
      STATUS mandatory
      DESCRIPTION
         "The number of Get operations performed on
         hrStorageTable objects since the subagent was last
         started.

         VALUE:  Integer without leading 0s.

         DERIVATION:  Computed by Host Resources Subagent."
      ::= { zhrmInfStorTable 6 }

   zhrmInfStorGetNextCounter  OBJECT-TYPE
      SYNTAX Counter
      ACCESS read-only
      STATUS mandatory
      DESCRIPTION
         "The number of GetNext operations performed on
         hrStorageTable objects since the subagent was last
         started.

         VALUE:  Integer without leading 0s.

         DERIVATION:  Computed by Host Resources Subagent."
      ::= { zhrmInfStorTable 7 }

   zhrmInfStorSetCounter   OBJECT-TYPE
      SYNTAX Counter
      ACCESS read-only
      STATUS mandatory
      DESCRIPTION
         "The number of Set operations performed on
         hrStorageTable objects since the subagent was last
         started.

         VALUE:  Integer without leading 0s.

         DERIVATION:  Computed by Host Resources Subagent."
      ::= { zhrmInfStorTable 8 }


   ------------------------------------------------------------------
   -- Information on the Device Table                              --
   ------------------------------------------------------------------
   zhrmInfDevEntries OBJECT-TYPE
      SYNTAX Gauge
      ACCESS read-only
      STATUS mandatory
      DESCRIPTION
         "The current number of entries in the hrDeviceTable.

         VALUE:  Integer without leading 0s.

         DERIVATION:  Computed by Host Resources Subagent."
      ::= { zhrmInfDevTable 1 }

   zhrmInfDevFirstIndex OBJECT-TYPE
      SYNTAX INTEGER (1..65535 )
      ACCESS read-only
      STATUS mandatory
      DESCRIPTION
         "The lowest value of hrDeviceIndex.

         VALUE:  Integer without leading 0s.

         DERIVATION:  hrDeviceTable."
      ::= { zhrmInfDevTable 2 }

   zhrmInfDevLastIndex  OBJECT-TYPE
      SYNTAX INTEGER ( 1..65535 )
      ACCESS read-only
      STATUS mandatory
      DESCRIPTION
         "The highest value of hrDeviceIndex.

         VALUE:  Integer without leading 0s.

         DERIVATION:  hrDeviceTable."
      ::= { zhrmInfDevTable 3 }

   zhrmInfDevLastDynamRefresh OBJECT-TYPE
      SYNTAX DisplayString
      ACCESS read-only
      STATUS mandatory
      DESCRIPTION
         "The system time at which hrDeviceTable values
         controlled by the -d startup parameter or the
         zhrmDynamRefreshNow object were last refreshed.

         VALUE:  month DD, YYYY HH:MM:SS.

         DERIVATION:  Guardian procedure JULIANTIMESTAMP."
      ::= { zhrmInfDevTable 4 }

   zhrmInfDevLastStableRefresh   OBJECT-TYPE
      SYNTAX DisplayString
      ACCESS read-only
      STATUS mandatory
      DESCRIPTION
         "The system time at which hrDeviceTable values
         controlled by the -s startup parameter or the
         zhrmStableRefreshNow object were last refreshed.

         VALUE:  month DD, YYYY HH:MM:SS.

         DERIVATION:  Guardian procedure JULIANTIMESTAMP."
      ::= { zhrmInfDevTable 5 }

   zhrmInfDevGetCounter OBJECT-TYPE
      SYNTAX Counter
      ACCESS read-only
      STATUS mandatory
      DESCRIPTION
         "The number of Get operations performed on
         hrDeviceTable objects since the subagent was last
         started.

         VALUE:  Integer without leading 0s.

         DERIVATION:  Computed by Host Resources Subagent."
      ::= { zhrmInfDevTable 6 }

   zhrmInfDevGetNextCounter   OBJECT-TYPE
      SYNTAX Counter
      ACCESS read-only
      STATUS mandatory
      DESCRIPTION
         "The number of GetNext operations performed on
         hrDeviceTable objects since the subagent was last
         started.

         VALUE:  Integer without leading 0s.

         DERIVATION:  Computed by Host Resources Subagent."
      ::= { zhrmInfDevTable 7 }

   zhrmInfDevSetCounter OBJECT-TYPE
      SYNTAX Counter
      ACCESS read-only
      STATUS mandatory
      DESCRIPTION
         "The number of Set operations performed on
         hrDeviceTable objects since the subagent was last
         started.

         VALUE:  Integer without leading 0s.

         DERIVATION:  Computed by Host Resources Subagent."
      ::= { zhrmInfDevTable 8 }


   ------------------------------------------------------------------
   -- Information on the Processor Table                           --
   ------------------------------------------------------------------
   zhrmInfCpuEntries OBJECT-TYPE
      SYNTAX Gauge
      ACCESS read-only
      STATUS mandatory
      DESCRIPTION
         "The current number of entries in the hrProcessorTable.

         VALUE:  Integer without leading 0s.

         DERIVATION:  Computed by Host Resources Subagent."
      ::= { zhrmInfCpuTable 1 }

   zhrmInfCpuFirstIndex OBJECT-TYPE
      SYNTAX INTEGER (1..65535 )
      ACCESS read-only
      STATUS mandatory
      DESCRIPTION
         "The lowest value of hrDeviceIndex for hrProcessorTable
         entries.

         VALUE:  Integer without leading 0s.

         DERIVATION:  hrProcessorTable."
      ::= { zhrmInfCpuTable 2 }

   zhrmInfCpuLastIndex  OBJECT-TYPE
      SYNTAX INTEGER (1..65535 )
      ACCESS read-only
      STATUS mandatory
      DESCRIPTION
         "The highest value of hrDeviceIndex for
         hrProcessorTable entries.

         VALUE:  Integer without leading 0s.

         DERIVATION:  hrProcessorTable."
      ::= { zhrmInfCpuTable 3 }

   zhrmInfCpuLastDynamRefresh OBJECT-TYPE
      SYNTAX DisplayString
      ACCESS read-only
      STATUS mandatory
      DESCRIPTION
         "The system time at which hrProcessorTable values
         controlled by the -d startup parameter or the
         zhrmDynamRefreshNow object were last refreshed.

         VALUE:  month DD, YYYY HH:MM:SS.

         DERIVATION:  Guardian procedure JULIANTIMESTAMP."
      ::= { zhrmInfCpuTable 4 }

   zhrmInfCpuLastStableRefresh   OBJECT-TYPE
      SYNTAX DisplayString
      ACCESS read-only
      STATUS mandatory
      DESCRIPTION
         "The system time at which hrProcessorTable values
         controlled by the -s startup parameter or the
         zhrmStableRefreshNow object were last refreshed.

         VALUE:  month DD, YYYY HH:MM:SS.

         DERIVATION:  Guardian procedure JULIANTIMESTAMP."
      ::= { zhrmInfCpuTable 5 }

   zhrmInfCpuGetCounter OBJECT-TYPE
      SYNTAX Counter
      ACCESS read-only
      STATUS mandatory
      DESCRIPTION
         "The number of Get operations performed on
         hrProcessorTable objects since the subagent was last
         started.

         VALUE:  Integer without leading 0s.

         DERIVATION:  Computed by Host Resources Subagent."
      ::= { zhrmInfCpuTable 6 }

   zhrmInfCpuGetNextCounter   OBJECT-TYPE
      SYNTAX Counter
      ACCESS read-only
      STATUS mandatory
      DESCRIPTION
         "The number of GetNext operations performed on
         hrProcessorTable objects since the subagent was last
         started.

         VALUE:  Integer without leading 0s.

         DERIVATION:  Computed by Host Resources Subagent."
      ::= { zhrmInfCpuTable 7 }

   zhrmInfCpuSetCounter OBJECT-TYPE
      SYNTAX Counter
      ACCESS read-only
      STATUS mandatory
      DESCRIPTION
         "The number of Set operations performed on
         hrProcessorTable objects since the subagent was last
         started.

         VALUE:  Integer without leading 0s.

         DERIVATION:  Computed by Host Resources Subagent."
      ::= { zhrmInfCpuTable 8 }


   ------------------------------------------------------------------
   -- Information on the Network Interface Table                   --
   ------------------------------------------------------------------
   zhrmInfNetEntries OBJECT-TYPE
      SYNTAX Gauge
      ACCESS read-only
      STATUS mandatory
      DESCRIPTION
         "The current number of entries in the hrNetworkTable.

         VALUE:  Integer without leading 0s.

         DERIVATION:  Computed by Host Resources Subagent."
      ::= { zhrmInfNetTable 1 }

   zhrmInfNetFirstIndex OBJECT-TYPE
      SYNTAX INTEGER (1..65535 )
      ACCESS read-only
      STATUS mandatory
      DESCRIPTION
         "The lowest value of hrDeviceIndex for hrNetworkTable
         entries.

         VALUE:  Integer without leading 0s.

         DERIVATION:  hrNetworkTable."
      ::= { zhrmInfNetTable 2 }

   zhrmInfNetLastIndex  OBJECT-TYPE
      SYNTAX INTEGER (1..65535 )
      ACCESS read-only
      STATUS mandatory
      DESCRIPTION
         "The highest value of hrDeviceIndex for hrNetworkTable
         entries.

         VALUE:  Integer without leading 0s.

         DERIVATION:  hrNetworkTable."
      ::= { zhrmInfNetTable 3 }

   zhrmInfNetLastDynamRefresh OBJECT-TYPE
      SYNTAX DisplayString
      ACCESS read-only
      STATUS mandatory
      DESCRIPTION
         "The system time at which hrNetworkTable values
         controlled by the -d startup parameter or the
         zhrmDynamRefreshNow object were last refreshed.

         VALUE:  month DD, YYYY HH:MM:SS.

         DERIVATION:  Guardian procedure JULIANTIMESTAMP."
      ::= { zhrmInfNetTable 4 }

   zhrmInfNetLastStableRefresh   OBJECT-TYPE
      SYNTAX DisplayString
      ACCESS read-only
      STATUS mandatory
      DESCRIPTION
         "The system time at which hrNetworkTable values
         controlled by the -s startup parameter or the
         zhrmStableRefreshNow object were last refreshed.

         VALUE:  month DD, YYYY HH:MM:SS.

         DERIVATION:  Guardian procedure JULIANTIMESTAMP."
      ::= { zhrmInfNetTable 5 }

   zhrmInfNetGetCounter OBJECT-TYPE
      SYNTAX Counter
      ACCESS read-only
      STATUS mandatory
      DESCRIPTION
         "The number of Get operations performed on
         hrNetworkTable objects since the subagent was last
         started.

         VALUE:  Integer without leading 0s.

         DERIVATION:  Computed by Host Resources Subagent."
      ::= { zhrmInfNetTable 6 }

   zhrmInfNetGetNextCounter   OBJECT-TYPE
      SYNTAX Counter
      ACCESS read-only
      STATUS mandatory
      DESCRIPTION
         "The number of GetNext operations performed on
         hrNetworkTable objects since the subagent was last
         started.

         VALUE:  Integer without leading 0s.

         DERIVATION:  Computed by Host Resources Subagent."
      ::= { zhrmInfNetTable 7 }

   zhrmInfNetSetCounter OBJECT-TYPE
      SYNTAX Counter
      ACCESS read-only
      STATUS mandatory
      DESCRIPTION
         "The number of Set operations performed on
         hrNetworkTable objects since the subagent was last
         started.

         VALUE:  Integer without leading 0s.

         DERIVATION:  Computed by Host Resources Subagent."
      ::= { zhrmInfNetTable 8 }


   ------------------------------------------------------------------
   -- Information on the Printer Table                             --
   ------------------------------------------------------------------
   zhrmInfPrnEntries OBJECT-TYPE
      SYNTAX Gauge
      ACCESS read-only
      STATUS mandatory
      DESCRIPTION
         "The current number of entries in the hrPrinterTable.

         VALUE:  Integer without leading 0s.

         DERIVATION:  Computed by Host Resources Subagent."
      ::= { zhrmInfPrnTable 1 }

   zhrmInfPrnFirstIndex OBJECT-TYPE
      SYNTAX INTEGER (1..65535 )
      ACCESS read-only
      STATUS mandatory
      DESCRIPTION
         "The lowest value of hrDeviceIndex for hrPrinterTable
         entries.

         VALUE:  Integer without leading 0s.

         DERIVATION:  hrPrinterTable."
      ::= { zhrmInfPrnTable 2 }

   zhrmInfPrnLastIndex  OBJECT-TYPE
      SYNTAX INTEGER (1..65535 )
      ACCESS read-only
      STATUS mandatory
      DESCRIPTION
         "The highest value of hrDeviceIndex for hrPrinterTable
         entries.

         VALUE:  Integer without leading 0s.

         DERIVATION:  hrPrinterTable."
      ::= { zhrmInfPrnTable 3 }

   zhrmInfPrnLastDynamRefresh OBJECT-TYPE
      SYNTAX DisplayString
      ACCESS read-only
      STATUS mandatory
      DESCRIPTION
         "The system time at which hrPrinterTable values
         controlled by the -d startup parameter or the
         zhrmDynamRefreshNow object were last refreshed.

         VALUE:  month DD, YYYY HH:MM:SS.

         DERIVATION:  Guardian procedure JULIANTIMESTAMP."
      ::= { zhrmInfPrnTable 4 }

   zhrmInfPrnLastStableRefresh   OBJECT-TYPE
      SYNTAX DisplayString
      ACCESS read-only
      STATUS mandatory
      DESCRIPTION
         "The system time at which hrPrinterTable values
         controlled by the -s startup parameter or the
         zhrmStableRefreshNow object were last refreshed.

         VALUE:  month DD, YYYY HH:MM:SS.

         DERIVATION:  Guardian procedure JULIANTIMESTAMP."
      ::= { zhrmInfPrnTable 5 }

   zhrmInfPrnGetCounter OBJECT-TYPE
      SYNTAX Counter
      ACCESS read-only
      STATUS mandatory
      DESCRIPTION
         "The number of Get operations performed on
         hrPrinterTable objects since the subagent was last
         started.

         VALUE:  Integer without leading 0s.

         DERIVATION:  Computed by Host Resources Subagent."
      ::= { zhrmInfPrnTable 6 }

   zhrmInfPrnGetNextCounter   OBJECT-TYPE
      SYNTAX Counter
      ACCESS read-only
      STATUS mandatory
      DESCRIPTION
         "The number of GetNext operations performed on
         hrPrinterTable objects since the subagent was last
         started.

         VALUE:  Integer without leading 0s.

         DERIVATION:  Computed by Host Resources Subagent."
      ::= { zhrmInfPrnTable 7 }

   zhrmInfPrnSetCounter OBJECT-TYPE
      SYNTAX Counter
      ACCESS read-only
      STATUS mandatory
      DESCRIPTION
         "The number of Set operations performed on
         hrPrinterTable objects since the subagent was last
         started.

         VALUE:  Integer without leading 0s.

         DERIVATION:  Computed by Host Resources Subagent."
      ::= { zhrmInfPrnTable 8 }


   ------------------------------------------------------------------
   -- Information on the Disk Table                                --
   ------------------------------------------------------------------
   zhrmInfDiskEntries   OBJECT-TYPE
      SYNTAX Gauge
      ACCESS read-only
      STATUS mandatory
      DESCRIPTION
         "The current number of entries in the
         hrDiskStorageTable.

         VALUE:  Integer without leading 0s.

         DERIVATION:  Computed by Host Resources Subagent."
      ::= { zhrmInfDiskTable 1 }

   zhrmInfDiskFirstIndex   OBJECT-TYPE
      SYNTAX INTEGER (1..65535 )
      ACCESS read-only
      STATUS mandatory
      DESCRIPTION
         "The lowest value of hrDeviceIndex for
         hrDiskStorageTable entries.

         VALUE:  Integer without leading 0s.

         DERIVATION:  hrDiskStorageTable."
      ::= { zhrmInfDiskTable 2 }

   zhrmInfDiskLastIndex OBJECT-TYPE
      SYNTAX INTEGER (1..65535 )
      ACCESS read-only
      STATUS mandatory
      DESCRIPTION
         "The highest value of hrDeviceIndex for
         hrDiskStorageTable entries.

         VALUE:  Integer without leading 0s.

         DERIVATION:  hrDiskStorageTable."
      ::= { zhrmInfDiskTable 3 }

   zhrmInfDiskLastDynamRefresh   OBJECT-TYPE
      SYNTAX DisplayString
      ACCESS read-only
      STATUS mandatory
      DESCRIPTION
         "The system time at which hrDiskStorageTable values
         controlled by the -d startup parameter or the
         zhrmDynamRefreshNow object were last refreshed.

         VALUE:  month DD, YYYY HH:MM:SS.

         DERIVATION:  Guardian procedure JULIANTIMESTAMP."
      ::= { zhrmInfDiskTable 4 }

   zhrmInfDiskLastStableRefresh  OBJECT-TYPE
      SYNTAX DisplayString
      ACCESS read-only
      STATUS mandatory
      DESCRIPTION
         "The system time at which hrDiskStorageTable values
         controlled by the -s startup parameter or the
         zhrmStableRefreshNow object were last refreshed.

         VALUE:  month DD, YYYY HH:MM:SS.

         DERIVATION:  Guardian procedure JULIANTIMESTAMP."
      ::= { zhrmInfDiskTable 5 }

   zhrmInfDiskGetCounter   OBJECT-TYPE
      SYNTAX Counter
      ACCESS read-only
      STATUS mandatory
      DESCRIPTION
         "The number of Get operations performed on
          hrDiskStorageTable objects since the subagent was last
         started.

         VALUE:  Integer without leading 0s.

         DERIVATION:  Computed by Host Resources Subagent."
      ::= { zhrmInfDiskTable 6 }

   zhrmInfDiskGetNextCounter  OBJECT-TYPE
      SYNTAX Counter
      ACCESS read-only
      STATUS mandatory
      DESCRIPTION
         "The number of GetNext operations performed on
         hrDiskStorageTable objects since the subagent was last
         started.

         VALUE:  Integer without leading 0s.

         DERIVATION:  Computed by Host Resources Subagent."
      ::= { zhrmInfDiskTable 7 }

   zhrmInfDiskSetCounter   OBJECT-TYPE
      SYNTAX Counter
      ACCESS read-only
      STATUS mandatory
      DESCRIPTION
         "The number of Set operations performed on
         hrDiskStorageTable objects since the subagent was last
         started.

         VALUE:  Integer without leading 0s.

         DERIVATION:  Computed by Host Resources Subagent."
      ::= { zhrmInfDiskTable 8 }


   ------------------------------------------------------------------
   -- Information on the Partition Table                           --
   ------------------------------------------------------------------
   zhrmInfPartEntries   OBJECT-TYPE
      SYNTAX Gauge
      ACCESS read-only
      STATUS mandatory
      DESCRIPTION
         "The current number of entries in the hrPartitionTable.

         VALUE:  Integer without leading 0s.

         DERIVATION:  Computed by Host Resources Subagent."
      ::= { zhrmInfPartTable 1 }

   zhrmInfPartFirstIndex   OBJECT-TYPE
      SYNTAX INTEGER (1..65535 )
      ACCESS read-only
      STATUS mandatory
      DESCRIPTION
         "The lowest value of hrDeviceIndex for hrPartitionTable
         entries.

         VALUE:  Integer without leading 0s.

         DERIVATION:  hrPartitionTable."
      ::= { zhrmInfPartTable 2 }

   zhrmInfPartLastIndex OBJECT-TYPE
      SYNTAX INTEGER (1..65535)
      ACCESS read-only
      STATUS mandatory
      DESCRIPTION
         "The highest value of hrDeviceIndex for
         hrPartitionTable entries.

         VALUE:  Integer without leading 0s.

         DERIVATION:  hrPartitionTable."
      ::= { zhrmInfPartTable 3 }

   zhrmInfPartLastDynamRefresh   OBJECT-TYPE
      SYNTAX DisplayString
      ACCESS read-only
      STATUS mandatory
      DESCRIPTION
         "The system time at which hrPartitionTable values
         controlled by the -d startup parameter or the
         zhrmDynamRefreshNow object were last refreshed.

         VALUE:  month DD, YYYY HH:MM:SS.

         DERIVATION:  Guardian procedure JULIANTIMESTAMP."
      ::= { zhrmInfPartTable 4 }

   zhrmInfPartLastStableRefresh  OBJECT-TYPE
      SYNTAX DisplayString
      ACCESS read-only
      STATUS mandatory
      DESCRIPTION
         "The system time at which hrPartitionTable values
         controlled by the -s startup parameter or the
         zhrmStableRefreshNow object were last refreshed.

         VALUE:  month DD, YYYY HH:MM:SS.

         DERIVATION:  Guardian procedure JULIANTIMESTAMP."
      ::= { zhrmInfPartTable 5 }

   zhrmInfPartGetCounter   OBJECT-TYPE
      SYNTAX Counter
      ACCESS read-only
      STATUS mandatory
      DESCRIPTION
         "The number of Get operations performed on
         hrPartitionTable objects since the subagent was last
         started.

         VALUE:  Integer without leading 0s.

         DERIVATION:  Computed by Host Resources Subagent."
      ::= { zhrmInfPartTable 6 }

   zhrmInfPartGetNextCounter  OBJECT-TYPE
      SYNTAX Counter
      ACCESS read-only
      STATUS mandatory
      DESCRIPTION
         "The number of GetNext operations performed on
         hrPartitionTable objects since the subagent was last
         started.

         VALUE:  Integer without leading 0s.

         DERIVATION:  Computed by Host Resources Subagent."
      ::= { zhrmInfPartTable 7 }

   zhrmInfPartSetCounter   OBJECT-TYPE
      SYNTAX Counter
      ACCESS read-only
      STATUS mandatory
      DESCRIPTION
         "The number of Set operations performed on
         hrPartitionTable objects since the subagent was last
         started.

         VALUE:  Integer without leading 0s.

         DERIVATION:  Computed by Host Resources Subagent."
      ::= { zhrmInfPartTable 8 }


   ------------------------------------------------------------------
   -- Information on the Filesystem Table                          --
   ------------------------------------------------------------------
   zhrmInfFSEntries  OBJECT-TYPE
      SYNTAX Gauge
      ACCESS read-only
      STATUS mandatory
      DESCRIPTION
         "The current number of entries in the hrFSTable.

         VALUE:  Integer without leading 0s.

         DERIVATION:  Computed by Host Resources Subagent."
      ::= { zhrmInfFSTable 1 }

   zhrmInfFSFirstIndex  OBJECT-TYPE
      SYNTAX INTEGER (1..65535)
      ACCESS read-only
      STATUS mandatory
      DESCRIPTION
         "The lowest value of hrFSIndex.

         VALUE:  Integer without leading 0s.

         DERIVATION:  hrFSTable."
      ::= { zhrmInfFSTable 2 }

   zhrmInfFSLastIndex   OBJECT-TYPE
      SYNTAX INTEGER (1..65535)
      ACCESS read-only
      STATUS mandatory
      DESCRIPTION
         "The highest value of hrFSIndex.

         VALUE:  Integer without leading 0s.

         DERIVATION:  hrFSTable."
      ::= { zhrmInfFSTable 3 }

   zhrmInfFSLastDynamRefresh  OBJECT-TYPE
      SYNTAX DisplayString
      ACCESS read-only
      STATUS mandatory
      DESCRIPTION
         "The system time at which hrFSTable values controlled
         by the -d startup parameter or the zhrmDynamRefreshNow
         object were last refreshed.

         VALUE:  month DD, YYYY HH:MM:SS.

         DERIVATION:  Guardian procedure JULIANTIMESTAMP."
      ::= { zhrmInfFSTable 4 }

   zhrmInfFSLastStableRefresh OBJECT-TYPE
      SYNTAX DisplayString
      ACCESS read-only
      STATUS mandatory
      DESCRIPTION
         "The system time at which hrFSTable values controlled
         by the -s startup parameter or the zhrmStableRefreshNow
         object were last refreshed.

         VALUE:  month DD, YYYY HH:MM:SS.

         DERIVATION:  Guardian procedure JULIANTIMESTAMP."
      ::= { zhrmInfFSTable 5 }

   zhrmInfFSGetCounter  OBJECT-TYPE
      SYNTAX Counter
      ACCESS read-only
      STATUS mandatory
      DESCRIPTION
         "The number of subagent accesses of hrFSTable objects
         to handle Get requests since the subagent was last
         started.

         VALUE:  Integer without leading 0s.

         DERIVATION:  Computed by Host Resources Subagent."
      ::= { zhrmInfFSTable 6 }

   zhrmInfFSGetNextCounter OBJECT-TYPE
      SYNTAX Counter
      ACCESS read-only
      STATUS mandatory
      DESCRIPTION
         "The number of subagent accesses of hrFSTable objects
         to handle GetNext requests since the subagent was last
         started.

         VALUE:  Integer without leading 0s.

         DERIVATION:  Computed by Host Resources Subagent."
      ::= { zhrmInfFSTable 7 }

   zhrmInfFSSetCounter  OBJECT-TYPE
      SYNTAX Counter
      ACCESS read-only
      STATUS mandatory
      DESCRIPTION
         "The number of subagent accesses of hrFSTable objects
         to handle Set requests since the subagent was last
         started.

         VALUE:  Integer without leading 0s.

         DERIVATION:  Computed by Host Resources Subagent."
      ::= { zhrmInfFSTable 8 }


   ------------------------------------------------------------------
   --                                                              --
   -- zhrmThreshold: the Threshold group                           --
   --                                                              --
   ------------------------------------------------------------------

   zhrmThrRAM        OBJECT IDENTIFIER ::= { zhrmThreshold 1 }
   zhrmThrDisk       OBJECT IDENTIFIER ::= { zhrmThreshold 2 }

   ------------------------------------------------------------------
   -- The Threshold RAM Group                                      --
   ------------------------------------------------------------------
   zhrmThrRAMTotal   OBJECT-TYPE
      SYNTAX Gauge
      ACCESS read-only
      STATUS mandatory
      DESCRIPTION
         "The total number of megabytes of RAM in the system.

         VALUE:  Integer without leading 0s.

         DERIVATION:  The value of hrMemorySize, expressed as
         megabytes instead of kilobytes."
      ::= { zhrmThrRAM 1 }

   zhrmThrRAMUse  OBJECT-TYPE
      SYNTAX Gauge
      ACCESS read-only
      STATUS mandatory
      DESCRIPTION
         "The total number of megabytes of RAM currently being
         used.

         VALUE:  Integer without leading 0s.

         DERIVATION:  Sum of hrStorageUsed values for all RAM
         entries in the hrStorageTable. "
      ::= { zhrmThrRAM 2 }

   zhrmThrRAMPercentUse OBJECT-TYPE
      SYNTAX Gauge
      ACCESS read-only
      STATUS mandatory
      DESCRIPTION
         "The percent of zhrmThrRAMTotal that is currently being
         used.

         VALUE:  Integer without leading 0s.

         DERIVATION:  Computed by Host Resources Subagent."
      ::= { zhrmThrRAM 3 }

   zhrmThrRAMTrapEnable OBJECT-TYPE
      SYNTAX INTEGER { ramTrapsDisabled(0),
                       ramTrapsEnabled(1) }
      ACCESS read-write
      STATUS mandatory
      DESCRIPTION
         "When set to 1 (ramTrapsEnabled), a trap
         (zhrmRAMThreshold) is sent whenever utilization of a
         RAM storage area reaches or exceeds zhrmThrRAMHighValue
         or reaches or falls below zhrmThrRAMLowValue.

         VALUE:  One of these values is displayed:
         ramTrapsDisabled or ramTrapsEnabled.

         When setting these values, use 0 or 1.

         DERIVATION:  Initialized to 1 (ramTrapsEnabled) at
         startup, but can be changed from a manager station."
      ::= { zhrmThrRAM 4 }

   zhrmThrRAMHighValue  OBJECT-TYPE
      SYNTAX INTEGER (1..100)
      ACCESS read-write
      STATUS mandatory
      DESCRIPTION
         "The percent utilization of a RAM storage area at or
         above which zhrmThrRAMTable entries are created and a
         trap generated if zhrmThrRAMTrapEnable is set to 1.

         VALUE:  A value of 1 through 100, 90 by default.  A
         value of 100 suppresses trap generation (regardless of
         the value of zhrmThrRAMTrapEnable) and zhrmThrRAMTable
         entry creation.

         DERIVATION:  Set at startup by using the -h startup
         parameter.  Can be changed by setting the value of this
         MIB object."
      ::= { zhrmThrRAM 5 }

   zhrmThrRAMLowValue   OBJECT-TYPE
      SYNTAX INTEGER (1..100)
      ACCESS read-write
      STATUS mandatory
      DESCRIPTION
         "The percent utilization of a RAM storage area at or
         below which a trap is generated if zhrmThrRAMTrapEnable
         is set to 1.

         VALUE:  A value of 1 through 100, 45 by default.  A
         value of 0 suppresses trap generation, regardless of
         the value of zhrmThrRAMTrapEnable.

         DERIVATION:  Set at startup by using the -i startup
         parameter.  Can be changed by setting the value of this
         MIB object."
      ::= { zhrmThrRAM 6 }

   zhrmThrRAMTable OBJECT-TYPE
      SYNTAX  SEQUENCE OF ZhrmThrRAMEntry
      ACCESS  not-accessible
      STATUS  mandatory
      DESCRIPTION
         "Entries describing RAM in the hrStorageTable whose
         usage has reached or exceeded the value of
         zhrmThrRAMHighValue."
      ::= { zhrmThrRAM 7 }

   zhrmThrRAMEntry OBJECT-TYPE
      SYNTAX  ZhrmThrRAMEntry
      ACCESS  not-accessible
      STATUS  mandatory
      DESCRIPTION
         "Information about RAM in the hrStorageTable whose
         usage has reached or exceeded the value of
         zhrmThrRAMHighValue."
      INDEX   { zhrmThrRAMIndex }
      ::= { zhrmThrRAMTable 1 }

   ZhrmThrRAMEntry ::= SEQUENCE {
           zhrmThrRAMIndex               INTEGER,
           zhrmThrRAMDescr               DisplayString,
           zhrmThrRAMAllocationUnits     INTEGER,
           zhrmThrRAMSize                INTEGER,
           zhrmThrRAMUsed                INTEGER,
           zhrmThrRAMAllocationFailures  Counter
       }

   zhrmThrRAMIndex OBJECT-TYPE
       SYNTAX INTEGER (1..2147483647)
       ACCESS read-only
       STATUS mandatory
       DESCRIPTION
         "An index value having a corresponding value
         (hrFSStorageIndex) in the hrFSTable.

         VALUE:  Integer, numbered sequentially starting at 1.

         DERIVATION:  The value of hrStorageIndex for the
         device."
       ::= { zhrmThrRAMEntry 1 }

   zhrmThrRAMDescr OBJECT-TYPE
       SYNTAX DisplayString
       ACCESS read-only
       STATUS mandatory
       DESCRIPTION
         "Description of the type of storage represented by the
         entry.

         VALUE:  The number and type of a processor:  CPUnn
         (processor-type) running Dnn.nn.

         DERIVATION:  The value of hrStorageDescr for the
         device."
       ::= { zhrmThrRAMEntry 2 }

   zhrmThrRAMAllocationUnits OBJECT-TYPE
       SYNTAX      INTEGER (1..2147483647)
       ACCESS      read-only
       STATUS      mandatory
       DESCRIPTION
         "The number of bytes allocated by the entry when
         storage is requested.

         VALUE:  Integer without leading 0s, indicating the page
         size.

         DERIVATION:  The value of hrStorageAllocationUnits for
         the device."
       ::= { zhrmThrRAMEntry 3 }

   zhrmThrRAMSize OBJECT-TYPE
       SYNTAX INTEGER (0..2147483647)
       ACCESS read-only
       STATUS mandatory
       DESCRIPTION
         "The capacity of the entry, in number of allocation
         units.

         VALUE:  Integer without leading 0s.  If the number
         exceeds 2,147,483,647, the value returned is -1D.

         DERIVATION:  The value of hrStorageSize for the
         device."
       ::= { zhrmThrRAMEntry 4 }

   zhrmThrRAMUsed OBJECT-TYPE
       SYNTAX INTEGER (0..2147483647)
       ACCESS read-only
       STATUS mandatory
       DESCRIPTION
         "The capacity of the entry, in number of allocation
         units.

         VALUE:  Integer without leading 0s.

         DERIVATION:  The value of hrStorageUsed for the
         device."
       ::= { zhrmThrRAMEntry 5 }

   zhrmThrRAMAllocationFailures OBJECT-TYPE
       SYNTAX Counter
       ACCESS read-only
       STATUS mandatory
       DESCRIPTION
         "The number of requests for storage by the entry that
         could not be honored because of insufficient space.

         VALUE:  Integer without leading 0s, indicating the
         number of page-fault interrupts since the processor was
         loaded.

         DERIVATION:  The value of hrStorageAllocationFailures
         for the device."
       ::= { zhrmThrRAMEntry 6 }

   ------------------------------------------------------------------
   -- The Threshold Disk Group                                     --
   ------------------------------------------------------------------
   zhrmThrDiskTotal  OBJECT-TYPE
      SYNTAX Gauge
      ACCESS read-only
      STATUS mandatory
      DESCRIPTION
         "The total number of megabytes of writeable disk in the
         system.

         VALUE:  Integer without leading 0s.

         DERIVATION:  Sum of hrStorageSize values for all disk
         entries in the hrStorageTable, expressed as megabytes."
      ::= { zhrmThrDisk 1 }

   zhrmThrDiskUse OBJECT-TYPE
      SYNTAX Gauge
      ACCESS read-only
      STATUS mandatory
      DESCRIPTION
         "The total number of megabytes of writeable disk
         currently being used.

         VALUE:  Integer without leading 0s.

         DERIVATION:  Sum of hrStorageUsed values for all disk
         entries in the hrStorageTable."
      ::= { zhrmThrDisk 2 }

   zhrmThrDiskPercentUse   OBJECT-TYPE
      SYNTAX Gauge
      ACCESS read-only
      STATUS mandatory
      DESCRIPTION
         "The percent of zhrmThrDiskTotal that is currently
         being used.

         VALUE:  Integer without leading 0s.

         DERIVATION:  Computed by Host Resources Subagent."
      ::= { zhrmThrDisk 3 }

   zhrmThrDiskTrapEnable   OBJECT-TYPE
      SYNTAX INTEGER { diskTrapsDisabled(0),
                       diskTrapsEnabled(1) }
      ACCESS read-write
      STATUS mandatory
      DESCRIPTION
         "When set to 1 (diskTrapsEnabled), a trap
         (zhrmDiskThreshold) is sent whenever utilization of a
         writeable disk reaches or exceeds zhrmThrDiskHighValue
         or reaches or falls below zhrmThrDiskLowValue.

         VALUE:  One of these values is displayed:
         diskTrapsDisabled or diskTrapsEnabled.

         When setting these values, use 0 or 1.

         DERIVATION:  Initialized to 1 (diskTrapsEnabled) at
         startup, but can be changed from a manager station."
      ::= { zhrmThrDisk 4 }

   zhrmThrDiskHighValue OBJECT-TYPE
      SYNTAX INTEGER (1..100)
      ACCESS read-write
      STATUS mandatory
      DESCRIPTION
         "The percent utilization of a writeable disk at or
         above which zhrmThrDiskTable entries are created and a
         trap generated if zhrmThrDiskTrapEnable is set to 1.

         VALUE:  A value of 1 through 100, 90 by default.  A
         value of 100 suppresses trap generation (regardless of
         the value of zhrmThrDiskTrapEnable) and
         zhrmThrDiskTable entry creation.

         DERIVATION:  Set at startup by using the -h startup
         parameter.  Can be changed by setting the value of this
         MIB object."
      ::= { zhrmThrDisk 5 }

   zhrmThrDiskLowValue  OBJECT-TYPE
      SYNTAX INTEGER (1..100)
      ACCESS read-write
      STATUS mandatory
      DESCRIPTION
         "The percent utilization of a writeable disk at or
         below which a trap is generated if
         zhrmThrDiskTrapEnable is set to 1.

         VALUE:  A value of 1 through 100, 45 by default.  A
         value of 0 suppresses trap generation, regardless of
         the value of zhrmThrDiskTrapEnable.

         DERIVATION:  Set at startup by using the -i startup
         parameter.  Can be changed by setting the value of this
         MIB object."
      ::= { zhrmThrDisk 6 }

   zhrmThrDiskTable OBJECT-TYPE
      SYNTAX  SEQUENCE OF ZhrmThrDiskEntry
      ACCESS  not-accessible
      STATUS  mandatory
      DESCRIPTION
         "Entries describing writeable disks in the
         hrStorageTable whose usage has reached or exceeded the
         value of zhrmThrDiskHighValue."
      ::= { zhrmThrDisk 7 }

   zhrmThrDiskEntry OBJECT-TYPE
      SYNTAX  ZhrmThrDiskEntry
      ACCESS  not-accessible
      STATUS  mandatory
      DESCRIPTION
         "Information about writeable disks in the
         hrStorageTable whose usage has reached or exceeded the
         value of zhrm ThrDiskHighValue."
      INDEX   { zhrmThrDiskIndex }
      ::= { zhrmThrDiskTable 1 }

   ZhrmThrDiskEntry ::= SEQUENCE {
           zhrmThrDiskIndex               INTEGER,
           zhrmThrDiskDescr               DisplayString,
           zhrmThrDiskAllocationUnits     INTEGER,
           zhrmThrDiskSize                INTEGER,
           zhrmThrDiskUsed                INTEGER,
           zhrmThrDiskAllocationFailures  Counter
       }

   zhrmThrDiskIndex OBJECT-TYPE
       SYNTAX INTEGER (1..2147483647)
       ACCESS read-only
       STATUS mandatory
       DESCRIPTION
         "An index value having a corresponding value
         (hrFSStorageIndex) in the hrFSTable.

         VALUE:  Integer, numbered sequentially starting at 1.

         DERIVATION:  The value of hrStorageIndex for the
         device."
       ::= { zhrmThrDiskEntry 1 }

   zhrmThrDiskDescr OBJECT-TYPE
       SYNTAX DisplayString
       ACCESS read-only
       STATUS mandatory
       DESCRIPTION
         "Description of the type of storage represented by the
         entry.

         VALUE:  The name and type of the disk:  $volume(disk-
         type).

         DERIVATION:  The value of hrStorageDescr for the
         device."
       ::= { zhrmThrDiskEntry 2 }

   zhrmThrDiskAllocationUnits OBJECT-TYPE
       SYNTAX      INTEGER (1..2147483647)
       ACCESS      read-only
       STATUS      mandatory
       DESCRIPTION
         "The number of bytes allocated by the entry when
         storage is requested.

         VALUE:  2048, indicating one page.

         DERIVATION:  The value of hrStorageAllocationUnits for
         the device."
       ::= { zhrmThrDiskEntry 3 }

   zhrmThrDiskSize OBJECT-TYPE
       SYNTAX INTEGER (0..2147483647)
       ACCESS read-only
       STATUS mandatory
       DESCRIPTION
         "The capacity of the entry, in number of allocation
         units.

         VALUE:  Integer without leading 0s.  The number
         describes the pages formatted.

         DERIVATION:  The value of hrStorageSize for the
         device."
       ::= { zhrmThrDiskEntry 4 }

   zhrmThrDiskUsed OBJECT-TYPE
       SYNTAX INTEGER (0..2147483647)
       ACCESS read-only
       STATUS mandatory
       DESCRIPTION
         "The amount of allocated storage associated with the
         entry, in allocation units.

         VALUE:  Integer without leading 0s.

         DERIVATION:  The value of hrStorageUsed for the
         device."
       ::= { zhrmThrDiskEntry 5 }

   zhrmThrDiskAllocationFailures OBJECT-TYPE
       SYNTAX Counter
       ACCESS read-only
       STATUS mandatory
       DESCRIPTION
         "The number of requests for storage by the entry that
         could not be honored because of insufficient space.

         VALUE:  This value is not available, and 0 is returned.

         DERIVATION:  The value of hrStorageAllocationFailures
         for the device."
       ::= { zhrmThrDiskEntry 6 }


   ------------------------------------------------------------------
   --                                                              --
   -- zhrmDevUnavail: the Device Unavailable group                 --
   --                                                              --
   ------------------------------------------------------------------

   zhrmDevUnCurrTime OBJECT-TYPE
      SYNTAX DisplayString
      ACCESS read-only
      STATUS mandatory
      DESCRIPTION
         "The current system time.

         VALUE:  month DD, YYYY HH:MM:SS.

         DERIVATION:  Guardian procedure JULIANTIMESTAMP."
      ::= { zhrmDevUnavail 1 }

   zhrmDevUnUp OBJECT-TYPE
      SYNTAX Gauge
      ACCESS read-only
      STATUS mandatory
      DESCRIPTION
         "The total number of devices for which the value of
         hrDeviceStatus is 2 (running).

         VALUE:  Integer without leading 0s.

         DERIVATION:  Sum of entries in hrDeviceTable having
         specified status."
      ::= { zhrmDevUnavail 2 }

   zhrmDevUnDown  OBJECT-TYPE
      SYNTAX Gauge
      ACCESS read-only
      STATUS mandatory
      DESCRIPTION
         "The total number of devices for which the value of
         hrDeviceStatus is 5 (down).

         VALUE:  Integer without leading 0s.

         DERIVATION:  Sum of entries in hrDeviceTable having
         specified status."
      ::= { zhrmDevUnavail 3 }

   zhrmDevUnOther OBJECT-TYPE
      SYNTAX Gauge
      ACCESS read-only
      STATUS mandatory
      DESCRIPTION
         "The total number of devices for which the value of
         hrDeviceStatus is 1 (unknown), 3 (warning), or 4
         (testing).

         VALUE:  Integer without leading 0s.

         DERIVATION:  Sum of entries in hrDeviceTable having
         specified status."
      ::= { zhrmDevUnavail 4 }

   zhrmDevUnTrapEnable  OBJECT-TYPE
      SYNTAX INTEGER { devUnTrapsDisabled(0),
                       devUnTrapsEnabled(1) }
      ACCESS read-write
      STATUS mandatory
      DESCRIPTION
         "When set to 1 (devUnTrapsEnabled), a trap
         (zhrmTrapDeviceStateChange) is sent whenever the value
         of hrDeviceStatus changes.

         VALUE:  One of these values is displayed:
         devUnTrapsDisabled or devUnTrapsEnabled.

         When setting these values, use 0 or 1.

         DERIVATION:  Initialized to 1 (devUnTrapsEnabled) at
         startup, but can be changed from a manager station."
      ::= { zhrmDevUnavail 5 }

   zhrmDevUnTable OBJECT-TYPE
      SYNTAX  SEQUENCE OF ZhrmDevUnEntry
      ACCESS  not-accessible
      STATUS  mandatory
      DESCRIPTION
         "Entries duplicating entries in the hrDeviceTable for
         devices that have an hrDeviceStatus value other than 2
         (running)."
      ::= { zhrmDevUnavail 6 }

   zhrmDevUnEntry OBJECT-TYPE
      SYNTAX  ZhrmDevUnEntry
      ACCESS  not-accessible
      STATUS  mandatory
      DESCRIPTION
         "Information duplicating that in the hrDeviceTable for
         devices that have an hrDeviceStatus value other than 2
         (running)."
      INDEX   { zhrmDevUnIndex }
      ::= { zhrmDevUnTable 1 }

   ZhrmDevUnEntry ::= SEQUENCE {
           zhrmDevUnIndex         INTEGER,
           zhrmDevUnType          OBJECT IDENTIFIER,
           zhrmDevUnDescr         DisplayString,
           zhrmDevUnID            OBJECT IDENTIFIER,
           zhrmDevUnStatus        INTEGER,
           zhrmDevUnErrors        Counter
       }

   zhrmDevUnIndex OBJECT-TYPE
       SYNTAX INTEGER (1..2147483647)
       ACCESS read-only
       STATUS mandatory
       DESCRIPTION
         "Index values that point to entries in the
         hrProcessorTable, the hrPrinterTable, the
         hrDiskStorageTable, the hrNetworkTable, and the
         hrPartitionTable.

         VALUE:  Integers running sequentially from 1.

         DERIVATION:  The value of hrDeviceIndex for qualifying
         devices."
       ::= { zhrmDevUnEntry 1 }

   zhrmDevUnType OBJECT-TYPE
       SYNTAX OBJECT IDENTIFIER
       ACCESS read-only
       STATUS mandatory
       DESCRIPTION
         "One of the following device types defined by RFC 1514
         that characterizes the entry:  hrDeviceProcessor,
         hrDeviceNetwork, hrDevicePrinter, hrDeviceDiskStorage,
         hrDeviceTape.

         VALUE:  For CPUs:  1.3.6.1.2.1.25.3.1.3.
                 For printers:  1.3.6.1.2.1.25.3.1.5.
                 For disks:  1.3.6.1.2.1.25.3.1.6.
                 For tape drives:  1.3.6.1.2.1.25.3.1.18.
                 For network devices:  1.3.6.1.2.1.25.3.1.4.

         DERIVATION:  The value of hrDeviceType for qualifying
         devices."
       ::= { zhrmDevUnEntry 2 }

   zhrmDevUnDescr OBJECT-TYPE
       SYNTAX DisplayString (SIZE (0..64))
       ACCESS read-only
       STATUS mandatory
       DESCRIPTION
         "Description of the type of device represented by the
         entry.

         VALUE:  For CPUs:  the number and type of a processor:
                  CPUnn (processor-type).
                 For printers:  the name of a printer or Spooler
                  collector. Printers have names of the form
                  $printer-id.  Spooler collectors, used as
                  pseudo printers, have names of the form
                  [\node-name]$collector-process-name[.#group-
                  name].
                 For disks:  the name and type of the disk:
                  $volume(disk-type).
                 For tapes:  $tape-drive-name.
                 For network devices:  $network-device.
                 For a loop back device:  $NOIOP.
         DERIVATION:  The value of hrDeviceDescr for qualifying
         devices."
       ::= { zhrmDevUnEntry 3 }

   zhrmDevUnID OBJECT-TYPE
       SYNTAX OBJECT IDENTIFIER
       ACCESS read-only
       STATUS mandatory
       DESCRIPTION
         "An identifier characterizing the entry as a particular
         device type and subtype.

         VALUE:  The root of the identifier is the same for all
         entries: 1.3.6.1.4.1.169.3.180.

         Appended to this value are the type and subtype values.
         For example, the hrDeviceID for a 4500 (1038-MB
         formatted capacity per spindle) disk would look like
         this:1.3.6.1.4.1.169.3.180.3.22.

         Refer to the 'Guardian Procedure Calls Reference
         Manual' for a complete list of all device types and
         subtypes.

         DERIVATION:  The value of hrDeviceID for qualifying
         devices."
       ::= { zhrmDevUnEntry 4 }

   zhrmDevUnStatus OBJECT-TYPE
        SYNTAX  INTEGER {
             unknown(1),
             running(2),
             warning(3),
             testing(4),
             down(5)
        }
        ACCESS  read-only
        STATUS  mandatory
        DESCRIPTION
         "The current state the device represented by the entry
         is in.

         VALUE:  One of these values:  unknown, warning, testing
         down.

         DERIVATION:  The value of hrDeviceStatus for qualifying
         devices."
        ::= { zhrmDevUnEntry 5 }

   zhrmDevUnErrors OBJECT-TYPE
       SYNTAX Counter
       ACCESS read-only
       STATUS mandatory
       DESCRIPTION
         "The number of errors detected on the device described
         by the entry.

         VALUE:  Integer without leading 0s.

         DERIVATION:  The value of hrDeviceErrors for qualifying
         devices."
       ::= { zhrmDevUnEntry 6 }


   ------------------------------------------------------------------
   --                                                              --
   -- zhrmSaProcess: the Subagent Process group                    --
   --                                                              --
   ------------------------------------------------------------------

   zhrmSaProcCurrTime   OBJECT-TYPE
      SYNTAX DisplayString
      ACCESS read-only
      STATUS mandatory
      DESCRIPTION
         "The current system time.

         VALUE:  month DD, YYYY HH:MM:SS.

         DERIVATION:  Guardian procedure JULIANTIMESTAMP."
      ::= { zhrmSaProcess 1 }

   zhrmSaProcVersion OBJECT-TYPE
      SYNTAX DisplayString
      ACCESS read-only
      STATUS mandatory
      DESCRIPTION
         "The version of the Host Resources Subagent.

         VALUE:  T8496Dnn_date -- Tandem Host Resources Subagent.

         Where Dnn is the product version of the Host Resources
         Subagent, for example, D21.

DERIVATION:  Host Resources Subagent."
      ::= { zhrmSaProcess 2 }

   zhrmSaProcName OBJECT-TYPE
      SYNTAX DisplayString
      ACCESS read-only
      STATUS mandatory
      DESCRIPTION
         "The name of the subagent process.

         VALUE:  $process-name, where process-name is from 1
         through 5 alphanumeric characters.

         DERIVATION:  The name specified in the TACL NAME option
         when the subagent was started."
      ::= { zhrmSaProcess 3 }

   zhrmSaPaid  OBJECT-TYPE
      SYNTAX DisplayString
      ACCESS read-only
      STATUS mandatory
      DESCRIPTION
         "The process access ID (PAID) of the subagent process.

         VALUE:  group-number,user-number.

         DERIVATION:  The group and user numbers associated with
         the user who started the subagent."
      ::= { zhrmSaProcess 4 }

   zhrmSaPID   OBJECT-TYPE
      SYNTAX DisplayString
      ACCESS read-only
      STATUS mandatory
      DESCRIPTION
         "The process ID (PID) of the subagent process.

         VALUE:  (CPU-number,PIN-number).

         DERIVATION:  Host Resources Subagent."
      ::= { zhrmSaProcess 5 }

   zhrmSaCreatTime   OBJECT-TYPE
      SYNTAX DisplayString
      ACCESS read-only
      STATUS mandatory
      DESCRIPTION
         "The system time at which the subagent process started.

         VALUE:  started month DD, YYYY HH:MM:SS.

         DERIVATION:  Guardian procedure JULIANTIMESTAMP."
      ::= { zhrmSaProcess 6 }

   zhrmSaCpuTime  OBJECT-TYPE
      SYNTAX DisplayString
      ACCESS read-only
      STATUS mandatory
      DESCRIPTION
         "The amount of CPU time used by the subagent since
         starting.

         VALUE:  HH:MM:SS.

         DERIVATION:  Computed by Host Resources Subagent."
      ::= { zhrmSaProcess 7 }

   zhrmSaPri   OBJECT-TYPE
      SYNTAX INTEGER
      ACCESS read-write
      STATUS mandatory
      DESCRIPTION
         "The priority of the subagent primary and backup
         processes.

         VALUE:  Integer without leading 0s.

         DERIVATION:  Initially, the value of the -n startup
         parameter (145 or a user-specified value).  After
         startup, the value can be set from a manager station."
      ::= { zhrmSaProcess 8 }

   zhrmSaHomeTerm OBJECT-TYPE
      SYNTAX DisplayString
      ACCESS read-only
      STATUS mandatory
      DESCRIPTION
         "The name of the terminal from which the subagent was
         started.

         VALUE:  \node.$device-name.#subdevice-name.

         DERIVATION:  Guardian procedure PROCESS_GETINFO_."
      ::= { zhrmSaProcess 9 }

   zhrmSaIniFile  OBJECT-TYPE
      SYNTAX DisplayString
      ACCESS read-only
      STATUS mandatory
      DESCRIPTION
         "The name of the subagent˜s initialization file.

         VALUE:  \node.$volume.subvolume.file.

         DERIVATION:  The name specified in the -e startup
         parameter.  If not specified, the name HMSAINI."
      ::= { zhrmSaProcess 10 }

   zhrmSaHeapInitial OBJECT-TYPE
      SYNTAX Gauge
      ACCESS read-only
      STATUS mandatory
      DESCRIPTION
         "The number of bytes of memory buffer space allocated
         at subagent startup.

         VALUE:  Integer without leading 0s.

         DERIVATION:  Internal library routine."
      ::= { zhrmSaProcess 11 }

   zhrmSaHeapCurrent OBJECT-TYPE
      SYNTAX Gauge
      ACCESS read-only
      STATUS mandatory
      DESCRIPTION
         "The number of bytes of memory buffer space currently
         in use by the subagent.

         VALUE:  Integer without leading 0s.

         DERIVATION:  Internal library routine."
      ::= { zhrmSaProcess 12 }

   zhrmGetPDUsCounter   OBJECT-TYPE
      SYNTAX Counter
      ACCESS read-only
      STATUS mandatory
      DESCRIPTION
         "The number of Get requests received from the NonStop
         agent since starting.

         VALUE:  Integer without leading 0s.

         DERIVATION:  Computed by Host Resources Subagent."
      ::= { zhrmSaProcess 13 }

   zhrmGetNextPDUsCounter  OBJECT-TYPE
      SYNTAX Counter
      ACCESS read-only
      STATUS mandatory
      DESCRIPTION
         "The number of GetNext requests received from the
         NonStop agent since starting.

         VALUE:  Integer without leading 0s.

         DERIVATION:  Computed by Host Resources Subagent."
      ::= { zhrmSaProcess 14 }

   zhrmSetPDUsCounter   OBJECT-TYPE
      SYNTAX Counter
      ACCESS read-only
      STATUS mandatory
      DESCRIPTION
         "The number of Set requests received from the NonStop
         agent since starting.

         VALUE:  Integer without leading 0s.

         DERIVATION:  Computed by Host Resources Subagent."
      ::= { zhrmSaProcess 15 }

   zhrmTrapPDUsCounter  OBJECT-TYPE
      SYNTAX Counter
      ACCESS read-only
      STATUS mandatory
      DESCRIPTION
         "The number of traps generated by the subagent since
         starting.

         VALUE:  Integer without leading 0s.

         DERIVATION:  Computed by Host Resources Subagent."
      ::= { zhrmSaProcess 16 }

   zhrmEnableSoftwareGroup OBJECT-TYPE
      SYNTAX INTEGER { swValuesDisabled(0),
                       swValuesEnabled(1) }
      ACCESS read-write
      STATUS mandatory
      DESCRIPTION
         "A switch that suppresses maintenance of hrSWRun and
         hrSWRunPerf group objects when set to 0.

         VALUE:  One of these values is displayed:
         swValuesDisabled or swValuesEnabled.

         When setting these values, use 0 or 1.

         DERIVATION:  At startup, the subagent sets this value
         to 1 (swValuesEnabled) unless the -w startup parameter
         is used.  The -w startup parameter sets this value to
         0."
      ::= { zhrmSaProcess 17 }


   zhrmSwitchToBackupNow   OBJECT-TYPE
      SYNTAX INTEGER { autoProcessPairControl(0),
                       forceBackupTakeover(1) }
      ACCESS read-write
      STATUS mandatory
      DESCRIPTION
         "A switch that causes the subagent˜s backup process to
         take over and a new backup process to be created when
         set to 1.

         VALUE:  One of these values is displayed:
         autoProcessPairControl or forceBackupTakeover.

         When setting these values, use 0 or 1.

         DERIVATION:  At startup, the subagent sets this value
         to 0 (autoProcessPairControl), but it can be changed
         from a manager station if the subagent was started
         using the -b startup parameter."
      ::= { zhrmSaProcess 18 }


   -- ARUN OSS_ENHANCEMENT
   zhrmExamineGuardian   OBJECT-TYPE
      SYNTAX INTEGER { disabled(0),
                       enabled(1) }
      ACCESS read-write
      STATUS mandatory
      DESCRIPTION
         "determines whether the subagent obtains hrPartition,
         hrFilesystem, hrFileSystemType, hrSoftwareRun, and
         hrSoftwareRunPerformance table information from Guardian
         personality.

         VALUE:  One of these values is displayed:
         disabled or enabled.

         When setting these values, use 0 or 1.

         DERIVATION:  At startup, the subagent sets this value
         to 1 (enabled). The value of this variables depends
         on the -t startup parameter."
      ::= { zhrmSaProcess 19 }


   zhrmExamineOSS   OBJECT-TYPE
      SYNTAX INTEGER { disabled(0),
                       enabled(1) }
      ACCESS read-write
      STATUS mandatory
      DESCRIPTION
         "determines whether the subagent obtains hrPartition,
         hrFilesystem, hrFileSystemType, hrSoftwareRun, and
         hrSoftwareRunPerformance table information from Open
         Systems Services personality.

         VALUE:  One of these values is displayed:
         disabled or enabled.

         When setting these values, use 0 or 1.

         DERIVATION:  At startup, the subagent sets this value
         to 0 (disabled), but it can be changed from a manager
         station if the subagent was started using the -u
         startup parameter."
      ::= { zhrmSaProcess 20 }
   -- ARUN OSS_ENHANCEMENT


   ------------------------------------------------------------------
   --                                                              --
   -- zhrmRefresh: the Refresh group                               --
   --                                                              --
   ------------------------------------------------------------------

   zhrmRefreshCurrTime  OBJECT-TYPE
      SYNTAX DisplayString
      ACCESS read-only
      STATUS mandatory
      DESCRIPTION
         "The current system time.

         VALUE:  month DD, YYYY HH:MM:SS.

         DERIVATION:  Guardian procedure JULIANTIMESTAMP."
      ::= { zhrmRefresh 1 }

   zhrmDynamRefreshInterval   OBJECT-TYPE
      SYNTAX INTEGER
      ACCESS read-only
      STATUS mandatory
      DESCRIPTION
         "The number of minutes assigned to the -d startup
         parameter when the subagent was started.

         VALUE:  Integer without leading 0s.

         DERIVATION:  Subagent -d startup parameter."
      ::= { zhrmRefresh 2 }

   zhrmStableRefreshInterval  OBJECT-TYPE
      SYNTAX INTEGER
      ACCESS read-only
      STATUS mandatory
      DESCRIPTION
         "The number of minutes assigned to the -s startup
         parameter when the subagent was started.

         VALUE:  Integer without leading 0s.

         DERIVATION:  Subagent -s startup parameter."
      ::= { zhrmRefresh 3 }

   zhrmLastDynamRefreshTime   OBJECT-TYPE
      SYNTAX DisplayString
      ACCESS read-only
      STATUS mandatory
      DESCRIPTION
         "The system time at which MIB values controlled by the
         -d startup parameter or the zhrmDynamRefreshNow object
         were last refreshed.

         VALUE:  month DD, YYYY HH:MM:SS.

         DERIVATION:  Guardian procedure JULIANTIMESTAMP."
      ::= { zhrmRefresh 4 }

   zhrmLastStableRefreshTime  OBJECT-TYPE
      SYNTAX DisplayString
      ACCESS read-only
      STATUS mandatory
      DESCRIPTION
         "The system time at which MIB values controlled by the
         -s startup parameter or the zhrmStableRefreshNow object
         were last refreshed.

         VALUE:  month DD, YYYY HH:MM:SS

         DERIVATION:  Guardian procedure JULIANTIMESTAMP."
      ::= { zhrmRefresh 5 }

   zhrmDynamRefreshCnt  OBJECT-TYPE
      SYNTAX Counter
      ACCESS read-only
      STATUS mandatory
      DESCRIPTION
         "The number of times since the subagent was started
         that MIB values controlled by the -d startup parameter
         or the zhrmDynamRefreshNow object were refreshed.

         VALUE:  Integer without leading 0s.

         DERIVATION:  Computed by Host Resources Subagent."
      ::= { zhrmRefresh 6 }

   zhrmStableRefreshCnt OBJECT-TYPE
      SYNTAX Counter
      ACCESS read-only
      STATUS mandatory
      DESCRIPTION
         "The number of times since the subagent was started
         that MIB values controlled by the -s startup parameter
         or the zhrmStableRefreshNow object were refreshed.

         VALUE:  Integer without leading 0s.

         DERIVATION:  Computed by Host Resources Subagent."
      ::= { zhrmRefresh 7 }

   zhrmDynamRefreshNow  OBJECT-TYPE
      SYNTAX INTEGER { autoDynamicRefresh(0),
                       forceDynamicRefresh(1) }
      ACCESS read-write
      STATUS mandatory
      DESCRIPTION
         "When set to 1 (forceDynamicRefresh)MIB objects whose
         values are controlled by the -d startup parameter are
         refreshed.

         VALUE:  One of these values is displayed:
         autoDynamicRefresh forceDynamicRefresh.

         When setting these values, use 0 or 1.

         DERIVATION:  Initialized to 0 (autoDynamicRefresh) at
         startup, but can be changed from a manager station."
      ::= { zhrmRefresh 8 }

   zhrmStableRefreshNow OBJECT-TYPE
      SYNTAX INTEGER { autoStableRefresh(0),
                       forceStableRefresh(1) }
      ACCESS read-write
      STATUS mandatory
      DESCRIPTION
         "When set to 1(forceStableRefresh), MIB objects whose
         values are controlled by the -s startup parameter are
         refreshed.

         VALUE:  One of these values is displayed:
         autoStableRefresh or forceStableRefresh.

         When setting these values, use 0 or 1.

         DERIVATION:  Initialized to 0 (autoStableRefresh) at
         startup, but can be changed from a manager station."
      ::= { zhrmRefresh 9 }

   ------------------------------------------------------------------
   --                                                              --
   -- zhrmTraps: the traps defined for the Host MIB extension      --
   --                                                              --
   ------------------------------------------------------------------

   zhrmTrapDeviceStateIndex OBJECT-TYPE
       SYNTAX INTEGER (1..2147483647)
       ACCESS not-accessible
       STATUS mandatory
       DESCRIPTION
         "Index value that points to the entry (in the
         hrProcessorTable, the hrPrinterTable, the
         hrDiskStorageTable, the hrNetworkTable, or the
         hrPartitionTable) for the device that the trap
         describes.

         VALUE:  Integer, numbered sequentially starting at 1.

         DERIVATION:  The value of zhrmDevUnIndex for the
         device."
       ::= { zhrmTraps 1 }

   zhrmTrapDeviceDescr OBJECT-TYPE
       SYNTAX DisplayString (SIZE (0..64))
       ACCESS not-accessible
       STATUS mandatory
       DESCRIPTION
         "A description of the type of device that the trap
         describes.

         VALUE:  For CPUs:  the number and type of a processor:
                  CPUnn (processor-type).
                 For printers:  the name of a printer or Spooler
                  collector. Printers have names of the form
                  $printer-id.  Spooler collectors, used as
                  pseudo printers, have names of the form
                  [\node-name]$collector-process-name[.#group-
                  name].
                 For disks:  the name and type of the disk:
                  $volume(disk-type).
                 For tapes:  $tape-drive-name.
                 For network devices:  $network-device.
                 For a loop back device:  $NOIOP.

         DERIVATION:  The value of zhrmDevUnDescr for the
         device."
       ::= { zhrmTraps 2 }

   zhrmTrapDeviceStatus OBJECT-TYPE
        SYNTAX  INTEGER {
             unknown(1),
             running(2),
             warning(3),
             testing(4),
             down(5)
        }
        ACCESS  not-accessible
        STATUS  mandatory
        DESCRIPTION
         "The current state the device that the trap describes
         is in.

         VALUE:  One of the following values:  unknown, warning,
         testing, down.

         DERIVATION:  The value of zhrmDevUnStatus for the
         device."
        ::= { zhrmTraps 3 }

   zhrmTrapDeviceStateChange TRAP-TYPE
      ENTERPRISE    zhrmTraps
      VARIABLES     {
                     zhrmTrapDeviceStateIndex,
                     zhrmTrapDeviceDescr,
                     zhrmTrapDeviceStatus
                    }
      DESCRIPTION
         "When zhrmDevUnTrapEnable is set to 1, this trap is
         generated whenever the status of any device represented
         in the hrDevice group changes."
      ::= 1

   zhrmTrapStorageThrIndex OBJECT-TYPE
       SYNTAX INTEGER (1..2147483647)
       ACCESS not-accessible
       STATUS mandatory
       DESCRIPTION
         "Index value that points to the entry in the
         hrStorageTable for the device that the trap describes.

         VALUE:  Integer, numbered sequentially starting at 1.

         DERIVATION:  For RAM:  the value of zhrmThrRAMIndex for
                       the RAM storage area.
                      For disks:  the value of zhrmThrDiskIndex
                       for the device."
       ::= { zhrmTraps 4 }

   zhrmTrapStorageDescr OBJECT-TYPE
       SYNTAX DisplayString
       ACCESS read-only
       STATUS mandatory
       DESCRIPTION
         "Description of the type of storage represented by the
         entry.

         VALUE:  For RAM:  number and type of a processor:
                  CPUnn(processor-type) running Dnn.nn.
                 For disks:  The name and type of the disk:
                  $volume(disk-type).

         DERIVATION:  For RAM:  the value of zhrmThrRAMDescr for
                       the RAM storage area.
                      For disks:  the value of zhrmThrDiskDescr
                       for the device."
       ::= { zhrmTraps 5 }

   zhrmRAMThreshold TRAP-TYPE
      ENTERPRISE    zhrmTraps
      VARIABLES     {
                     zhrmTrapStorageThrIndex,
                     zhrmTrapStorageDescr,
                     zhrmThrRAMPercentUse
                    }
      DESCRIPTION
         "When zhrmThrRAMTrapEnable is set to 1, this trap is
         generated whenever the utilization of any RAM storage
         area represented in the hrStorage group reaches or
         exceeds a high threshold (represented by the value of
         zhrmThrRAMHighValue in the zhrmThreshold group) or
         reaches or falls below a low threshold (represented by
         the value of zhrmThrRAMLowValue in the zhrmThreshold
         group."
      ::= 2

   zhrmDiskThreshold TRAP-TYPE
      ENTERPRISE    zhrmTraps
      VARIABLES     {
                     zhrmTrapStorageThrIndex,
                     zhrmTrapStorageDescr,
                     zhrmThrDiskPercentUse
                    }
      DESCRIPTION
         "When zhrmThrDiskTrapEnable is set to 1, this trap is
         generated whenever the utilization of any disk
         represented in the hrStorage group reaches or exceeds a
         high threshold (represented by the value of
         zhrmThrDiskLowValue in the zhrmThreshold group) or
         reaches or falls below a low threshold (represented by
         the value of zhrmThrDiskLowValue in the zhrmThreshold
         group)."
      ::= 3

END -- SNMP-HMSA-MIB
