-- =====================================================================
-- == OPENGEAR-UPS-MIB :                                              ==
-- == Opengear UPS status notification Management Information Base    ==
-- ==                                                                 ==
-- == (c) Copyright 2005-2010 Opengear Inc.                           ==
-- =====================================================================

OPENGEAR-PRODUCTS-MIB DEFINITIONS ::= BEGIN

IMPORTS
	ogProducts, ogModules
		FROM OPENGEAR-SMI-MIB
	MODULE-IDENTITY
		FROM SNMPv2-SMI;

ogProductsMib MODULE-IDENTITY
      LAST-UPDATED "201004151127Z"
      ORGANIZATION "Opengear Inc."
      CONTACT-INFO
              "Opengear Inc.
               630 West 9560 South,
               Sandy, UT 84070
               support@opengear.com"
      DESCRIPTION
              "Opengear Product MIB"
      REVISION "201004151127Z"
      DESCRIPTION
              "Initial version."
      ::= { ogModules 2 }

ogCM4001 OBJECT IDENTIFIER ::= { ogProducts 1 }
ogCM4002 OBJECT IDENTIFIER ::= { ogProducts 2 }
ogCM4008 OBJECT IDENTIFIER ::= { ogProducts 3 }
ogCM41xx OBJECT IDENTIFIER ::= { ogProducts 10 }
ogSD4001 OBJECT IDENTIFIER ::= { ogProducts 20 }
ogSD4002 OBJECT IDENTIFIER ::= { ogProducts 21 }
ogSD4008 OBJECT IDENTIFIER ::= { ogProducts 22 }
ogSD4001DW OBJECT IDENTIFIER ::= { ogProducts 23 }
ogSD4002DX OBJECT IDENTIFIER ::= { ogProducts 24 }
ogCD OBJECT IDENTIFIER ::= { ogProducts 30 }
ogCMx86 OBJECT IDENTIFIER ::= { ogProducts 31 }
ogCMS61xx OBJECT IDENTIFIER ::= { ogProducts 40 }
ogIM4004 OBJECT IDENTIFIER ::= { ogProducts 50 }
ogIM42xx OBJECT IDENTIFIER ::= { ogProducts 60 }
ogKCS61xx OBJECT IDENTIFIER ::= { ogProducts 70 }
ogACM500x OBJECT IDENTIFIER ::= { ogProducts 80 }

END
