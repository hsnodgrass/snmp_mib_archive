-- ***************************************************************************
-- APPACCELERATION-PRODUCTS-MIB.txt: Citrix Systems Application Acceleration
--                                   Product Object Identifier Assignments
--
--
-- Copyright (c) 2004-2013 by Citrix Systems, Inc.
-- All rights reserved.
--
-- ***************************************************************************
--

APPACCELERATION-PRODUCTS-MIB DEFINITIONS ::= BEGIN

IMPORTS
    MODULE-IDENTITY
        FROM SNMPv2-SMI
    appAccelerationModules,
    appAccelerationProducts
        FROM APPACCELERATION-SMI;

appAccelerationProductsMIB MODULE-IDENTITY
    LAST-UPDATED    "201303050000Z"
    ORGANIZATION    "www.citrix.com"
    CONTACT-INFO
            "       Citrix Systems, Inc.
                                                                                
            Postal: 851 West Cypress Creek Road
                    Fort Lauderdale, Florida  33309
                    United States"

    DESCRIPTION
        "This module defines the object identifiers that are
        assigned to various hardware platforms, and hence are
        returned as values for sysObjectID."
    ::= { appAccelerationProducts 2 }


orbital5500      OBJECT IDENTIFIER ::= { appAccelerationProductsMIB 1 }
orbitalLC        OBJECT IDENTIFIER ::= { appAccelerationProductsMIB 2 }
Repeater6500     OBJECT IDENTIFIER ::= { appAccelerationProductsMIB 3 }
Repeater6800     OBJECT IDENTIFIER ::= { appAccelerationProductsMIB 4 }
Repeater8800     OBJECT IDENTIFIER ::= { appAccelerationProductsMIB 5 }
Repeater8500     OBJECT IDENTIFIER ::= { appAccelerationProductsMIB 6 }
dp104a           OBJECT IDENTIFIER ::= { appAccelerationProductsMIB 7 }
Repeater8810     OBJECT IDENTIFIER ::= { appAccelerationProductsMIB 8 }
Repeater8510     OBJECT IDENTIFIER ::= { appAccelerationProductsMIB 9 }
Repeater6510     OBJECT IDENTIFIER ::= { appAccelerationProductsMIB 10 }
Repeater6810     OBJECT IDENTIFIER ::= { appAccelerationProductsMIB 11 }
CloudBridge      OBJECT IDENTIFIER ::= { appAccelerationProductsMIB 12 }
CloudBridge700   OBJECT IDENTIFIER ::= { appAccelerationProductsMIB 13 }
CloudBridgeVPX   OBJECT IDENTIFIER ::= { appAccelerationProductsMIB 14 }
CloudBridgeSDX   OBJECT IDENTIFIER ::= { appAccelerationProductsMIB 15 }
CloudBridge2000  OBJECT IDENTIFIER ::= { appAccelerationProductsMIB 16 }
CloudBridge3000  OBJECT IDENTIFIER ::= { appAccelerationProductsMIB 17 }

END
