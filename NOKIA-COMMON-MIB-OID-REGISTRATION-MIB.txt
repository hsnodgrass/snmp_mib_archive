-- Private Enterprise Codes below ntcCommon subtree
-- 
-- Prefix: iso.org.dod.internet.private.enterprise.nokia.nokiaProducts.ntcCommon (1.3.6.1.4.1.94.1.16)
--
-- Nokia oids imported below are located in 
-- /vob/nnmsc/nms300/MIB/oid/nokia.oid
-- 
-- Version history
-- 21.01.1998 01 MKi Initial version of NTC Common OID subtree, Common Alarm Reporting added 
-- 19.08.1998 02 MKi ASN.1 Module prefix / suffix added.
-- 03.09.1998 03 MKi Subtree for Rate shaping MIB added.
-- 09.09.1998 04 MKi Subtree for rate shaping MIB corrected, one for trap destination added.
-- 24.09.1998 05 MKi New OID subtree structure for Nokia Common MIBs taken into use
-- 29.09.1998 06 MKi Removing comments, adding subtree for ntcHWUnitTypes
-- 08.10.1998 07 MKi Adding subtree for Access Control MIB.


NOKIA-COMMON-MIB-OID-REGISTRATION-MIB DEFINITIONS ::= BEGIN

IMPORTS
    ntcCommon
        FROM NOKIA-OID-REGISTRATION-MIB;

-- OIDs allocated to NTC Common MIB modules

ntcCommonAlarm           OBJECT IDENTIFIER ::= { ntcCommon 1 } -- Mika Kiikkila
ntcCommonAlarmTrap       OBJECT IDENTIFIER ::= { ntcCommon 2 } -- Mika Kiikkila
ntcCommonTrapDest        OBJECT IDENTIFIER ::= { ntcCommon 3 } -- Trap Destination MIB, Jarkko Lapinlampi
ntcRS                    OBJECT IDENTIFIER ::= { ntcCommon 4 } -- Rate Shaping MIB, Alan Francisco
-- From now on, all forthcoming Nokia Common MIB modules shall be registered below following subtrees
ntcCommonModules         OBJECT IDENTIFIER ::= { ntcCommon 5 }
ntcCommonAgentCaps       OBJECT IDENTIFIER ::= { ntcCommon 6 }
ntcCommonMibs            OBJECT IDENTIFIER ::= { ntcCommon 7 }
ntcCommonReqs            OBJECT IDENTIFIER ::= { ntcCommon 8 }


-- *******************************************************
-- Nokia Common MIB - OID subtree for Module registrations
-- *******************************************************

ntcHWModule              OBJECT IDENTIFIER ::= { ntcCommonModules 1 }
ntcNtpModule             OBJECT IDENTIFIER ::= { ntcCommonModules 2 }
ntcHWUnitTypeModule      OBJECT IDENTIFIER ::= { ntcCommonModules 3 }
ntcACModule              OBJECT IDENTIFIER ::= { ntcCommonModules 4 } -- Access Control MIB
ntcGprsTracingModule     OBJECT IDENTIFIER ::= { ntcCommonModules 5 } 

-- *****************************************************
-- Nokia Common MIB - OID subtree for Agent Capabilities
-- *****************************************************

ntcHWAgentCap            OBJECT IDENTIFIER ::= { ntcCommonAgentCaps 1 }
ntcNtpAgentCap           OBJECT IDENTIFIER ::= { ntcCommonAgentCaps 2 }
ntcHWUnitTypeAgentCap    OBJECT IDENTIFIER ::= { ntcCommonAgentCaps 3 }
ntcACAgentCap            OBJECT IDENTIFIER ::= { ntcCommonAgentCaps 4 }
ntcGprsTracingAgentCap   OBJECT IDENTIFIER ::= { ntcCommonAgentCaps 5 } 


-- **********************************************
-- Nokia Common MIB - OID subtree for MIB objects
-- **********************************************

ntcHWMibs                OBJECT IDENTIFIER ::= { ntcCommonMibs 1 }
ntcNtpMibs               OBJECT IDENTIFIER ::= { ntcCommonMibs 2 }
ntcHWUnitTypeMibs        OBJECT IDENTIFIER ::= { ntcCommonMibs 3 }
ntcACMibs                OBJECT IDENTIFIER ::= { ntcCommonMibs 4 }
ntcGprsTracingMibs       OBJECT IDENTIFIER ::= { ntcCommonMibs 5 } 

-- ***********************************************
-- Nokia Common MIB - OID subtree for Requirements
-- ***********************************************

ntcHWReqs                OBJECT IDENTIFIER ::= { ntcCommonReqs 1 }
ntcNtpReqs               OBJECT IDENTIFIER ::= { ntcCommonReqs 2 }
ntcHWUnitTypeReqs        OBJECT IDENTIFIER ::= { ntcCommonReqs 3 }
ntcACReqs                OBJECT IDENTIFIER ::= { ntcCommonReqs 4 }
ntcGprsTracingReqs       OBJECT IDENTIFIER ::= { ntcCommonReqs 5 } 

END
