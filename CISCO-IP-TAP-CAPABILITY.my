-- *****************************************************************
-- CISCO-IP-TAP-CAPABILITY.my:
-- Cisco CISCO-IP-TAP-MIB AGENT-CAPABILITIES
--
-- September 2007, Edward Pham 
--
-- Copyright (c) 2007 by Cisco Systems, Inc.
-- All rights reserved.
-- *****************************************************************

CISCO-IP-TAP-CAPABILITY DEFINITIONS ::= BEGIN

IMPORTS
        MODULE-IDENTITY
                FROM SNMPv2-SMI
        AGENT-CAPABILITIES
                FROM SNMPv2-CONF
        InetAddressType
                FROM INET-ADDRESS-MIB
        ciscoAgentCapability
                FROM CISCO-SMI;

ciscoIpTapCapability MODULE-IDENTITY
        LAST-UPDATED    "200709100000Z"
        ORGANIZATION    "Cisco Systems, Inc."
        CONTACT-INFO
                "       Cisco Systems
                        Customer Service

                Postal: 170 West Tasman Drive
                        San Jose, CA  95134
                        USA

                   Tel: +1 800 553-NETS

                E-mail: cs-li@cisco.com"
        DESCRIPTION
                "The capabilities description of CISCO-IP-TAP-MIB."
        REVISION        "200709100000Z"
        DESCRIPTION
                "Initial version of this MIB module."
        ::= { ciscoAgentCapability 558 }

ciscoIpTapCapV12R0233SXHPCat6k AGENT-CAPABILITIES
    PRODUCT-RELEASE     "Cisco IOS 12.2(33)SXH on Catalyst 6000/6500
                         series devices."
    STATUS              current
    DESCRIPTION         "CISCO-IP-TAP-MIB capabilities."

    SUPPORTS            CISCO-IP-TAP-MIB
        INCLUDES        {
                          ciscoIpTapStreamComplianceGroup 
                        }

        VARIATION       citapStreamCapabilities 
        SYNTAX          BITS { 
                               tapEnable(0), 
                               interface(1),
                               ipV4(2),
                               l4Port(4),
                               dscp(5)
                        }
        DESCRIPTION     "Only limited set of enumerated values are
                        supported."
 
        VARIATION       citapStreamAddrType 
        SYNTAX          InetAddressType { ipv4(1) } 
        DESCRIPTION     "Only limited set of enumerated values are
                        supported."

    ::= { ciscoIpTapCapability 1 }

END
