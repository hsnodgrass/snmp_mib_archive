NOKIA-NE3S-REGISTRATION-MIB DEFINITIONS ::= BEGIN


-- ===============================================================
--     Copyright (C) Nokia Networks 2001-2002
-- ===============================================================
--
--
-- Description:  MIB file for the Nokia OID registration tree
--               used in conjunction with the 
--                    Enhanced SNMP Solution Suite
-- 
-- Protocol:     SNMPv2c MIB (Simple network management protocol,
--               version 2c, Management Information Base  )
-- Format:       SMIv2
--
-- Version 
-- 1.0         : FM PM 
-- 1.3         : CM OID's added
-- 1.3.1       : MIB File renamed, to avoid naming conflict with 
--               Nokia general OID registration MIB.
--               OID for "nokia" and "nokiaSNMPInteface" now imported
--               from general registration MIB, where the OIDis 
--               defined first 
--
-- ===============================================================
-- Author      : M.Grosse-Kreul et. all.
-- Version     : 1.3.1
-- Last Update : 9.1.2002
--================================================================


IMPORTS 
--        enterprises 
--        FROM RFC1155-SMI ;

--        This OID's are defined in Nokia general OID registration
--        file.
--        
--        nokia OBJECT IDENTIFIER ::= { enterprises 94 }
--        nokiaSnmpInterface OBJECT IDENTIFIER ::= { nokia 7 }

        nokiaSnmpInterface
        FROM NOKIA-OID-REGISTRATION-MIB ;


        --======================================================================
        --
        -- Topmost Object Identifier for Fault Management in the 
        -- Enhanced SNMP Solution Suite
        --
        -- OID for Fault Management branch of the Enhanced SNMP Solution Suite
        -- =====================================================================
        noiFaultManagement    OBJECT IDENTIFIER ::= { nokiaSnmpInterface 1 }

        -- ---------------------------------------------------------------------
        -- OID for Interface Modules used within NEe3S
        -- ---------------------------------------------------------------------
        noiOpenInterfaceModule   OBJECT IDENTIFIER ::= { noiFaultManagement 1 }

  
        -- =====================================================================
        -- OID for Fault Management Objects of the Enhanced SNMP Solution Suite
        -- =====================================================================

      -- ---------------------------------------------------------------------
        -- OID for Common Variables used within SNMP based Fault Management
        -- ---------------------------------------------------------------------
        noiFaultManagementVariable    OBJECT IDENTIFIER ::= { noiFaultManagement 2}


        -- ---------------------------------------------------------------------
        -- OID for Notification in SNMP based Fault Management
        -- ---------------------------------------------------------------------
        noiAlarmNotificationDef    OBJECT IDENTIFIER ::= { noiFaultManagement 3 }
        noiAlarmNotification       OBJECT IDENTIFIER ::= { noiAlarmNotificationDef 0 }


        -- ---------------------------------------------------------------------
        -- OID for alarm table in SNMP based Fault Management
        -- ---------------------------------------------------------------------
        noiAlarmTables          OBJECT IDENTIFIER ::= { noiFaultManagement 4 }
 

        -- ---------------------------------------------------------------------
        -- OID for Alarm Log in SNMP based Fault Management
        -- ---------------------------------------------------------------------
        noiAlarmLog           OBJECT IDENTIFIER ::= { noiFaultManagement 5 }

        -- ---------------------------------------------------------------------
        -- OID for Compliance Statement Fault Management
        -- ---------------------------------------------------------------------
        noiFMCompliance       OBJECT IDENTIFIER ::= { noiFaultManagement 6 }


        --===================================================================
        --
        -- Topmost Object Identifier for Configuration Management in the 
        -- Enhanced SNMP Solution Suite
        --
        -- OID for Basic ConfigurationManagement Management branch of the
        -- Enhanced SNMP Solution Suite
        -- ==================================================================
        noiConfigurationManagement    OBJECT IDENTIFIER ::= 
{ nokiaSnmpInterface 2 }


        -- ---------------------------------------------------------------------
        -- OID for Common Variables used within SNMP based Configuration Management
        -- ---------------------------------------------------------------------
        noiConfigurationManagementVariable    OBJECT IDENTIFIER ::= { noiConfigurationManagement 2}


        -- ---------------------------------------------------------------------
        -- OID for Notification in SNMP based ConfigurationManagement Management
        -- ---------------------------------------------------------------------

        noiConfigurationManagementNotificationDef  OBJECT IDENTIFIER ::= { noiConfigurationManagement 3 }
        noiConfigurationManagementNotification     OBJECT IDENTIFIER ::= { noiConfigurationManagementNotificationDef 0 }
        noiConfigurationManagementCompliance       OBJECT IDENTIFIER ::= { noiConfigurationManagement 4 }


        --======================================================================
        --
        -- Topmost Object Identifier for Performance Management
        --
        -- OID for Performance Management branch of the Enhanced SNMP Solution Suite
        -- =====================================================================
        noiPerformanceManagement    OBJECT IDENTIFIER ::= { nokiaSnmpInterface 3 }


        -- ---------------------------------------------------------------------
        -- OID for Common Variables used within SNMP based Performance Management
        -- ---------------------------------------------------------------------
        noiPmVariable    OBJECT IDENTIFIER ::= { noiPerformanceManagement 2}


        -- ---------------------------------------------------------------------
        -- OID for Notification in SNMP based Performance Management
        -- ---------------------------------------------------------------------
        noiPmNotificationDef    OBJECT IDENTIFIER ::= { noiPerformanceManagement 3 }
        noiPmNotification       OBJECT IDENTIFIER ::= { noiPmNotificationDef 0 }


        -- ---------------------------------------------------------------------
        -- OID for tables in SNMP based Performance Management
        -- ---------------------------------------------------------------------
        noiPmTable              OBJECT IDENTIFIER ::= { noiPerformanceManagement 4 }
 

        -- ---------------------------------------------------------------------
        -- OID for Compliance Statement Performance Management
        -- ---------------------------------------------------------------------
        noiPmCompliance       OBJECT IDENTIFIER ::= { noiPerformanceManagement 6 }



END
