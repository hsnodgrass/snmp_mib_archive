-- *****************************************************************
-- ciscoNtpCapabilities MIB
--
-- AGENT-CAPABILITIES mib for CISCO-NTP-MIB 
--
-- April 2003, Michael Sung
--
-- Copyright(c) 2003, 2006 by Cisco Systems,Inc.
--
-- *****************************************************************

CISCO-NTP-CAPABILITY DEFINITIONS ::= BEGIN

IMPORTS
        MODULE-IDENTITY
                FROM SNMPv2-SMI
        AGENT-CAPABILITIES
                FROM SNMPv2-CONF
        ciscoAgentCapability
                FROM CISCO-SMI;   

ciscoNtpCapability MODULE-IDENTITY
        LAST-UPDATED    "200604050000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"

        DESCRIPTION
                "The Agent Capabilities for CISCO-NTP-MIB."

	REVISION "200604050000Z"
	DESCRIPTION
		"Added ciscoNtpCapabilityIOS124"
        REVISION "200506220000Z"
        DESCRIPTION
            "Capability for MDS platform."
        REVISION "200304080000Z"
        DESCRIPTION
            "Initial version of the MIB Module."
        ::= { ciscoAgentCapability 99999 }

ciscoNtpCapabilityV3R00 AGENT-CAPABILITIES
    PRODUCT-RELEASE      "MGX8850 Release 3.00,BPX SES Release "
    STATUS               current
    DESCRIPTION          "NTP MIB Capabilities."

    SUPPORTS CISCO-NTP-MIB
    INCLUDES { ciscoNtpPeersGroup }

        VARIATION   cntpPeersAssocId 
--      ACCESS      not-implemented
        DESCRIPTION "Not supported."

        VARIATION   cntpPeersConfigured 
        ACCESS      not-implemented
        DESCRIPTION "Not supported."

        VARIATION   cntpPeersPeerAddress 
        ACCESS      not-implemented
        DESCRIPTION "Not supported."

        VARIATION   cntpPeersPeerPort 
        ACCESS      not-implemented
        DESCRIPTION "Not supported."

        VARIATION   cntpPeersHostAddress 
        ACCESS      not-implemented
        DESCRIPTION "Not supported."

        VARIATION   cntpPeersHostPort 
        ACCESS      not-implemented
        DESCRIPTION "Not supported."

        VARIATION   cntpPeersLeap 
        ACCESS      not-implemented
        DESCRIPTION "Not supported."

        VARIATION   cntpPeersMode 
        ACCESS      not-implemented
        DESCRIPTION "Not supported."

        VARIATION   cntpPeersStratum 
        DESCRIPTION "Write access is not supported."

        VARIATION   cntpPeersPeerPoll 
        ACCESS      not-implemented
        DESCRIPTION "Not supported."

        VARIATION   cntpPeersHostPoll 
        ACCESS      not-implemented
        DESCRIPTION "Not supported."

        VARIATION   cntpPeersPrecision 
        ACCESS      not-implemented
        DESCRIPTION "Not supported."

        VARIATION   cntpPeersRootDelay 
        ACCESS      not-implemented
        DESCRIPTION "Not supported."

        VARIATION   cntpPeersRootDispersion 
        ACCESS      not-implemented
        DESCRIPTION "Not supported."

        VARIATION   cntpPeersRefId 
        ACCESS      not-implemented
        DESCRIPTION "Not supported."

        VARIATION   cntpPeersRefTime 
        ACCESS      not-implemented
        DESCRIPTION "Not supported."

        VARIATION   cntpPeersOrgTime 
        ACCESS      not-implemented
        DESCRIPTION "Not supported."

        VARIATION   cntpPeersReceiveTime 
        ACCESS      not-implemented 
        DESCRIPTION "Not supported."

        VARIATION   cntpPeersTransmitTime
        ACCESS      not-implemented 
        DESCRIPTION "Not supported."

        VARIATION   cntpPeersUpdateTime
        ACCESS      not-implemented 
        DESCRIPTION "Not supported."

        VARIATION   cntpPeersReach
        ACCESS      not-implemented 
        DESCRIPTION "Not supported."

        VARIATION   cntpPeersTimer
        ACCESS      not-implemented 
        DESCRIPTION "Not supported."

        VARIATION   cntpPeersOffset
        ACCESS      not-implemented 
        DESCRIPTION "Not supported."

        VARIATION   cntpPeersDelay
        ACCESS      not-implemented 
        DESCRIPTION "Not supported."

        VARIATION   cntpPeersDispersion
        ACCESS      not-implemented 
        DESCRIPTION "Not supported."

        VARIATION   cntpPeersFilterValidEntries
        ACCESS      not-implemented 
        DESCRIPTION "Not supported."

        VARIATION   cntpPeersEntryStatus
        ACCESS      not-implemented 
        DESCRIPTION "Not supported."

    ::= { ciscoNtpCapability 1 }

ciscoNtpCapabilitySANOSV3R0001 AGENT-CAPABILITIES
    PRODUCT-RELEASE      "SAN-OS 3.0(1) "
    STATUS               current
    DESCRIPTION          "NTP MIB Capabilities for 
                          SAN-OS 3.0(1)."

    SUPPORTS CISCO-NTP-MIB
    INCLUDES { ciscoNtpPeersGroupRev2,
               ciscoNtpPeerExtGroup,
               ciscoNtpSysGroup }

        VARIATION       cntpSysLeap
        ACCESS          read-only
        DESCRIPTION     "read-write is not supported"

        VARIATION       cntpSysStratum
        ACCESS          read-only
        DESCRIPTION     "read-write is not supported"

        VARIATION       cntpPeersHostAddress
        ACCESS          read-only
        DESCRIPTION     "read-create is not supported"

    ::= { ciscoNtpCapability 2 }


ciscoNtpCapabilityIOS124  AGENT-CAPABILITIES
    PRODUCT-RELEASE	 "IOS 12.4"
    STATUS		 current
    DESCRIPTION          "NTP MIB Capabilities for
			  IOS 12.4 release"
    SUPPORTS CISCO-NTP-MIB
    INCLUDES { ciscoNtpPeersGroupRev2,
               ciscoNtpPeerExtGroup,
               ciscoNtpSysGroup }

        VARIATION   cntpPeersPeerName
        ACCESS      not-implemented
        DESCRIPTION "Not Supported"

        VARIATION   cntpPeersPeerType
        ACCESS      not-implemented
        DESCRIPTION "Not Supported"
   ::= { ciscoNtpCapability 3 }

END
