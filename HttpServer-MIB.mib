HttpServer-MIB DEFINITIONS ::= BEGIN

        IMPORTS
                enterprises,
                OBJECT-TYPE,
                Counter
                        FROM RFC1155-SMI
                internetServer
                        FROM InternetServer-MIB;

--      microsoft       OBJECT IDENTIFIER ::= { enterprises 311 }
--      software        OBJECT IDENTIFIER ::= { microsoft 1 }
--      internetServer  OBJECT IDENTIFIER ::= { software 7 }
        httpServer      OBJECT IDENTIFIER ::= { internetServer 3 }
        httpStatistics  OBJECT IDENTIFIER ::= { httpServer 1 }

-- Http Server Statistics

        totalBytesSentHighWord OBJECT-TYPE
                SYNTAX  Counter
                ACCESS  read-only
                STATUS  mandatory
                DESCRIPTION
                        "This is the high 32-bits of the total number of
                        of BYTEs sent by the Http Server"
                ::= { httpStatistics 1 }

        totalBytesSentLowWord OBJECT-TYPE
                SYNTAX  Counter
                ACCESS  read-only
                STATUS  mandatory
                DESCRIPTION
                        "This is the low 32-bits of the total number of
                        of BYTEs sent by the Http Server"
                ::= { httpStatistics 2 }

        totalBytesReceivedHighWord OBJECT-TYPE
                SYNTAX  Counter
                ACCESS  read-only
                STATUS  mandatory
                DESCRIPTION
                        "This is the high 32-bits of the total number of
                        of BYTEs received by the Http Server"
                ::= { httpStatistics 3 }

        totalBytesReceivedLowWord OBJECT-TYPE
                SYNTAX  Counter
                ACCESS  read-only
                STATUS  mandatory
                DESCRIPTION
                        "This is the low 32-bits of the total number of
                        of BYTEs received by the Http Server"
                ::= { httpStatistics 4 }

        totalFilesSent OBJECT-TYPE
                SYNTAX  Counter
                ACCESS  read-only
                STATUS  mandatory
                DESCRIPTION
                        "This is the total number of files sent by this
                        Http Server"
                ::= { httpStatistics 5 }

        currentAnonymousUsers OBJECT-TYPE
                SYNTAX  INTEGER
                ACCESS  read-only
                STATUS  mandatory
                DESCRIPTION
                        "This is the number of anonymous users currently
                        connected to the Http Server"
                ::= { httpStatistics 6 }

        currentNonAnonymousUsers OBJECT-TYPE
                SYNTAX  INTEGER
                ACCESS  read-only
                STATUS  mandatory
                DESCRIPTION
                        "This is the number of nonanonymous users currently
                        connected to the Http Server"
                ::= { httpStatistics 7  }

        totalAnonymousUsers OBJECT-TYPE
                SYNTAX  Counter
                ACCESS  read-only
                STATUS  mandatory
                DESCRIPTION
                        "This is the total number of anonymous users that
                        have ever connected to the Http Server"
                ::= { httpStatistics 8  }

        totalNonAnonymousUsers OBJECT-TYPE
                SYNTAX  Counter
                ACCESS  read-only
                STATUS  mandatory
                DESCRIPTION
                        "This is the total number of nonanonymous users that
                        have ever connected to the Http Server"
                ::= { httpStatistics 9  }

        maxAnonymousUsers OBJECT-TYPE
                SYNTAX  Counter
                ACCESS  read-only
                STATUS  mandatory
                DESCRIPTION
                        "This is the maximum number of anonymous users
                        simultaneously connected to the Http Server"
                ::= { httpStatistics 10 }

        maxNonAnonymousUsers OBJECT-TYPE
                SYNTAX  Counter
                ACCESS  read-only
                STATUS  mandatory
                DESCRIPTION
                        "This is the maximum number of nonanonymous users
                        simultaneously connected to the Http Server"
                ::= { httpStatistics 11 }

        currentConnections OBJECT-TYPE
                SYNTAX  INTEGER
                ACCESS  read-only
                STATUS  mandatory
                DESCRIPTION
                        "This is the current number of connections to the
                        Http Server"
                ::= { httpStatistics 12 }

        maxConnections OBJECT-TYPE
                SYNTAX  Counter
                ACCESS  read-only
                STATUS  mandatory
                DESCRIPTION
                        "This is the maximum number of simultaneous
                        connections to the Http Server"
                ::= { httpStatistics 13 }

        connectionAttempts OBJECT-TYPE
                SYNTAX  Counter
                ACCESS  read-only
                STATUS  mandatory
                DESCRIPTION
                        "This is the number of connection attempts that
                        have been made to the Http Server"
                ::= { httpStatistics 14 }

        logonAttempts OBJECT-TYPE
                SYNTAX  Counter
                ACCESS  read-only
                STATUS  mandatory
                DESCRIPTION
                        "This is the number of logon attempts that have
                        been made to this Http Server"
                ::= { httpStatistics 15 }

        totalGets OBJECT-TYPE
                SYNTAX  Counter
                ACCESS  read-only
                STATUS  mandatory
                DESCRIPTION
                        "This is the number of requests using the GET method
                        that have been made to this Http Server"
                ::= { httpStatistics 16 }

        totalPosts OBJECT-TYPE
                SYNTAX  Counter
                ACCESS  read-only
                STATUS  mandatory
                DESCRIPTION
                        "This is the number of requests using the POST
method
                        that have been made to this Http Server"
                ::= { httpStatistics 17 }

        totalHeads OBJECT-TYPE
                SYNTAX  Counter
                ACCESS  read-only
                STATUS  mandatory
                DESCRIPTION
                        "This is the number of requests using the HEAD
method
                        that have been made to this Http Server"
                ::= { httpStatistics 18 }

        totalOthers OBJECT-TYPE
                SYNTAX  Counter
                ACCESS  read-only
                STATUS  mandatory
                DESCRIPTION
                        "This is the number of requests not using the GET,
                        POST or HEAD method that have been made to this Http
                        Server"
                ::= { httpStatistics 19 }

        totalCGIRequests OBJECT-TYPE
                SYNTAX  Counter
                ACCESS  read-only
                STATUS  mandatory
                DESCRIPTION
                        "This is the number of Common Gateway Interface
(CGI)
                        requests that have been made to this Http Server"
                ::= { httpStatistics 20 }

        totalBGIRequests OBJECT-TYPE
                SYNTAX  Counter
                ACCESS  read-only
                STATUS  mandatory
                DESCRIPTION
                        "This is the number of Binary Gateway Interface
(BGI)
                        requests that have been made to this Http Server"
                ::= { httpStatistics 21 }

        totalNotFoundErrors OBJECT-TYPE
                SYNTAX  Counter
                ACCESS  read-only
                STATUS  mandatory
                DESCRIPTION
                        "This is the number of requests the Http server
could
                        not satisfy because the requested resource could not
                        be found"
                ::= { httpStatistics 22 }

END
