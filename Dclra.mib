-- HIP Version = X131 
--  
-- MIB generated by miftomib version 1.0a

DELLLOCALRESPONSEAGENTMIF-MIB DEFINITIONS ::= BEGIN

-- This is the MIF for the Dell automatic response agent

IMPORTS
    OBJECT-TYPE
    FROM RFC-1212
    enterprises
    FROM RFC1155-SMI
    DisplayString
    FROM RFC1213-MIB;

DmiInteger			::= INTEGER
DmiDisplaystring	::= DisplayString
DmiDate				::= OCTET STRING (SIZE (28))
DmiComponentIndex	::= INTEGER

dell                	OBJECT IDENTIFIER ::= {enterprises 674}
server             	OBJECT IDENTIFIER ::= {dell 10890}
localresponseagent      	OBJECT IDENTIFIER ::= {server 3}
dmtfGroups          	OBJECT IDENTIFIER ::= {localresponseagent 1}

SComponentid ::= SEQUENCE {
	a1Manufacturer                          	DmiDisplaystring,
	a1Product                               	DmiDisplaystring,
	a1Version                               	DmiDisplaystring,
	a1SerialNumber                          	DmiDisplaystring,
	a1Installation                          	DmiDate,
	a1Verify                                	DmiInteger
}

tComponentid OBJECT-TYPE
	SYNTAX		SEQUENCE OF SComponentid
	ACCESS		not-accessible
	STATUS		mandatory
	DESCRIPTION	"This group defines attributes common to all components."
	::= {dmtfGroups 1}

eComponentid OBJECT-TYPE
	SYNTAX		SComponentid
	ACCESS		not-accessible
	STATUS		mandatory
	DESCRIPTION	""
	INDEX		{DmiComponentIndex}
	::= {tComponentid 1}

a1Manufacturer OBJECT-TYPE
	SYNTAX		DmiDisplaystring
	ACCESS		read-only
	STATUS		mandatory
	DESCRIPTION	"The name of the manufacturer that produced this component."
	::= {eComponentid 1}

a1Product OBJECT-TYPE
	SYNTAX		DmiDisplaystring
	ACCESS		read-only
	STATUS		mandatory
	DESCRIPTION	"The name of the component."
	::= {eComponentid 2}

a1Version OBJECT-TYPE
	SYNTAX		DmiDisplaystring
	ACCESS		read-only
	STATUS		mandatory
	DESCRIPTION	"The version for the component."
	::= {eComponentid 3}

a1SerialNumber OBJECT-TYPE
	SYNTAX		DmiDisplaystring
	ACCESS		read-only
	STATUS		mandatory
	DESCRIPTION	"The serial number for this instance of this component."
	::= {eComponentid 4}

a1Installation OBJECT-TYPE
	SYNTAX		DmiDate
	ACCESS		read-only
	STATUS		mandatory
	DESCRIPTION	"The time & date of the lastest installation of this component."
	::= {eComponentid 5}

a1Verify OBJECT-TYPE
	SYNTAX		INTEGER {
		vAnErrorOccurredCheckStatusCode         	(0),
		vThisComponentDoesNotExist              	(1),
		vTheVerifyIsNotSupported                	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is still installed and working."
	::= {eComponentid 6}

SActionResponseTable ::= SEQUENCE {
	a2Actionname                            	DmiInteger,
	a2Actionresponse                        	DmiDisplaystring,
	a2Actionexecute                         	DmiDisplaystring,
	a2Actionsource                          	DmiDisplaystring
}

tActionResponseTable OBJECT-TYPE
	SYNTAX		SEQUENCE OF SActionResponseTable
	ACCESS		not-accessible
	STATUS		mandatory
	DESCRIPTION	"This table describes the actions to be performed whenever
a particular indication is generated."
	::= {dmtfGroups 2}

eActionResponseTable OBJECT-TYPE
	SYNTAX		SActionResponseTable
	ACCESS		not-accessible
	STATUS		mandatory
	DESCRIPTION	""
	INDEX		{DmiComponentIndex, a2Actionname}
	::= {tActionResponseTable 1}

a2Actionname OBJECT-TYPE
	SYNTAX		INTEGER {
		vUnknown                                	(0),
		vAdaptec-HostAdapterFailed              	(3),
		vAdaptec-LogicalUnitFailed              	(7),
		vApc-SystemOnLowUtilityPower            	(13),
		vApc-SystemOnLowBatteryPower            	(14),
		vTemperatureSensorDetectedAFailure      	(160),
		vFanSensorDetectedAFailure              	(168),
		vVoltageSensorDetectedAFailure          	(172),
		vTemperatureSensorWarningDetected       	(200),
		vVoltageSensorWarningDetected           	(202),
		vFanSensorWarningDetected               	(204),
		vCurrentSensorDetectedAFailure          	(206),
		vCurrentSensorWarningDetected           	(208),
		vPowerSupplyLostRedundancyDetected      	(210),
		vPowerSupplyDegradedRedundancyDetected  	(212),
		vPowerSupplyDetectedAFailure            	(214),
		vChassisIntrusionDetected               	(220),
		vLostConnectionToDiskPod                	(225)
	}
	ACCESS		read-only
	STATUS		mandatory
	DESCRIPTION	"This specifies the Dell trap which generates the action"
	::= {eActionResponseTable 1}

a2Actionresponse OBJECT-TYPE
	SYNTAX		DmiDisplaystring
	ACCESS		read-write
	STATUS		mandatory
	DESCRIPTION	"This is a secure bit field which specifies which actions
are to be performed.Bitfield is as follows:   0x001 = Beep  0x002 = Console
Alert  0x004 = Broadcast  0x008 = Shutdown OS  0x010 = Reset  0x020 = Power
Cycle  0x040 = Power Off  0x080 = Log Reset/PowerCycle/PowerOff  0x100 =
Execute Application (uses actionExecute string)"
	::= {eActionResponseTable 2}

a2Actionexecute OBJECT-TYPE
	SYNTAX		DmiDisplaystring
	ACCESS		read-write
	STATUS		mandatory
	DESCRIPTION	"This takes an argument of the application to execute & arguments
if the Execute Application bit is set.  Specialized argument fields exist:
 %A - Address of MIF generating alert: cid,gid,(keys) %N - Name of alert
(Temperature sensor detected a failure) %L - Location of alert (Harrier 1
<Backplane Top>) %T - Trap number of alert (260) %S - Severity of alert"
	::= {eActionResponseTable 3}

a2Actionsource OBJECT-TYPE
	SYNTAX		DmiDisplaystring
	ACCESS		read-only
	STATUS		mandatory
	DESCRIPTION	"This contains a combined key for mapping non-dell indications
to a LRA format. Format is: MIFNAME;GID;KEY;AID;# MIFNAME - Text name of
MIF GID     - Group ID KEY     - Row index AID     - Attribute ID #     
 - Trap number to map to"
	::= {eActionResponseTable 4}

SActionCapabilities ::= SEQUENCE {
	a3LraCapabilities                       	DmiInteger
}

tActionCapabilities OBJECT-TYPE
	SYNTAX		SEQUENCE OF SActionCapabilities
	ACCESS		not-accessible
	STATUS		mandatory
	DESCRIPTION	"This class's attribute describes which LRA capabilities can
be performed on this machine."
	::= {dmtfGroups 3}

eActionCapabilities OBJECT-TYPE
	SYNTAX		SActionCapabilities
	ACCESS		not-accessible
	STATUS		mandatory
	DESCRIPTION	""
	INDEX		{DmiComponentIndex}
	::= {tActionCapabilities 1}

a3LraCapabilities OBJECT-TYPE
	SYNTAX		DmiInteger
	ACCESS		read-only
	STATUS		mandatory
	DESCRIPTION	"This value describes what LRA actions may be taken on this
system."
	::= {eActionCapabilities 1}

SMiftomib ::= SEQUENCE {
	a99DellLocalResponseAgentMib            	DmiDisplaystring,
	a99MibOid                               	DmiDisplaystring,
	a99DisableTraps                         	DmiInteger
}

tMiftomib OBJECT-TYPE
	SYNTAX		SEQUENCE OF SMiftomib
	ACCESS		not-accessible
	STATUS		mandatory
	DESCRIPTION	"This group maps the DMI attributes to SNMP."
	::= {dmtfGroups 99}

eMiftomib OBJECT-TYPE
	SYNTAX		SMiftomib
	ACCESS		not-accessible
	STATUS		mandatory
	DESCRIPTION	""
	INDEX		{DmiComponentIndex}
	::= {tMiftomib 1}

a99DellLocalResponseAgentMib OBJECT-TYPE
	SYNTAX		DmiDisplaystring
	ACCESS		read-only
	STATUS		mandatory
	DESCRIPTION	"The MIB name that defines thif MIF"
	::= {eMiftomib 1}

a99MibOid OBJECT-TYPE
	SYNTAX		DmiDisplaystring
	ACCESS		read-only
	STATUS		mandatory
	DESCRIPTION	"The MIB OID that corresponds to this MIF"
	::= {eMiftomib 2}

a99DisableTraps OBJECT-TYPE
	SYNTAX		DmiInteger
	ACCESS		read-only
	STATUS		mandatory
	DESCRIPTION	"Setting this value to 1 disables trap generation."
	::= {eMiftomib 3}


END
