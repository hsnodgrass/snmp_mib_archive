Intel-Common-MIB DEFINITIONS ::= BEGIN

IMPORTS
    enterprises FROM RFC1155-SMI;

-- Categories

intel               OBJECT IDENTIFIER ::=   { enterprises 343 }

-- 
-- Intel Private space divides into 3 branches at the top. They are
-- identifiers, products, and experimental.  
-- 
-- 'identifers' branch typically contains objects which are used as
-- constants.  For example, if a mib contained an object identifier
-- "appliance-type", somewhere down under identifiers would be a list
-- containing OIDs for "refrigerator", "toaster", etc.  Currently
-- there are 3 groups under identifiers; systems, objects and
-- comm-methods.
-- 'systems' contains objects for system type such as PCs, hubs, etc.
-- 'objects' contains identifiers for component pieces.  
-- 'comm-methods' refers to the transmission medium used in 
-- proxy-to-agent conversation.
-- 
-- 'products' branch contains objects which are specifically Intel
-- products.  Under this branch go all MIBs for Intel products.
-- 
-- 'experimental' is for exactly what the name implies.
--  
-- 'information-technology' encompasses the work of the Information 
-- Technology (IT) group within Intel. 
--  
-- For example, an identifier for a toaster would exist under
-- 'identifiers.systems.toasters' while another identifier for an
-- Intel specific toaster MIB would live under 'products.appliances'.
-- 

identifiers         OBJECT IDENTIFIER ::=   { intel 1 }
products            OBJECT IDENTIFIER ::=   { intel 2 }
experimental        OBJECT IDENTIFIER ::=   { intel 3 }
information-technology  OBJECT IDENTIFIER ::=   { intel 4 }

-- Groups under 'identifiers'

systems             OBJECT IDENTIFIER ::=   { identifiers 1 }
objects             OBJECT IDENTIFIER ::=   { identifiers 2 }
comm-methods        OBJECT IDENTIFIER ::=   { identifiers 3 }

pc-systems          OBJECT IDENTIFIER ::=   { systems 1 }
proxy-systems       OBJECT IDENTIFIER ::=   { systems 2 }
hub-systems         OBJECT IDENTIFIER ::=   { systems 3 }

local-proxy-1       OBJECT IDENTIFIER ::=   { comm-methods 1 }
pc-novell-1         OBJECT IDENTIFIER ::=   { comm-methods 2 }

-- Identifiers for 'hub-systems'
-- Note: These items match the definitions for moduleType
--       in intelhub.mib.

express10-100Stack  OBJECT IDENTIFIER ::=   { hub-systems 1 }
express12TX         OBJECT IDENTIFIER ::=   { hub-systems 2 }
express24TX         OBJECT IDENTIFIER ::=   { hub-systems 3 }
expressReserved     OBJECT IDENTIFIER ::=   { hub-systems 4 }
expressMgmt         OBJECT IDENTIFIER ::=   { hub-systems 5 }
expressBridge       OBJECT IDENTIFIER ::=   { hub-systems 6 }
express210-12       OBJECT IDENTIFIER ::=   { hub-systems 7 }
express210-24       OBJECT IDENTIFIER ::=   { hub-systems 8 }
express220-12       OBJECT IDENTIFIER ::=   { hub-systems 9 }
express220-24       OBJECT IDENTIFIER ::=   { hub-systems 10 }

-- Groups under 'products'

pc-products         OBJECT IDENTIFIER ::=   { products 1 }
hub-products        OBJECT IDENTIFIER ::=   { products 2 }
proxy               OBJECT IDENTIFIER ::=   { products 3 }
print-products      OBJECT IDENTIFIER ::=   { products 4 }
network-products    OBJECT IDENTIFIER ::=   { products 5 }
snmp-agents         OBJECT IDENTIFIER ::=   { products 6 }
nic-products        OBJECT IDENTIFIER ::=   { products 7 }

-- Groups under 'hub-products'

express110          OBJECT IDENTIFIER ::=   { hub-products 1 }

-- Groups under 'print-products'

netport-1           OBJECT IDENTIFIER ::=   { print-products 1 }
netport-2           OBJECT IDENTIFIER ::=   { print-products 2 }
netport-express     OBJECT IDENTIFIER ::=   { print-products 3 }

-- Groups under 'network-products'

lanDesk             OBJECT IDENTIFIER ::=   { network-products 1 }
ld-alarms           OBJECT IDENTIFIER ::=   { lanDesk 1 }
internetServer-2    OBJECT IDENTIFIER ::=   { network-products 2 }
iS-alarms           OBJECT IDENTIFIER ::=   { internetServer-2 1 }

-- Groups under 'experimental'

-- <none>

--

END
