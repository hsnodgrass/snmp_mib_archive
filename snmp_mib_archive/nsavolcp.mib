-- ****************************************************************************
--
--                       HP Storage Capacity
--      Management Information Base for SNMP Network Management
--
--      Version Q.01.02 (9/28/94)
-- 
--      Copyright 1994 Hewlett-Packard Company.
--      All Rights Reserved.
--
--      The information in this document is subject to change without notice.
--
--      The HP Enterprise number is 11.
--      The ASN.1 prefix to, and including the HP Enterprise is:
--      1.3.6.1.4.1.11
--
-- ****************************************************************************
-- Summary of HP NSA Storage Capacity Information MIB
-- ****************************************************************************
--
-- hp  (1.3.6.1.4.1.11)
--    nm  (1.3.6.1.4.1.11.2)
--       hpnsa  (1.3.6.1.4.1.11.2.23)
--          hpnsaStorageCap Group     (hpnsa.15)
--             hpnsaSCMibRev Group    (hpnsa.15.1)             
--                hpnsaSCMibRevMajor  (hpnsa.15.1.1)  
--                hpnsaSCMibRevMinor  (hpnsa.15.1.2)
--
--             hpnsaSCAgent Group            (hpnsa.15.2)
--                hpnsaSCAgentTable          (hpnsa.15.2.1)
--                   hpnsaSCAgentEntry       (hpnsa.15.2.1.1)
--                      hpnsaSCAgentIndex    (hpnsa.15.2.1.1.1)
--                      hpnsaSCAgentName     (hpnsa.15.2.1.1.2)
--                      hpnsaSCAgentVersion  (hpnsa.15.2.1.1.3)
--                      hpnsaSCAgentDate     (hpnsa.15.2.1.1.4)
--
--             hpnsaSCDrv (hpnsa.15.3)
--                hpnsaSCDrvNumOfDrives                  (hpnsa.15.3.1)
--                hpnsaSCDrvTable                        (hpnsa.15.3.2)
--                   hpnsaSCDrvEntry                     (hpnsa.15.3.2.1)
--                      hpnsaSCDrvIndex                  (hpnsa.15.3.2.1.1)
--                      hpnsaSCDrvName                   (hpnsa.15.3.2.1.2)
--                      hpnsaSCDrvTrapsEnabled           (hpnsa.15.3.2.1.3)
--                      hpnsaSCDrvTrapsPollTime          (hpnsa.15.3.2.1.4)
--                      hpnsaSCDrvHistSampleTime         (hpnsa.15.3.2.1.5)
--                      hpnsaSCDrvLoThreshold            (hpnsa.15.3.2.1.6)
--                      hpnsaSCDrvWarnThreshold          (hpnsa.15.3.2.1.7)
--                      hpnsaSCDrvCritThreshold          (hpnsa.15.3.2.1.8)
--                      hpnsaSCDrvTotalNumDirEntries     (hpnsa.15.3.2.1.9)
--                      hpnsaSCDrvTotalNumDirEntriesUsed (hpnsa.15.3.2.1.10)
--                      hpnsaSCDrvCurrentTotal           (hpnsa.15.3.2.1.11) 
--                      hpnsaSCDrvCurrentAvailable       (hpnsa.15.3.2.1.12) 
--                      hpnsaSCDrvNumOfSamples           (hpnsa.15.3.2.1.13)
--                      hpnsaSCDrvClearHist              (hpnsa.15.3.2.1.14)
--
--             hpnsaSCHist                      (hpnsa.15.4)
--                hpnsaSCHistTable              (hpnsa.15.4.1)
--                   hpnsaSCHistEntry           (hpnsa.15.4.1.1)
--                      hpnsaSCHistDriveIndex   (hpnsa.15.4.1.1.1)
--                      hpnsaSCHistIndex        (hpnsa.15.4.1.1.2)
--                      hpnsaSCHistSample       (hpnsa.15.4.1.1.3)
--
-- Note: The phrase Storage Capacity has been abbreviated to the letters
--       "SC" to make the names more readable.
--
-- ******************************************************************************
HPNSASTORAGECAP-MIB DEFINITIONS ::= BEGIN
   IMPORTS
      enterprises    FROM RFC1155-SMI
      DisplayString  FROM RFC1213-MIB
		OBJECT-TYPE    FROM RFC-1212;
		
   hp              OBJECT IDENTIFIER ::= { enterprises 11 }
   nm              OBJECT IDENTIFIER ::= { hp 2 }
   hpnsa           OBJECT IDENTIFIER ::= { nm 23 }  
   hpnsaStorageCap OBJECT IDENTIFIER ::= { hpnsa 15 }
   hpnsaSCMibRev   OBJECT IDENTIFIER ::= { hpnsaStorageCap 1 }
   hpnsaSCAgent    OBJECT IDENTIFIER ::= { hpnsaStorageCap 2 }      
   hpnsaSCDrv      OBJECT IDENTIFIER ::= { hpnsaStorageCap 3 }      
   hpnsaSCHist     OBJECT IDENTIFIER ::= { hpnsaStorageCap 4 }      

-- ****************************************************************************
--   HP Storage Cap Information MIB 
--   ======================================
--
-- hp  (1.3.6.1.4.1.11)
--    nm  (1.3.6.1.4.1.11.2)
--       hpnsa  (1.3.6.1.4.1.11.2.23)
--          hpnsaStorageCap Group  (hpnsa.15)
--             hpnsaSCMibRev Group  (hpnsa.15.1)             
--                hpnsaSCMibRevMajor  (hpnsa.15.1.1)  
--                hpnsaSCMibRevMinor  (hpnsa.15.1.2)
--
--    Implementation of the MibRev group is mandatory for all HPNSA Agents
--    supporting the HP Storage Capacity MIB.
--
--    An HPNSA Agent conforming to this document will return a
--    hpnsaSCMibRevMajor of 1 and a hpnsaSCMibRevMinor of 0. 
--
-- ****************************************************************************

    hpnsaSCMibRevMajor OBJECT-TYPE
        SYNTAX  INTEGER (1..65535)
        ACCESS  read-only
        STATUS  mandatory
        DESCRIPTION
            "The major revision level of the MIB."
        ::= { hpnsaSCMibRev 1 }

    hpnsaSCMibRevMinor OBJECT-TYPE
        SYNTAX  INTEGER (0..65535)
        ACCESS  read-only
        STATUS  mandatory
        DESCRIPTION
            "The minor revision level of the MIB."
        ::= { hpnsaSCMibRev 2 }

  
-- ****************************************************************************
--   HP Storage Capacity MIB Agent Information
--   =========================================
--
-- hp  (1.3.6.1.4.1.11)
--    nm  (1.3.6.1.4.1.11.2)
--       hpnsa  (1.3.6.1.4.1.11.2.23)
--          hpnsaStorageCap Group  (hpnsa.15)
--             hpnsaSCAgent Group  (hpnsa.15.2)
--
--                hpnsaSCAgentTable          (hpnsa.15.2.1)
--                   hpnsaSCAgentEntry       (hpnsa.15.2.1.1)
--                      hpnsaSCAgentIndex    (hpnsa.15.2.1.1.1)
--                      hpnsaSCAgentName     (hpnsa.15.2.1.1.2)
--                      hpnsaSCAgentVersion  (hpnsa.15.2.1.1.3)
--                      hpnsaSCAgentDate     (hpnsa.15.2.1.1.4)
--
--  Implementation of the hpnsaSCAgent group is mandatory for all
--  HPNSA Agents that support the Storage Capacity MIB.
--
-- ****************************************************************************
--   HP Storage Capacity Agent Module Table
-- ****************************************************************************

   hpnsaSCAgentTable OBJECT-TYPE
      SYNTAX  SEQUENCE OF HPnsaSCAgentEntry
      ACCESS  not-accessible
      STATUS  mandatory
      DESCRIPTION
         "A table of SNMP Agents that satisfy requests for this MIB."
      ::= { hpnsaSCAgent 1 }

   hpnsaSCAgentEntry OBJECT-TYPE
      SYNTAX  HPnsaSCAgentEntry
      ACCESS  not-accessible
      STATUS  mandatory
      DESCRIPTION
        "A description of the agents that access Storage Capacity
         related information."
      INDEX   { hpnsaSCAgentIndex }
      ::= { hpnsaSCAgentTable 1 }
        
      HPnsaSCAgentEntry ::= SEQUENCE {
         hpnsaSCAgentIndex       INTEGER,
         hpnsaSCAgentName        DisplayString,
         hpnsaSCAgentVersion     DisplayString,
         hpnsaSCAgentDate        OCTET STRING
      }

   hpnsaSCAgentIndex OBJECT-TYPE
      SYNTAX  INTEGER (0..255)
      ACCESS  read-only
      STATUS  mandatory
      DESCRIPTION
          "A unique index for this module description."
      ::= { hpnsaSCAgentEntry 1 }

   hpnsaSCAgentName OBJECT-TYPE
      SYNTAX  DisplayString (SIZE (0..255))
      ACCESS  read-only
      STATUS  mandatory
      DESCRIPTION
         "Name of the Agent/Agents satisfying SNMP requests for this MIB."
      ::= { hpnsaSCAgentEntry 2 }

   hpnsaSCAgentVersion OBJECT-TYPE
      SYNTAX  DisplayString (SIZE (0..5))
      ACCESS  read-only
      STATUS  mandatory
      DESCRIPTION
         "Version number of the Agent/Agents satisfying SNMP requests for
         this MIB."
      ::= { hpnsaSCAgentEntry 3 }

   hpnsaSCAgentDate OBJECT-TYPE
      SYNTAX  OCTET STRING (SIZE (6))
      ACCESS  read-only
      STATUS  mandatory
      DESCRIPTION
         "The date on which this Agent was created.

         field  octets  contents                  range
         _________________________________________________
           1       1    years since 1900          0..255
           2       2    month                     1..12
           3       3    day                       1..31
           4       4    hour                      0..23
           5       5    minute                    0..59  
           6       6    second                    0..59
			 "
      ::= { hpnsaSCAgentEntry 4 }


-- *************************************************************************************
-- hp  (1.3.6.1.4.1.11)
--    nm  (1.3.6.1.4.1.11.2)
--       hpnsa  (1.3.6.1.4.1.11.2.23)
--          hpnsaStorageCap Group  (hpnsa.15)
--             hpnsaSCDrv Group  (hpnsa.15.3)
--
--                hpnsaSCDrvNumOfDrives                  (hpnsa.15.3.1)
--                hpnsaSCDrvTable                        (hpnsa.15.3.2)
--                   hpnsaSCDrvEntry                     (hpnsa.15.3.2.1)
--                      hpnsaSCDrvIndex                  (hpnsa.15.3.2.1.1)
--                      hpnsaSCDrvName                   (hpnsa.15.3.2.1.2)
--                      hpnsaSCDrvTrapsEnabled           (hpnsa.15.3.2.1.3)
--                      hpnsaSCDrvTrapsPollTime          (hpnsa.15.3.2.1.4)
--                      hpnsaSCDrvHistSampleTime         (hpnsa.15.3.2.1.5)
--                      hpnsaSCDrvLoThreshold            (hpnsa.15.3.2.1.6)
--                      hpnsaSCDrvWarnThreshold          (hpnsa.15.3.2.1.7)
--                      hpnsaSCDrvCritThreshold          (hpnsa.15.3.2.1.8)
--                      hpnsaSCDrvTotalNumDirEntries     (hpnsa.15.3.2.1.9)
--                      hpnsaSCDrvTotalNumDirEntriesUsed (hpnsa.15.3.2.1.10)
--                      hpnsaSCDrvCurrentTotal           (hpnsa.15.3.2.1.11) 
--                      hpnsaSCDrvCurrentAvailable       (hpnsa.15.3.2.1.12) 
--                      hpnsaSCDrvNumOfSamples           (hpnsa.15.3.2.1.13)
--                      hpnsaSCDrvClearHist              (hpnsa.15.3.2.1.14)
-- ****************************************************************************************
--   HP Storage Capacity Drive Information Table
-- ****************************************************************************

   hpnsaSCDrvNumOfDrives OBJECT-TYPE
      SYNTAX INTEGER
      ACCESS read-only
      STATUS mandatory
      DESCRIPTION
         "This specifies the number of logical drives or volumes
         in this system."
      ::= {hpnsaSCDrv 1}

   hpnsaSCDrvTable OBJECT-TYPE
      SYNTAX  SEQUENCE OF HpnsaSCDrvEntry
      ACCESS  not-accessible
      STATUS  mandatory
      DESCRIPTION
          " A table of storage capacity logical drive information entries."
      ::= { hpnsaSCDrv 2 }

   hpnsaSCDrvEntry OBJECT-TYPE
      SYNTAX  HpnsaSCDrvEntry
      ACCESS  not-accessible
      STATUS  mandatory
      DESCRIPTION
          " Storage Capacity logical drive information."
      INDEX   { hpnsaSCDrvIndex }
      ::= { hpnsaSCDrvTable 1 }

      HpnsaSCDrvEntry ::= SEQUENCE {
         hpnsaSCDrvIndex                   INTEGER,
         hpnsaSCDrvName                    DisplayString,
         hpnsaSCDrvTrapsEnabled            INTEGER,
         hpnsaSCDrvTrapsPollTime           INTEGER, 
         hpnsaSCDrvHistSampleTime          INTEGER,
         hpnsaSCDrvLoThreshold             INTEGER,
         hpnsaSCDrvWarnThreshold           INTEGER,
         hpnsaSCDrvCritThreshold           INTEGER,
         hpnsaSCDrvTotalNumDirEntries      INTEGER,
         hpnsaSCDrvTotalNumDirEntriesUsed  INTEGER,
         hpnsaSCDrvCurrentTotal            INTEGER,
         hpnsaSCDrvCurrentAvailable        INTEGER,
         hpnsaSCDrvNumOfSamples            INTEGER,
         hpnsaSCDrvClearHist               INTEGER
         }

   hpnsaSCDrvIndex OBJECT-TYPE
      SYNTAX  INTEGER 
      ACCESS  read-only
      STATUS  mandatory
      DESCRIPTION
          "A unique index for the logical drive."
      ::= { hpnsaSCDrvEntry 1 }

   hpnsaSCDrvName OBJECT-TYPE
      SYNTAX  DisplayString 
      ACCESS  read-only
      STATUS  mandatory
      DESCRIPTION
          "A string indicating the name of the logical drive"
      ::= { hpnsaSCDrvEntry 2 }

   hpnsaSCDrvTrapsEnabled  OBJECT-TYPE
      SYNTAX  INTEGER {
								disabled(0),
                        enabled(1)
                      }
      ACCESS  read-write
      STATUS  mandatory
      DESCRIPTION
         "This parameter specifies whether storage capacity traps
         are generated (enabled 1) or not (disabled 0)."
      ::= {hpnsaSCDrvEntry 3}

   hpnsaSCDrvTrapsPollTime OBJECT-TYPE
      SYNTAX INTEGER
      ACCESS read-write
      STATUS mandatory
      DESCRIPTION
         "This specifies the time in minutes in which a logical
         drive  is polled to check if thresholds have
         been exceeded."
      ::= {hpnsaSCDrvEntry 4}

   hpnsaSCDrvHistSampleTime OBJECT-TYPE
      SYNTAX INTEGER
      ACCESS read-write
      STATUS mandatory
      DESCRIPTION
         "This specifies the time in minutes in which a logical
         drive is sampled to maintain historical data."
      ::= {hpnsaSCDrvEntry 5}

   hpnsaSCDrvLoThreshold OBJECT-TYPE
      SYNTAX INTEGER
      ACCESS read-write
      STATUS mandatory
      DESCRIPTION
         "This specifies the lower threshold (a percentage of the
         total capacity of the logical drive) which has to be
         exceeded to trigger off an informational trap"
      ::= {hpnsaSCDrvEntry 6}

   hpnsaSCDrvWarnThreshold OBJECT-TYPE
      SYNTAX INTEGER
      ACCESS read-write
      STATUS mandatory
      DESCRIPTION
         "This specifies the threshold (a percentage of the
         total capacity of the logical drive) which has to be
         exceeded to trigger off a warning trap"
      ::= {hpnsaSCDrvEntry 7}

   hpnsaSCDrvCritThreshold OBJECT-TYPE
      SYNTAX INTEGER
      ACCESS read-write
      STATUS mandatory
      DESCRIPTION
         "This specifies the threshold (a percentage of the
         total capacity of the logical drive) which has to be
         exceeded to trigger off a critical trap"
      ::= {hpnsaSCDrvEntry 8}

   hpnsaSCDrvTotalNumDirEntries  OBJECT-TYPE
      SYNTAX  INTEGER 
      ACCESS  read-only
      STATUS  optional
      DESCRIPTION
         "Total number of directory entries per logical drive. Only applicable
          to netware"
      ::= {hpnsaSCDrvEntry 9}

   hpnsaSCDrvTotalNumDirEntriesUsed  OBJECT-TYPE
      SYNTAX  INTEGER 
      ACCESS  read-only
      STATUS  optional
      DESCRIPTION
      "Number of directory entries used per logical drive. Only applicable
       to netware"
      ::= {hpnsaSCDrvEntry 10}

   hpnsaSCDrvCurrentTotal  OBJECT-TYPE
      SYNTAX  INTEGER 
      ACCESS  read-only
      STATUS  mandatory
      DESCRIPTION
          "The current total capacity of the logical drive in KB"
      ::= {hpnsaSCDrvEntry 11}


   hpnsaSCDrvCurrentAvailable  OBJECT-TYPE
      SYNTAX  INTEGER 
      ACCESS  read-only
      STATUS  mandatory
      DESCRIPTION
         "The current capacity available on the logical drive in KB"
      ::= {hpnsaSCDrvEntry 12}

   hpnsaSCDrvNumOfSamples  OBJECT-TYPE
      SYNTAX  INTEGER 
      ACCESS  read-only
      STATUS  mandatory
      DESCRIPTION
         "Total number historical samples for the logical drive."
      ::= {hpnsaSCDrvEntry 13}

   hpnsaSCDrvClearHist  OBJECT-TYPE
      SYNTAX  INTEGER 
      ACCESS  read-write
      STATUS  mandatory
      DESCRIPTION
         "Setting this variable to the decimal value 1234 will 
          trigger the agent to immediately delete the samples
          for the logical drive. Getting the value will always
          return a 0.
         "
      ::= {hpnsaSCDrvEntry 14}


-- *************************************************************************************
-- hp  (1.3.6.1.4.1.11)
--    nm  (1.3.6.1.4.1.11.2)
--       hpnsa  (1.3.6.1.4.1.11.2.23)
--          hpnsaStorageCap Group  (hpnsa.15)
--             hpnsaSCHist  (hpnsa.15.4)
--
--                hpnsaSCHistTable              (hpnsa.15.4.1)
--                   hpnsaSCHistEntry           (hpnsa.15.4.1.1)
--                      hpnsaSCHistDriveIndex   (hpnsa.15.4.1.1.1)
--                      hpnsaSCHistIndex        (hpnsa.15.4.1.1.2)
--                      hpnsaSCHistSample       (hpnsa.15.4.1.1.3)
-- *************************************************************************************
--   HP Storage Capacity Drive Historical Samples Table
-- ****************************************************************************

   hpnsaSCHistTable OBJECT-TYPE
      SYNTAX  SEQUENCE OF HpnsaSCHistEntry
      ACCESS  not-accessible
      STATUS  mandatory
      DESCRIPTION
          " A table of storage capacity logical drive information entries."
      ::= { hpnsaSCHist 1 }

   hpnsaSCHistEntry OBJECT-TYPE
      SYNTAX  HpnsaSCHistEntry
      ACCESS  not-accessible
      STATUS  mandatory
      DESCRIPTION
          "Storage Capacity logical drive historical information."
      INDEX   { hpnsaSCHistDriveIndex , hpnsaSCHistIndex }
      ::= { hpnsaSCHistTable 1 }

   HpnsaSCHistEntry ::= SEQUENCE {
      hpnsaSCHistDriveIndex   INTEGER,
      hpnsaSCHistIndex        INTEGER,
      hpnsaSCHistSample       OCTET STRING
      }

   hpnsaSCHistDriveIndex OBJECT-TYPE
      SYNTAX  INTEGER (0..255)
      ACCESS  read-only
      STATUS  mandatory
      DESCRIPTION
         "A unique index for the logical drive."
      ::= { hpnsaSCHistEntry 1 }

   hpnsaSCHistIndex OBJECT-TYPE
      SYNTAX  INTEGER (0..400)
      ACCESS  read-only
      STATUS  mandatory
      DESCRIPTION
         "A unique index for each historical drive sample."
      ::= { hpnsaSCHistEntry 2 }

   hpnsaSCHistSample OBJECT-TYPE
      SYNTAX  OCTET STRING (SIZE (14))
      ACCESS  read-only
      STATUS  mandatory
      DESCRIPTION
         "A block of data containing one historical drive
          sample. The structure of the bytes are:
      
           octets  contents                  range
           __________________________________________

                  Local date and time on 
                  which sample was taken.

             1    years since 1900          0..255
             2    month                     1..12
             3    day                       1..31
             4    hour                      0..23
             5    minute                    0..59  
             6    second                    0..59

           7-10   Total capacity in Kbytes. 
                  The 32-bit integer format 
                  is:

                    Octet 7  (LSB)                  
                    Octet 10 (MSB)

          11-14   Available space in Kbytes.
                  The 32-bit integer format
                  is:

                    Octet 11 (LSB)         
                    Octet 14 (MSB)
          "
     ::= { hpnsaSCHistEntry 3 }


END
