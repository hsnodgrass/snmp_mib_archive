--
-- Tandem SNMP Agent Public MIB definitions.
-- 19-Jan-2001  Sada 10-000721-9307  zagInTdPort object is added.

SNMP-AGENT-PUBLIC-MIB DEFINITIONS ::= BEGIN


   IMPORTS
           enterprises
               FROM RFC1155-SMI
           OBJECT-TYPE
               FROM RFC-1212
           DisplayString
               FROM RFC1213-MIB;

   DateAndTime ::= OCTET STRING (SIZE(8 | 11))
--         A date-time specification for the local time of day.
--         The data type is intended to provide a consistent
--         method of reporting date information.  See RFC 1514.
--
--            field      octets   contents                     range
--            _____      ______   ________                     _____
--              1        1-2      year                         0..65536
--                                (in network byte order)
--              2         3       month                        1..12
--              3         4       day                          1..31
--              4         5       hour                         0..23
--              5         6       minutes                      0..59
--              6         7       seconds                      0..60
--                                (use 60 for leap-second)
--              7         8       deci-seconds                 0..9
--              8         9       direction from UTC           "+"/"-"
--                                (in ascii notation)
--              9         10      hours from UTC               0..11
--             10         11      minutes from UTC             0..59
--
--            Note that if only local time is know, then timezone
--            information (fields 8-10) is not present.

   --  AGENT-MIB

   tandem          OBJECT IDENTIFIER ::= { enterprises 169 }

   nonstopsystems  OBJECT IDENTIFIER ::= { tandem 3 }

   zsmp            OBJECT IDENTIFIER ::= { nonstopsystems 155 }

   zsmpagent       OBJECT IDENTIFIER ::= { zsmp 1 }


   -- **************************************************************
   -- the agent's Internal group
   -- **************************************************************

   zagInternal     OBJECT IDENTIFIER ::= { zsmpagent 7 }


   -- **************************************************************
   -- the agent's Internal group's groups                         --
   -- **************************************************************

   zagInProcess    OBJECT IDENTIFIER  ::= { zagInternal 1 }

   zagInEndpoint   OBJECT IDENTIFIER  ::= { zagInternal 2 }

   zagInProfile    OBJECT IDENTIFIER  ::= { zagInternal 3 }

   zagInTrapdest   OBJECT IDENTIFIER  ::= { zagInternal 4 }

   -- **************************************************************
   -- the agent's Process group
   -- **************************************************************

   zagInProcCurrTime  OBJECT-TYPE
      SYNTAX DisplayString
      ACCESS read-only
      STATUS mandatory
      DESCRIPTION
         "String showing the current time.
          ('month day, year  hours:minutes:seconds.hundreths')"
      ::= { zagInProcess 1 }

   zagInProcVersion   OBJECT-TYPE
      SYNTAX DisplayString
      ACCESS read-only
      STATUS mandatory
      DESCRIPTION
         "String showing the version of the agent."
      ::= { zagInProcess 2 }

   zagInProcName   OBJECT-TYPE
      SYNTAX DisplayString
      ACCESS read-only
      STATUS mandatory
      DESCRIPTION
         "String showing the agent's process name."
      ::= { zagInProcess 3 }

   zagInProcPAID   OBJECT-TYPE
      SYNTAX DisplayString
      ACCESS read-only
      STATUS mandatory
      DESCRIPTION
         "String showing the process access id ('group,user')."
      ::= { zagInProcess 4 }

   zagInProcPrimPID   OBJECT-TYPE
      SYNTAX DisplayString
      ACCESS read-only
      STATUS mandatory
      DESCRIPTION
         "String showing the primary process PID ('cpu,pin')."
      ::= { zagInProcess 5 }

   zagInProcBkupPID   OBJECT-TYPE
      SYNTAX DisplayString
      ACCESS read-only
      STATUS mandatory
      DESCRIPTION
         "String showing the backup process PID ('cpu,pin')."
      ::= { zagInProcess 6 }

   zagInProcCreatTime OBJECT-TYPE
      SYNTAX DisplayString
      ACCESS read-only
      STATUS mandatory
      DESCRIPTION
         "String showing the process creation time
          ('month day, year  hours:minutes:seconds.hundreths')"
      ::= { zagInProcess 7 }

   zagInProcCpuTime   OBJECT-TYPE
      SYNTAX DisplayString
      ACCESS read-only
      STATUS mandatory
      DESCRIPTION
         "Process CPU time ('hours:minutes:seconds.hundreths')"
      ::= { zagInProcess 8 }

   zagInProcPri OBJECT-TYPE
      SYNTAX INTEGER (1..199)
      ACCESS read-only
      STATUS mandatory
      DESCRIPTION
         "Current process priority. Valid range 1-199"
      ::= { zagInProcess 9 }

   zagInProcHomeTerm  OBJECT-TYPE
      SYNTAX DisplayString
      ACCESS read-only
      STATUS mandatory
      DESCRIPTION
         "String showing the process home terminal name."
      ::= { zagInProcess 10 }

   zagInProcMaxOpeners OBJECT-TYPE
      SYNTAX INTEGER
      ACCESS read-only
      STATUS mandatory
      DESCRIPTION
         "The maximum number of openers the agent can support at one time."
      ::= { zagInProcess 11 }

   zagInProcCurrentOpeners OBJECT-TYPE
      SYNTAX INTEGER
      ACCESS read-only
      STATUS mandatory
      DESCRIPTION
         "The current number of agent openers."
      ::= { zagInProcess 12 }


-- **************************************************************************
-- the agent's internal Endpoint group
-- **************************************************************************

   zagInEndpointTable OBJECT-TYPE
      SYNTAX   SEQUENCE OF ZagInEndpointEntry
      ACCESS   not-accessible
      STATUS   mandatory
      DESCRIPTION
                 "A list of endpoint entries, accessible via the SNMP
                  protocol."
      ::= { zagInEndpoint 1 }

   zagInEndpointEntry OBJECT-TYPE
      SYNTAX   ZagInEndpointEntry
      ACCESS   not-accessible
      STATUS   mandatory
      DESCRIPTION
                 "An endpoint entry containing objects defining
                  a socket on which SNMP manager messages will
                  be received and replied to."
      INDEX { zagInEpName }
      ::= { zagInEndpointTable 1 }

   ZagInEndpointEntry ::=
      SEQUENCE {
         zagInEpRowStatus
            INTEGER,
         zagInEpName
            DisplayString,
         zagInEpState
            INTEGER,
         zagInEpHostAddr
            DisplayString,
         zagInEpNetwork
            DisplayString
      } --<NOPDU>--

   zagInEpRowStatus OBJECT-TYPE
      SYNTAX   INTEGER {
                  -- The following two values are states.
                  -- These values can be read and written
                  active(1),        -- the row is available for use
                  notInService(2),  -- the row is administratively
                                    --    unavailable for use

                  -- The following value is a state.
                  -- This value may only be read.
                  notReady(3),      -- the row is incomplete and therefore
                                    --    unavailable for use

                  -- The following three values are actions.
                  -- These values may only be written.
                  createAndGo(4),   -- supplied by the management application
                                    --    wishing to create a new row and
                                    --    have it available for use
                  createAndWait(5), -- supplied by the management application
                                    --    wishing to create a new row but
                                    --    not have it available for use
                  destroy(6)        -- supplied by the management application
                                    --    wishing to delete the row.
               }
      ACCESS   read-write
      STATUS   mandatory
      DESCRIPTION
                 "Used to manage the creation, alteration and deletion of
                  table rows.  The row must be in the 'notReady' or the
                  'notInService' state for any row object to be modified."
      ::= { zagInEndpointEntry 1 }

   zagInEpName OBJECT-TYPE
      SYNTAX   DisplayString (SIZE (2..8))
      ACCESS   read-only
      STATUS   mandatory
      DESCRIPTION
                 "The name assigned to this endpoint.  This object is created
                  by the agent by extracting the index value from the initial
                  row creation varbind.  For compatibility with Tandem's
                  Subsystem Control Facility (SCF):
                       1. The name must be capitalized.
                       2. The name must start with '#'.
                       3. Valid characters are 'A' to 'Z' and '0' to '9'."
      ::= { zagInEndpointEntry 2 }

   zagInEpState OBJECT-TYPE
      SYNTAX   INTEGER {
                  -- The following five values are states.
                  -- These values can only be read.
                  -- These values correspond to the ZCOM_VAL_SUMSTATE..
                  -- values.
                  defined(1),
                  started(3),
                  starting(4),
                  stopped(5)
               }
      ACCESS   read-only
      STATUS   mandatory
      DESCRIPTION
                 "The current operational state of the endpoint."
      ::= { zagInEndpointEntry 3 }

   zagInEpHostAddr OBJECT-TYPE
      SYNTAX   DisplayString
      ACCESS   read-write
      STATUS   mandatory
      DESCRIPTION
                 "The local host address the agent is to monitor for
                  incoming messages.  For IP addresses, this value must be
                  either 0.0.0.0 or a fully specified address (e.g.,
                  103.252.12.3).  The default value is 0.0.0.0."
      ::= { zagInEndpointEntry 4 }

   zagInEpNetwork OBJECT-TYPE
      SYNTAX   DisplayString
      ACCESS   read-write
      STATUS   mandatory
      DESCRIPTION
                 "The name of the process the agent must use to establish
                  the socket session.  The default value is $ZTC0."
      ::= { zagInEndpointEntry 5 }

-- *************************************************************************
-- the agent's internal Profile group
-- **************************************************************************

   zagInProfileTable OBJECT-TYPE
      SYNTAX   SEQUENCE OF ZagInProfileEntry
      ACCESS   not-accessible
      STATUS   mandatory
      DESCRIPTION
                 "A list of profile entries, accessible via the SNMP and
                  snmpIPC protocols."
      ::= { zagInProfile 1 }

   zagInProfileEntry OBJECT-TYPE
      SYNTAX   ZagInProfileEntry
      ACCESS   not-accessible
      STATUS   mandatory
      DESCRIPTION
                 "A profile entry containing objects used for
                  authenticating a network management station request."
      INDEX { zagInPfName }
      ::= { zagInProfileTable 1 }

   ZagInProfileEntry ::=
      SEQUENCE {
         zagInPfRowStatus
            INTEGER,
         zagInPfName
            DisplayString,
         zagInPfState
            INTEGER,
         zagInPfHostAddr
            DisplayString,
         zagInPfCommunity
            DisplayString,
         zagInPfAccess
            INTEGER
      } --<NOPDU>--

   zagInPfRowStatus OBJECT-TYPE
      SYNTAX   INTEGER {
                  -- The following two values are states.
                  -- These values can be read and written.
                  active(1),        -- the row is available for use
                  notInService(2),  -- the row is administratively
                                    --    unavailable for use

                  -- The following value is a state.
                  -- This value may only be read.
                  notReady(3),      -- the row is incomplete and therefore
                                    --    unavailable for use

                  -- The following three values are actions.
                  -- These values may only be written.
                  createAndGo(4),   -- supplied by the management application
                                    --    wishing to create a new row and
                                    --    have it available for use
                  createAndWait(5), -- supplied by the management application
                                    --    wishing to create a new row but
                                    --    not have it available for use
                  destroy(6)        -- supplied by the management application
                                    --    wishing to delete the row.
               }
      ACCESS   not-accessible  -- #MGR: ACCESS read-write
      STATUS   mandatory
      DESCRIPTION
                 "Used to manage the creation, alteration and deletion of
                  table rows.  The row must in the 'notReady' or the
                  'notInService' state for any row object to be modified.

                  This object is accessible only via the #MGR interface."
      ::= { zagInProfileEntry 1 }

   zagInPfName OBJECT-TYPE
      SYNTAX   DisplayString (SIZE (2..8))
      ACCESS   not-accessible  -- #MGR: ACCESS read-only
      STATUS   mandatory
      DESCRIPTION
                 "The name assigned to this profile.  This object is created
                  by the agent by extracting the index value from the initial
                  row creation varbind.  For compatibility with Tandem's
                  Subsystem Control Facility (SCF):
                       1. The name must be capitalized.
                       2. The name must start with '#'.
                       3. Valid characters are 'A' to 'Z' and '0' to '9'.

                  This object is accessible only via the #MGR interface."
      ::= { zagInProfileEntry 2 }

   zagInPfState OBJECT-TYPE
      SYNTAX   INTEGER {
                  -- The following four values are states.
                  -- These values can only be read.
                  -- These values correspond to the ZCOM_VAL_SUMSTATE..
                  -- values.
                  defined(1),
                  started(3),
                  starting(4),
                  stopped(5)
               }
      ACCESS   not-accessible -- #MGR: ACCESS read-only
      STATUS   mandatory
      DESCRIPTION
                 "The current operational state of the profile.

                  This object is accessible only via the #MGR interface."
      ::= { zagInProfileEntry 3 }

   zagInPfHostAddr OBJECT-TYPE
      SYNTAX   DisplayString
      ACCESS   not-accessible -- #MGR: ACCESS read-write
      STATUS   mandatory
      DESCRIPTION
                 "The address of the host sending the message.  In
                  conjunction with the community name, provides the
                  authentication attributes for validating received
                  messages.  If the value of this attribute is 0.0.0.0,
                  messages with the correct commuinty string will be
                  accepted without regard to the originating host's
                  address.  The default value is 0.0.0.0.

                  This object is accessible only via the #MGR interface."
      ::= { zagInProfileEntry 4 }

   zagInPfCommunity OBJECT-TYPE
      SYNTAX   DisplayString (SIZE (0..255))
      ACCESS   not-accessible -- #MGR: ACCESS read-write
      STATUS   mandatory
      DESCRIPTION
                 "A data string to be compared with the community string
                  of received messages for the purpose of authenticating
                  the message.  The default value is 'public'.

                  The community string can be divided into two sections,
                  with syntax:

                  {<agent community string>}[::<subagent community string>]

                  The agent community string length can be 0 to 50 bytes.
                  The total community string length can be 0 to 255 bytes.
                  Since the agent knows only its own community strings,
                  only its community strings will be returned in response
                  to queries, whether via SCF, the SNMP protocol, or the
                  #MGR service point.

                  The following rules apply to setting the agent's
                  community string:

                  1. The length must be 0 to 50 characters.
                  2. The community string must not contain successive
                     colons ('::').
                  3. The community string must consist entirely of
                     printable characters.

                  If any of these rules is violated, the set is rejected
                  with a 'badValue' errorStatus.

                  The agent does not look at the subagent portion of the
                  community string.  Therefore, the subagent portion is
                  defined as OCTET STRING, rather than DisplayString; i.e.,
                  it is not restricted to printable characters.

                  This object is accessible only via the #MGR interface."
      ::= { zagInProfileEntry 5 }

   zagInPfAccess OBJECT-TYPE
      SYNTAX   INTEGER {
                  readOnly(1),
                  readWrite(2)
               }
      ACCESS   not-accessible -- #MGR: ACCESS read-write
      STATUS   mandatory
      DESCRIPTION
                 "Access defines the authority of the community members
                  to retrieve and alter network management information.
                  The default value is read-only.

                  This object is accessible only via the #MGR interface."
      ::= { zagInProfileEntry 6 }

-- **************************************************************************
-- the agent's internal Trapdest group
-- **************************************************************************

   zagInDirectedTrapdestName OBJECT-TYPE
      SYNTAX   DisplayString (SIZE (2..8))
      ACCESS   read-only
      STATUS   mandatory
      DESCRIPTION
                 "This object is used by the subagent to specify a trap
                  destination name (zagInTdName) in the agent's trapDest
                  table to which a directed trap is to be sent.  To issue a
                  directed trap, varbinds with this object identifier
                  must appear first in an snmpIPC-Trap-PDU's varbind list.

                  For compatibility with Tandem's Subsystem Control Facility
                  (SCF):
                       1. The name must be capitalized.
                       2. The name must start with '#'.
                       3. Valid characters are 'A' to 'Z' and '0' to '9'."
      ::= { zagInTrapdest 1 }

   zagInTrapdestTable OBJECT-TYPE
      SYNTAX   SEQUENCE OF ZagInTrapdestEntry
      ACCESS   not-accessible
      STATUS   mandatory
      DESCRIPTION
                 "A list of trap destination entries."
      ::= { zagInTrapdest 2 }

   zagInTrapdestEntry OBJECT-TYPE
      SYNTAX   ZagInTrapdestEntry
      ACCESS   not-accessible
      STATUS   mandatory
      DESCRIPTION
                 "A trap destination entry containing objects defining
                  the attributes of a trap destination."
      INDEX { zagInTdName }
      ::= { zagInTrapdestTable 1 }

   ZagInTrapdestEntry ::=
      SEQUENCE {
         zagInTdRowStatus
            INTEGER,
         zagInTdName
            DisplayString,
         zagInTdState
            INTEGER,
         zagInTdHostAddr
            DisplayString,
         zagInTdCommunity
            DisplayString,
         zagInTdNetwork
            DisplayString,
         zagInTdType
            INTEGER,
         zagInTdPort
            INTEGER
      } --<NOPDU>--

   zagInTdRowStatus OBJECT-TYPE
      SYNTAX   INTEGER {
                  -- The following two values are states.
                  -- These values can be read and written.
                  active(1),        -- the row is available for use
                  notInService(2),  -- the row is administratively
                                    --    unavailable for use

                  -- The following value is a state.
                  -- This value may only be read.
                  notReady(3),      -- the row is incomplete and therefore
                                    --    unavailable for use

                  -- The following three values are actions.
                  -- These values may only be written.
                  createAndGo(4),   -- supplied by the management application
                                    --    wishing to create a new row and
                                    --    have it available for use
                  createAndWait(5), -- supplied by the management application
                                    --    wishing to create a new row but
                                    --    not have it available for use
                  destroy(6)        -- supplied by the management application
                                    --    wishing to delete the row.
               }
      ACCESS   read-write
      STATUS   mandatory
      DESCRIPTION
                 "Used to manage the creation, alteration and deletion of
                  table rows.  The row must in the 'notReady' or the
                  'notInService' state for any row object to be modified."
      ::= { zagInTrapdestEntry 1 }

   zagInTdName OBJECT-TYPE
      SYNTAX   DisplayString (SIZE (2..8))
      ACCESS   read-only
      STATUS   mandatory
      DESCRIPTION
                 "The name assigned to this trapDest.  This object is created
                  by the agent by extracting the index value from the initial
                  row creation varbind.  For compatibility with Tandem's
                  Subsystem Control Facility (SCF):
                       1. The name must be capitalized.
                       2. The name must start with '#'.
                       3. Valid characters are 'A' to 'Z' and '0' to '9'."
      ::= { zagInTrapdestEntry 2 }

   zagInTdState OBJECT-TYPE
      SYNTAX   INTEGER {
                  -- The following five values are states.
                  -- These values can only be read.
                  -- These values correspond to the ZCOM_VAL_SUMSTATE..
                  -- values.
                  defined(1),
                  started(3),
                  starting(4),
                  stopped(5)
               }
      ACCESS   read-only
      STATUS   mandatory
      DESCRIPTION
                 "The current operational state of the trapdest."
      ::= { zagInTrapdestEntry 3 }

   zagInTdHostAddr OBJECT-TYPE
      SYNTAX   DisplayString
      ACCESS   read-write
      STATUS   mandatory
      DESCRIPTION
                 "The address of the host which is to receive trap
                  messages.  There is no default value."
      ::= { zagInTrapdestEntry 4 }

   zagInTdCommunity OBJECT-TYPE
      SYNTAX   DisplayString (SIZE (0..50))
      ACCESS   read-write
      STATUS   mandatory
      DESCRIPTION
                 "A data string to be compared with the community string
                  of received messages for the purpose of authenticating
                  the message.  The default value is 'Tandem'."
      ::= { zagInTrapdestEntry 5 }

   zagInTdNetwork OBJECT-TYPE
      SYNTAX   DisplayString
      ACCESS   read-write
      STATUS   mandatory
      DESCRIPTION
                 "The name of the process the agent must use to establish
                  the socket session.  The default value is $ZTC0."
      ::= { zagInTrapdestEntry 6 }

   zagInTdType OBJECT-TYPE
      SYNTAX   INTEGER {
                  broadcast(1),   -- non-directed traps
                  directed(2)     -- directed traps
               }
      ACCESS   read-write
      STATUS   mandatory
      DESCRIPTION
               "Broadcast trapDests are sent all trap messages except
                directed ones.  Directed trapDests receive only directed
                traps."
      ::= { zagInTrapdestEntry 7 }

   zagInTdPort OBJECT-TYPE
      SYNTAX   INTEGER
      ACCESS   read-write
      STATUS   mandatory
      DESCRIPTION
                 "The port of the host which is to receive trap
                  messages.  The default value is 162."
      ::= { zagInTrapdestEntry 8 }

END 
-- SNMP-AGENT-PUBLIC MIB
