NETWORTH-FASTPIPES-MIB  DEFINITIONS ::= BEGIN

--  This is the draft mib of the FastPipes Proprietary MIB.

-- Here are the sysobject ids for FastPipes

-- networth                     ::= { enterprises 215 }
-- networthProducts             ::= { networth 1 }
-- networthInternetworking      ::= { networthProduct 2 }
-- nwFastPipes                  ::= { networthInternetworking 2 }

-- nwFastPipesModular           ::= nwFastPipes.1.*.*
-- nwFastPipesNonModular        ::= nwFastPipes.2.*.*
-- nwFastPipesNoUplink          ::= nwFastPipes.*.1.*
-- nwFastPipesUplinkFDDI        ::= nwFastPipes.*.2.*
-- nwFastPipesUplinkATM         ::= nwFastPipes.*.3.*
-- nwFastPipesUpLink100BT       ::= nwFastPipes.*.4.*
-- nwFastPipesUpLink100VG       ::= nwFastPipes.*.5.*
-- nwFastPipesNonRouter         ::= nwFastPipes.*.*.1
-- nwFastPipesRouter            ::= nwFastPipes.*.*.2

-- Note that this defines 20 possible configurations (modular(2) x uplink(5) x
-- router(2) ) and 20 corresponding sysObjID's.

IMPORTS
		enterprises, IpAddress  FROM RFC1155-SMI
		DisplayString           FROM RFC1213-MIB
		TRAP-TYPE               FROM RFC-1215
		OBJECT-TYPE             FROM RFC-1212;

networth                    OBJECT IDENTIFIER ::= { enterprises 215 }
networthProducts            OBJECT IDENTIFIER ::= { networth 1 }
networthInternetworking     OBJECT IDENTIFIER ::= { networthProducts 2 }
nwFastPipes                 OBJECT IDENTIFIER ::= { networthInternetworking 2 }


nwfpProductType OBJECT-TYPE
	SYNTAX  DisplayString (SIZE (0..32))
	ACCESS  read-only
	STATUS  mandatory
	DESCRIPTION
	"The switch product type based on whether the switch is modular or 
    nonmodular, has one of four uplinks or none, and has routing or not.  
    The product types are:

	Modular with no Uplink and no Routing
	Modular with no Uplink and Routing
	Modular with FDDI Uplink and no Routing
	Modular with FDDI Uplink and Routing
	Modular with ATM Uplink and no Routing
	Modular with ATM Uplink and Routing
	Modular with 100BT Uplink and no Routing
	Modular with 100BT Uplink and Routing
	Modular with 100VG Uplink and no Routing
	Modular with 100VG Uplink and Routing
	NonModular with no Uplink and no Routing
	NonModular with no Uplink and Routing
	NonModular with FDDI Uplink and no Routing
	NonModular with FDDI Uplink and Routing
	NonModular with ATM Uplink and no Routing
	NonModular with ATM Uplink and Routing
	NonModular with 100BT Uplink and no Routing
	NonModular with 100BT Uplink and Routing
	NonModular with 100VG Uplink and no Routing
	NonModular with 100VG Uplink and Routing"
	::= { nwFastPipes 1 }

nwfpReset       OBJECT-TYPE
    SYNTAX      INTEGER 
    {
	no-reset(1),
	reset(2),
	reset-and-erase-config(3)
	}
	ACCESS  read-write
	STATUS  mandatory
	DESCRIPTION
	"Setting this object to reset(2) will cause the FastPipes to 
	perform a hardware reset within approximately 5 seconds.

    Setting this object to reset-and-erase-config(3) will cause 
	the switch to perform a hardware reset to all config values stored 
	in nvram to default values within approximately 5 seconds. 
	
    Setting this object to no-reset(1) will have no effect.  The 
	value no-reset(1) will be returned whenever this object is 
	retrieved.
	
    The primary purpose for including this variable in the FastPipes 
	MIB is to allow SNMP managers to modify the operational mode 
	of the FastPipes."
	::= { nwFastPipes 2 }

nwfpCurrentSoftwareVersion      OBJECT-TYPE
    SYNTAX      DisplayString (SIZE (0..15))
	ACCESS  read-only
	STATUS  mandatory
	DESCRIPTION
	"The version of software currently running on the switch. The version 
    is specified in ASCII format"
	::= { nwFastPipes 3 }

nwfpFutureSoftwareVersion       OBJECT-TYPE
    SYNTAX      DisplayString (SIZE (0..15))
	ACCESS  read-write
	STATUS  mandatory
	DESCRIPTION
	"The version of software the switch will run after the next reset.  
	If this variable is different than nwfpCurrentSoftwareVersion, 
	the switch will request a download for the new software the next 
	time the switch is reset (as in setting the variable nwfpReset or 
	power cycling the unit).  The version should be specified 
	as an ASCII string."
	::= { nwFastPipes 4 }

nwfpTFTPServerIPAddress OBJECT-TYPE
    SYNTAX  IpAddress
    ACCESS  read-write
    STATUS  mandatory
    DESCRIPTION
    "The IP address of the TFTP Server to which the FastPipes will send 
    its next TFTP request."
    ::= { nwFastPipes 5 }

nwfpCurrentUplinkSoftwareVers   OBJECT-TYPE
    SYNTAX      DisplayString (SIZE (0..15))
	ACCESS  read-only
	STATUS  mandatory
	DESCRIPTION
	"The version of software currently running on the switch's Uplink 
	Card.  The version is an ASCI string of the form."
	::= { nwFastPipes 6 }

nwfpFutureUplinkSoftwareVers    OBJECT-TYPE
    SYNTAX      DisplayString (SIZE (0..15))
	ACCESS  read-write
	STATUS  mandatory
	DESCRIPTION
	"The version of software the switch's Uplink Card will run after the 
	next reset. If this variable is different than 
	nwfpCurrentUplinkSoftwareVers, the switch will request a download 
	for the new software the next time the switch is reset (as in setting 
	the variable nwfpReset or power cycling the unit).  The version 
	should be specified as an ASCII string."
	::= { nwFastPipes 7 }

nwfpLastFailureReason   OBJECT-TYPE
	SYNTAX  INTEGER
	ACCESS  read-only
	STATUS  mandatory
	DESCRIPTION     
	"The last error that caused a switch failure.  A value of zero (0) 
	indicates that there has not been a switch failure since the nvram 
	was last erased.

	A non-zero value indicates the reason for the last switch failure.  
	A normal switch reset or power cycle will not change the value of 
	this variable (it will still indicate the reason for the last 
	known failure)."
	::= { nwFastPipes 8 } 

nwfpEEPROMVersion       OBJECT-TYPE
    SYNTAX      DisplayString (SIZE (0..32))
	ACCESS  read-only
	STATUS  mandatory
	DESCRIPTION
	"The hardware EEPROM version.  The string 'unknown' is returned if
	the value is not known."
	::= { nwFastPipes 9 }

nwfpManufactureDate     OBJECT-TYPE
    SYNTAX      DisplayString (SIZE (0..32))
	ACCESS  read-only
	STATUS  mandatory
	DESCRIPTION
	"The hardware manufacture date.  The string 'unknown' is returned if 
    the value is not known."
	::= { nwFastPipes 10 }

nwfpAuthErrIPaddress OBJECT-TYPE
    SYNTAX  IpAddress
    ACCESS  read-only
    STATUS  mandatory
    DESCRIPTION
    "The IP address of the device that sent the SNMP packet that caused 
    an authentication error trap to be issued by the switch."
    ::= { nwFastPipes 11 }

nwfpRAMsize     OBJECT-TYPE
    SYNTAX      INTEGER
    {
	one-MB(1),
	two-MB(2),
	four-MB(4),
	eight-MB(8)
    }
	ACCESS  read-only
	STATUS  mandatory
	DESCRIPTION
	"The size of RAM."
	::= { nwFastPipes 12 }

nwfpEthernetTable       OBJECT-TYPE
    SYNTAX      SEQUENCE OF NwfpEthernetEntry
    ACCESS      not-accessible
    STATUS      mandatory
    DESCRIPTION 
    "A table of ethernet-port-specific information for the FastPipes. 
    This table augments the Ethernet RFC1398 MIB."
    ::= { nwFastPipes 13 }

nwfpEthernetEntry       OBJECT-TYPE
    SYNTAX      NwfpEthernetEntry
    ACCESS      not-accessible
    STATUS      mandatory
    DESCRIPTION 
    "A list of information for every ethernet interface."
    INDEX       { nwfpIfIndex }
    ::= { nwfpEthernetTable 1 }

NwfpEthernetEntry ::= SEQUENCE {
    nwfpIfIndex            
	INTEGER,
    nwfpBOOTPrequestFlag   
	INTEGER
    }

nwfpIfIndex     OBJECT-TYPE
    SYNTAX      INTEGER (1..12)
    ACCESS      read-only
    STATUS      mandatory
    DESCRIPTION 
    "Ethernet interface number that corresponds to the ifIndex value 
    in mib-2."
    ::= { nwfpEthernetEntry 1 }

nwfpBOOTPrequestFlag    OBJECT-TYPE
    SYNTAX INTEGER 
    {
    enabled(1),
    disabled(2)
    }
    ACCESS      read-write
    STATUS      mandatory
    DESCRIPTION 
    "This flag determines whether this ethernet interface will send a BOOTP 
    request.  When booting, the FastPipes will broadcast a BOOTP request 
    from the lowest ethernet interface with this value enabled(1). If that 
    BOOTP request fails, the FastPipes will broadcast another BOOTP request 
    from the next ethernet interface with this value enabled(1). At least 
    one ethernet interface must have this value enabled(1) or BOOTP will 
    not work."
    ::= { nwfpEthernetEntry 2 }

nwfpBOOTPServerIPAddress OBJECT-TYPE
    SYNTAX  IpAddress
    ACCESS  read-only
    STATUS  mandatory
    DESCRIPTION
    "The IP address of the BOOTP Server that responded to the  FastPipes's 
    BOOTP request."
    ::= { nwFastPipes 18 }

nwfpBOOTPEthernetIF OBJECT-TYPE
    SYNTAX  INTEGER
    ACCESS  read-only
    STATUS  mandatory
    DESCRIPTION
    "The Ethernet interface number that successfully completed the BOOTP 
    interaction."
    ::= { nwFastPipes 19 }

nwfpUplinkSoftwarePath  OBJECT-TYPE
    SYNTAX      DisplayString (SIZE (0..255))
    ACCESS      read-write
    STATUS      mandatory
    DESCRIPTION
    "The path to the switch software file. Following this path will reveal 
    the actual version of the file."
    ::= { nwFastPipes 20 }

nwfpSerialNumber        OBJECT-TYPE
    SYNTAX      DisplayString (SIZE (0..32))
    ACCESS      read-only
    STATUS      mandatory
    DESCRIPTION
    "The hardware serial number."
    ::= { nwFastPipes 21 }

nwfpConfiguration       OBJECT-TYPE
    SYNTAX INTEGER 
    {
	fsp12(500),
	fsp6(501),
	fsp11(502),
	fsp12fx(503),
	fsp6fl(504)
    } 
    ACCESS      read-only
    STATUS      mandatory
    DESCRIPTION
    "This object returns the type of base module that is being queried."
    ::= { nwFastPipes 22 }

nwfpUpLinkEEPROMVersion OBJECT-TYPE
    SYNTAX      DisplayString (SIZE (0..32))
    ACCESS      read-only
    STATUS      mandatory
    DESCRIPTION
    "The uplink EEPROM version.  The string 'unknown' is returned 
    if the value is not known."
    ::= { nwFastPipes 23 }

nwfpUpLinkManufactureDate       OBJECT-TYPE
    SYNTAX      DisplayString (SIZE (0..32))
    ACCESS      read-only
    STATUS      mandatory
    DESCRIPTION
    "The uplink manufacture date.  The string 'unknown' is returned if 
    the value is not known."
    ::= { nwFastPipes 24 }

nwfpUpLinkSerialNumber  OBJECT-TYPE
    SYNTAX      DisplayString (SIZE (0..32))
    ACCESS      read-only
    STATUS      mandatory
    DESCRIPTION
    "The uplink serial number."
    ::= { nwFastPipes 25 }

nwfpUpLinkConfiguration OBJECT-TYPE
    SYNTAX      INTEGER
    {
    none(1),
    fddi-fiber-das(2),
    fddi-fiber-sas(3),
    fddi-tppmd-sas(4),
    ethernet-100mbps-t4(5),
    ethernet-100mbps-tx(6),
    ethernet-100mbps-fx(7),
    atm(8)
    }
    ACCESS      read-only
    STATUS      mandatory
    DESCRIPTION
    "This object returns the type of HSSP (Uplink) module that is in the
    base unit."
    ::= { nwFastPipes 26 }

nwfpSoftwarePath        OBJECT-TYPE
    SYNTAX      DisplayString (SIZE (0..255))
    ACCESS      read-write
    STATUS      mandatory
    DESCRIPTION
    "The path to the switch software file. Following this path will 
    reveal the actual version of the file."
    ::= { nwFastPipes 27 }

nwfpCurrentBooterSoftwareVersion        OBJECT-TYPE
	SYNTAX  DisplayString (SIZE (0..15))
	ACCESS  read-only
	STATUS  mandatory
	DESCRIPTION
	"The version of Booter software currently running on the switch.  
	The version is an ASCII string."
	::= { nwFastPipes 28 }

nwfpFutureBooterSoftwareVersion OBJECT-TYPE
	SYNTAX  DisplayString (SIZE (0..15))
	ACCESS  read-write
	STATUS  mandatory
	DESCRIPTION
	"The version of Booter software the switch will run after the next reset.  
	If this variable is different than nwfpCurrentSoftwareVersion, 
	the switch will request a download for the new software the next 
	time the switch is reset (as in setting the variable nwfpReset or 
	power cycling the unit).  The version is an ASCII string."
	::= { nwFastPipes 29 }

nwfpBooterSoftwarePath  OBJECT-TYPE
	SYNTAX  DisplayString (SIZE (0..255))
	ACCESS  read-write
	STATUS  mandatory
	DESCRIPTION
	"The path to the Booter software file. Following this path will 
    reveal the actual version of the file."
	::= { nwFastPipes 30 }

nwfpSaveConfig        OBJECT-TYPE
    SYNTAX      INTEGER 
    {
    config-info-saved(1),
    save-all(2)
    }
    ACCESS      read-write
    STATUS      mandatory
	DESCRIPTION
    "This object allows the user to permanently save configuration parameters 
    into the NVRAM of a managed device. It can only be written with 
    save-all(2). Writing this object with config-info-saved(1) has no effect.

    Setting this object to save-all(2) will save all configuration info 
    changed into the NVRAM.

    Reading this object will normally return config-info-saved(1) if the 
    previous save operation is successful. It will return the value set when 
    the previous set operation failed."
	::= { nwFastPipes 31 }

nwfpFddiIPFrag  OBJECT-TYPE
    SYNTAX INTEGER 
    {
    off(1),
    on(2)
    }
    ACCESS read-write
    STATUS mandatory
    DESCRIPTION
    "When on(2), the FastPipes FDDI Uplink will perform IP fragmentation. 
    When off(1), IP fragmentation is not done and FDDI frames containing 
    IP information that exceed the Ethernet maximum frame size will
    be dropped. Default mode is on(2)."
 ::= { nwFastPipes 32 }
     
nwfpFddiToEthIPTrans    OBJECT-TYPE
    SYNTAX INTEGER 
    {
    ethernet-ii(1),         -- Translate from FDDI to Ethernet_II frame only
    ethernet-802-3-RAW(2),  -- Translate from FDDI to ethernet-802.3 RAW only
    automatic(3)            -- Translate from FDDI to any of above frame types
    }
    ACCESS read-write
    STATUS mandatory
    DESCRIPTION
    "This attribute defines how FDDI frames containing IP packets get 
    translated into Ethernet frames. When automatic(3) mode is selected, 
    then FDDI frames are translated either in 802.3 RAW or ethernet-ii frames, 
    depending on the FDDI frame format (FDDI SNAP frames are translated into 
    ethernet-ii frames and FDDI 802.2 frames are translated into 802.3 RAW
    frames). When ethernet-802-3-RAW(2) mode is selected, all FDDI frames are 
    translated into 802.3 RAW frames. When ethernet-ii(1) mode is selected, 
    all FDDI frames are translated into ethernet-ii frames. Default mode is 
    automatic(3)."
 ::= { nwFastPipes  33 }
     
nwfpFddiSNAPToEthIPXTrans OBJECT-TYPE
    SYNTAX INTEGER 
    {
    ethernet-ii(1),         -- Translate from FDDI SNAP to Ethernet_II frame 
    ieee8022snap(2)         -- Translate from FDDI SNAP to 802.3 with 802.2 SNAP 
    }
    ACCESS read-write
    STATUS mandatory
    DESCRIPTION
    "This attribute defines how incoming FDDI SNAP frames containing IPX 
    information are translated into ethernet frames. When ethernet-ii(1) mode 
    is selected, then, the incoming FDDI SNAP frames are translated into 
    ethernet-ii frames. When ieee8022snap(2) is selected, then the incoming 
    FDDI SNAP frames are translated into ethernet SNAP frames. Default mode 
    is ethernet-ii(1)."
    ::= { nwFastPipes 34 }
     
nwfpFddi8022ToEthIPXTrans  OBJECT-TYPE
    SYNTAX INTEGER 
    {
    ethernet-802-3-RAW(1),  -- Translate from FDDI802.2 to ethernet-802.3 RAW
    ieee8022(2)             -- Translate from FDDI802.2 to 802.3 with 802.2 
    }
    ACCESS read-write
    STATUS mandatory
    DESCRIPTION
    "This attribute defines how incoming FDDI 802.2 frames containing IPX 
    information are translated into ethernet frames. When the 802-3-Raw(1) 
    mode is selected, then, incoming FDDI 802.2 frames are translated into 
    802.3 Raw format. When the 802-2(2) format is selected, then incoming 
    FDDI 802.2 frames are translated into 802.2 frames. Default mode is 
    802-3-Raw(1)."
    ::= { nwFastPipes 35 }
     
nwfpFddiLocTrafFiltering OBJECT-TYPE
    SYNTAX INTEGER 
    {
    off(1),
    on(2)
    }
    ACCESS read-write
    STATUS mandatory
    DESCRIPTION
    "Defines whether or not traffic local to the FDDI network the FastPipes 
    is connected to is filtered or not (i.e not forwarded to the FastPipes 
    switch process). The default is on(2)"
    ::= { nwFastPipes 36 }
     
nwfpSpanningTreeEnable  OBJECT-TYPE
    SYNTAX INTEGER 
    {
    enable(1),
    disable(2)
    }
    ACCESS read-write
    STATUS mandatory
    DESCRIPTION
    "When set to enable(1), the FastPipes will run the Spanning Tree Protocol 
    (STP). When set to disable(2), the FastPipes will not run STP. Default 
    value is enable(1)."
    ::= { nwFastPipes  37 }
     
nwfpTpFdbMaxSize  OBJECT-TYPE
    SYNTAX INTEGER
    ACCESS read-only
    STATUS mandatory
    DESCRIPTION
    "Gives the maximum number of entries that the forwarding data base may 
    have "
    ::= { nwFastPipes  38 }
     
nwfpTpFdbNbEntriesUsed  OBJECT-TYPE
    SYNTAX INTEGER
    ACCESS read-only
    STATUS mandatory
    DESCRIPTION
    "Gives the number of entries currently existing in the forwarding data 
    base."
    ::= { nwFastPipes  39 }
     
nwfpEthIPX8023ToFddiTrans OBJECT-TYPE
    SYNTAX INTEGER 
    {
     ethernet-802-3-RAW(1),
     ieee8022(2)          
    }
    ACCESS read-write
    STATUS mandatory
    DESCRIPTION
    "When set to ieee8022(2), an LLC header is added to the FDDI 
    frame, between the MAC header and the IPX header.  When set to
    ethernet-802-3-RAW(1), 802.3 raw packet format will be used in performing
    packet translation.  The default mode is ethernet-802-3-RAW(1)."
    ::= { nwFastPipes  40 }

--
--  Power Supply Table: This table will supply information regarding the
--  power supplies in the unit. The table will always return 2 entries, one
--  for each supply. If a supply is in and working the status will be on(1).
--  If a supply is in but bad or has no power, the status will be off(2). If 
--  the supply is not in, the status is na(3).
--
nwfpPowerSupplyNumber   OBJECT-TYPE
    SYNTAX INTEGER
    ACCESS read-only
    STATUS mandatory
    DESCRIPTION
    "The number of system power supplies installed (regardless of their 
    current state) in the FastPipe product."
    ::= { nwFastPipes 41 }

nwfpPowerSupplyTable    OBJECT-TYPE
    SYNTAX      SEQUENCE OF NwfpPowerSupplyEntry
    ACCESS      not-accessible
    STATUS      mandatory
    DESCRIPTION 
    "A table of system power supply specific information for the FastPipes."
    ::= { nwFastPipes 42 }

nwfpPowerSupplyEntry    OBJECT-TYPE
    SYNTAX      NwfpPowerSupplyEntry
    ACCESS      not-accessible
    STATUS      mandatory
    DESCRIPTION 
    "A list of information for every power supply installed"
    INDEX       { nwfpPowerSupplyIndex }
    ::= { nwfpPowerSupplyTable 1 }

NwfpPowerSupplyEntry ::= SEQUENCE {
    nwfpPowerSupplyIndex            
	INTEGER,
    nwfpPowerSupplyStatus           
	INTEGER
    }

nwfpPowerSupplyIndex    OBJECT-TYPE
    SYNTAX      INTEGER
    ACCESS      read-only
    STATUS      mandatory
    DESCRIPTION 
    "A unique value for each power supply."
    ::= { nwfpPowerSupplyEntry 1 }

nwfpPowerSupplyStatus   OBJECT-TYPE
    SYNTAX INTEGER 
    {
    good(1),        -- power supply exists and operates okay
    bad(2),         -- power supply exists but is bad or no power applied
    na(3)           -- power supply does not exist
    }
    ACCESS      read-only
    STATUS      mandatory
    DESCRIPTION
    "The status of the power supply. The value good(1) is returned if the 
    power supply identified by nwfpPowerSupplyIndex is running properly. The 
    value bad(2) is returned if the power supply identified by nwfpPowerSupplyIndex 
    has failed to operate properly but has been inserted into the slot. This 
    will include an inserted power supply with no power. The value na(3) is 
    returned if the power supply has not been inserted into the slot."
    ::= { nwfpPowerSupplyEntry 2 }

--
--  Fan Supply Table: This table will supply information regarding the
--  fans in the unit. The table will always return 2 entries, one for each 
--  fan. If a fan is working, the status will be good(1). If a fan is bad, 
--  the status will be bad(2).
--
nwfpFanNumber   OBJECT-TYPE
    SYNTAX INTEGER
    ACCESS read-only
    STATUS mandatory
    DESCRIPTION
    "The number of system fans installed (regardless of their current state) 
    in the FastPipe product."
    ::= { nwFastPipes 43 }

nwfpFanTable    OBJECT-TYPE
    SYNTAX      SEQUENCE OF NwfpFanEntry
    ACCESS      not-accessible
    STATUS      mandatory
    DESCRIPTION 
    "A table of system fan specific information for the FastPipes."
    ::= { nwFastPipes 44 }

nwfpFanEntry    OBJECT-TYPE
    SYNTAX      NwfpFanEntry
    ACCESS      not-accessible
    STATUS      mandatory
    DESCRIPTION 
    "A list of information for every fans installed"
    INDEX       { nwfpFanIndex }
    ::= { nwfpFanTable 1 }

NwfpFanEntry ::= SEQUENCE {
    nwfpFanIndex            
	INTEGER,
    nwfpFanStatus           
	INTEGER
    }

nwfpFanIndex    OBJECT-TYPE
    SYNTAX      INTEGER
    ACCESS      read-only
    STATUS      mandatory
    DESCRIPTION 
    "A unique value for each fan. Its value ranges between 1 and the value 
    of nwfpFanNumber."
    ::= { nwfpFanEntry 1 }

nwfpFanStatus   OBJECT-TYPE
    SYNTAX INTEGER 
    {
    good(1),
    bad(2)
    }
    ACCESS      read-only
    STATUS      mandatory
    DESCRIPTION 
    "The status of the system fan. The value good(1) is returned if the fan 
    identified by nwfpFanIndex is running properly. The value bad(2) is 
    returned if the fan identified by nwfpFanIndex has failed to operate 
    properly."
    ::= { nwfpFanEntry 2 }

--
--  Monitor Port Information
--
nwfpMonitorPort OBJECT-TYPE
    SYNTAX INTEGER 
    ACCESS      read-write
    STATUS      mandatory
    DESCRIPTION 
	"The index value of a port which will receive all traffic from   
	 the ports specified in the nwfpMonitorSource bitmask. Acceptable     
	 values are 1 to Max port number."

    ::= { nwFastPipes 45 }

nwfpMonitorSource       OBJECT-TYPE
    SYNTAX INTEGER 
    ACCESS      read-write
    STATUS      mandatory
    DESCRIPTION 
	"A bitmask of the port numbers to monitor. This bitmask (which
	 must not include the port number used for nwfpMonitorPort) specifies
	 which ports are to be monitored. Traffic sent to the ports specified  
	 in this bitmask will also be sent to nwfpMonitorPort. Bit 0
	 in the bitmask corresponds to port 1, bit 1 corresponds to port 2,
	 and so on.
	 The greater the number of ports specified in the bitmask,
	 the lower the integrity of information to the monitoring port. i.e.
	 the more ports monitored, the greater the probability of lost data."

    ::= { nwFastPipes 46 }

nwfpMonitorPortStatus   OBJECT-TYPE
    SYNTAX INTEGER 
    {
    enabled(1),
    disabled(2)
    }
    ACCESS      read-write
    STATUS      mandatory
    DESCRIPTION 
	"Status value of RMON monitoring. When set to disabled the port
	 specified in nwfpMonitorPort will not receive monitored data. When set to 
	 enabled the port will begin recieving data from the ports 
	 specified in nwfpMonitorSource."

    ::= { nwFastPipes 47 }

-- TRAPS
-- Power supply and fan related traps:

nwfpPowerSupplyDown TRAP-TYPE
    ENTERPRISE  networth
    VARIABLES   {   nwfpPowerSupplyIndex,
		            nwfpPowerSupplyStatus   }
    DESCRIPTION
    "A nwfpPowerSupplyDown trap signifies that a system power supply has 
    stopped running. This trap will only be generated when the system power 
    supply changes its operational state from up to down due to internal 
    failure."
              --#TYPE "PowerSupplyDown"
              --#SUMMARY "PowerSupplyDown"
              --#ARGUMENTS {2}
              --#SEVERITY CRITICAL
              --#TIMEINDEX 99
    ::= 11

nwfpPowerSupplyUp TRAP-TYPE
    ENTERPRISE  networth
    VARIABLES   {   nwfpPowerSupplyIndex,
		            nwfpPowerSupplyStatus   }
    DESCRIPTION
    "A nwfpPowerSupplyUp trap signifies that a system power supply is up 
    and running. This trap will only be generated when the system power 
    supply changes its operational state from down to up. "
              --#TYPE "PowerSupplyUp"
              --#SUMMARY "PowerSupplyUp"
              --#ARGUMENTS {2}
              --#SEVERITY INFORMATIONAL
              --#TIMEINDEX 99
    ::= 12

nwfpfanDown TRAP-TYPE
    ENTERPRISE  networth
    VARIABLES   {   nwfpFanIndex,
		            nwfpFanStatus   }
    DESCRIPTION
    "A nwfpfanDown trap signifies that a system fan has stopped running. 
    This trap will only be generated when the system fan changes its 
    operational state from up to down due to internal failure. "
              --#TYPE "fanDown"
              --#SUMMARY "fanDown"
              --#ARGUMENTS {2}
              --#SEVERITY CRITICAL
              --#TIMEINDEX 99
    ::= 13

nwfpfanUp TRAP-TYPE
    ENTERPRISE  networth
    VARIABLES   {   nwfpFanIndex,
		            nwfpFanStatus   }
    DESCRIPTION
    "A nwfpfanUp trap signifies that a system fan is up and running.  
    This trap will only be generated when the system fan changes its 
    operational state from down to up. "
              --#TYPE "FanUp"
              --#SUMMARY "fanUp"
              --#ARGUMENTS {2}
              --#SEVERITY INFORMATIONAL
              --#TIMEINDEX 99
    ::= 14

END
