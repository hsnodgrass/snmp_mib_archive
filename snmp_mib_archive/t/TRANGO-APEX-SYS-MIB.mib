TRANGO-APEX-SYS-MIB DEFINITIONS ::= BEGIN

IMPORTS
	MODULE-IDENTITY,
	OBJECT-TYPE,
	OBJECT-IDENTITY,
	Unsigned32,
	NOTIFICATION-TYPE,
        apex
                FROM TRANGO-APEX-MIB	        
        DisplayString
		FROM SNMPv2-TC
	MODULE-COMPLIANCE
		FROM SNMPv2-CONF;
	
-- *******************************************************************
-- ** System Information ** trango.twb.apex.sys
-- *******************************************************************
sys		OBJECT IDENTIFIER ::= { apex 1 }

sysUnitType	OBJECT-TYPE
    SYNTAX	INTEGER { NOTYPE(0), ACTIVE(1), STANDBY(2) }
    MAX-ACCESS	read-write
    STATUS	current
    DESCRIPTION "Unit Type"
    ::= { sys 1 }

ver		OBJECT IDENTIFIER ::= { sys 2  } 

sysIFMVer	OBJECT-TYPE
    SYNTAX	DisplayString (SIZE(0..80))
    MAX-ACCESS	read-only
    STATUS	current
    DESCRIPTION "SYS IFM Firmware version"
    ::= { ver 1 }

sysFPGAVer	OBJECT-TYPE
    SYNTAX	DisplayString (SIZE(0..80))
    MAX-ACCESS	read-only
    STATUS	current
    DESCRIPTION "FPGA Version"
    ::= { ver 2 }

sysFWVer	OBJECT-TYPE
    SYNTAX	DisplayString (SIZE(0..80))
    MAX-ACCESS	read-only
    STATUS	current
    DESCRIPTION "firmware version"
    ::= { ver 3 }

sysOSVer	OBJECT-TYPE
    SYNTAX	DisplayString (SIZE(0..80))
    MAX-ACCESS	read-only
    STATUS	current
    DESCRIPTION "OS version"
    ::= { ver 4 }

sysPICVer	OBJECT-TYPE
    SYNTAX	DisplayString (SIZE(0..80))
    MAX-ACCESS	read-only
    STATUS	current
    DESCRIPTION "PIC version"
    ::= { ver 5 }

sysModemVer	OBJECT-TYPE
    SYNTAX	DisplayString (SIZE(0..80))
    MAX-ACCESS	read-only
    STATUS	current
    DESCRIPTION "Modem version number"
    ::= { ver 6 }

prever		OBJECT IDENTIFIER ::= { sys 3  } 

sysFPGAPreVer	OBJECT-TYPE
    SYNTAX	DisplayString (SIZE(0..80))
    MAX-ACCESS	read-only
    STATUS	current
    DESCRIPTION "FPGA Previous version"
    ::= { prever 1 }

sysFWPreVer	OBJECT-TYPE
    SYNTAX	DisplayString (SIZE(0..80))
    MAX-ACCESS	read-only
    STATUS	current
    DESCRIPTION "FW Previous version"
    ::= { prever 2 }

sysOSPreVer	OBJECT-TYPE
    SYNTAX	DisplayString (SIZE(0..80))
    MAX-ACCESS	read-only
    STATUS	current
    DESCRIPTION "OS Previous version"
    ::= { prever 3 }

sysPICPreVer	OBJECT-TYPE
    SYNTAX	DisplayString (SIZE(0..80))
    MAX-ACCESS	read-only
    STATUS	current
    DESCRIPTION "PIC Previous version"
    ::= { prever 4 }

sysRFMPreVer	OBJECT-TYPE
    SYNTAX	DisplayString (SIZE(0..80))
    MAX-ACCESS	read-only
    STATUS	current
    DESCRIPTION "RFM Previous version"
    ::= { prever 5 }

model		OBJECT IDENTIFIER ::= { sys 4  } 

sysModel	OBJECT-TYPE
    SYNTAX	DisplayString (SIZE(0..80))
    MAX-ACCESS	read-only
    STATUS	current
    DESCRIPTION "System Model number"
    ::= { model 1 }

sysSerialID	OBJECT-TYPE
    SYNTAX	INTEGER (SIZE(0..127))
    MAX-ACCESS	read-only
    STATUS	current
    DESCRIPTION " System Serial ID"
    ::= { model 2 }

mac		OBJECT IDENTIFIER ::= { sys 5  } 

sysMACeth0	OBJECT-TYPE
    SYNTAX	DisplayString (SIZE(12))
    MAX-ACCESS	read-only
    STATUS	current
    DESCRIPTION "MAC address of Ethernet 0"
    ::= { mac 2 }

sysMACeth1	OBJECT-TYPE
    SYNTAX	DisplayString (SIZE(12))
    MAX-ACCESS	read-only
    STATUS	current
    DESCRIPTION "MAC address of Ethernet 1"
    ::= { mac 3 }

sysBackupStatus OBJECT-TYPE
    SYNTAX	INTEGER { OFF(0), READY(1) }
    MAX-ACCESS	read-only
    STATUS	current
    DESCRIPTION "The backup link is operational and ready or not"
    ::= { sys 6 }

opmode		OBJECT IDENTIFIER ::= { sys 7 }

sysDefaultOpmode	OBJECT-TYPE
    SYNTAX	INTEGER { OFF(0), ON(1) }
    MAX-ACCESS	read-write
    STATUS	current
    DESCRIPTION "Default operation mode"
    ::= { opmode 1 }

sysOpmode	OBJECT-TYPE
    SYNTAX	INTEGER { OFF(0), ON(1) }
    MAX-ACCESS	read-write
    STATUS	current
    DESCRIPTION "Display/Set current Opmode"
    ::= { opmode 2 }

community	OBJECT IDENTIFIER ::= { sys 8 }

sysReadCommStr	OBJECT-TYPE
    SYNTAX	DisplayString (SIZE(1..32))
    MAX-ACCESS	read-write
    STATUS	current
    DESCRIPTION "SNMP agent read community string.  It is used For authentication purpse "
    ::= { community 1 }

sysWriteCommStr	OBJECT-TYPE
    SYNTAX	DisplayString (SIZE(1..32))
    MAX-ACCESS	read-write
    STATUS	current
    DESCRIPTION "SNMP agent Write community string.  It is used For authentication purpse "
    ::= { community 2 }

sysSave	OBJECT-TYPE
    SYNTAX	INTEGER 
    MAX-ACCESS	read-write
    STATUS	current
    DESCRIPTION "Save the configuration parameter"
    ::= { sys 9 }

sysReboot	OBJECT-TYPE
    SYNTAX	INTEGER 
    MAX-ACCESS	read-write
    STATUS	current
    DESCRIPTION "Reboot the system"
    ::= { sys 10 }

sysResetFactoryDefault	OBJECT-TYPE
    SYNTAX		INTEGER 
    MAX-ACCESS		read-write
    STATUS		current
    DESCRIPTION 	"Reset configuration parameter to factory defaults"
    ::= { sys 11 }

ipconfig          OBJECT IDENTIFIER ::= { sys 12 }

sysIpAddress	OBJECT-TYPE
    SYNTAX	IpAddr
    MAX-ACCESS	read-write
    STATUS	current
    DESCRIPTION "IP Address"
    ::= { ipconfig 1 }

sysSubnetMask	OBJECT-TYPE
    SYNTAX	IpAddr
    MAX-ACCESS	read-write
    STATUS	current
    DESCRIPTION "Subnet Mask"
    ::= { ipconfig 2 }

sysDefaultGateway	OBJECT-TYPE
    SYNTAX	IpAddr
    MAX-ACCESS	read-write
    STATUS	current
    DESCRIPTION "Default Gateway"
    ::= { ipconfig 3 }

sysRemarks	OBJECT-TYPE
    SYNTAX	DisplayString (SIZE (0..100))
    MAX-ACCESS	read-write
    STATUS	current
    DESCRIPTION "Remarks"
    ::= { sys 13 }

daemon         	    OBJECT IDENTIFIER ::= { sys 14 }

sysTFTPD	    	OBJECT-TYPE
    SYNTAX		INTEGER { OFF(0), ON(1) }
    MAX-ACCESS	    	read-write
    STATUS	    	current
    DESCRIPTION     	"Enable or disable to receive code or fileset download"
    ::= { daemon 1 }

sysHTTPD	    OBJECT-TYPE
    SYNTAX		INTEGER { OFF(0), ON(1) }
    MAX-ACCESS	    read-write
    STATUS	    current
    DESCRIPTION     "Enable or disable HTTPD"
    ::= { daemon 2 }

sysTelnetd	    OBJECT-TYPE
    SYNTAX		INTEGER { OFF(0), ON(1) }
    MAX-ACCESS	    read-write
    STATUS	    current
    DESCRIPTION     "Enable or disable Telnetd"
    ::= { daemon 3 }

sysAlignmentMode	OBJECT-TYPE
    SYNTAX		INTEGER { OFF(0), ON(1) }
    MAX-ACCESS		read-write
    STATUS		current
    DESCRIPTION 	"Alignment mode of the radio"
    ::= { sys 15 }

sysFailover             OBJECT-TYPE
    SYNTAX		INTEGER { OFF(0), ON(1) }
    MAX-ACCESS      	read-only
    STATUS          	current
    DESCRIPTION     	"Enable/Disable failover feature"
    ::= { sys 16 }

trapinfo       		OBJECT IDENTIFIER ::= { sys 17 }

sysTrapEnable           OBJECT-TYPE
    SYNTAX		INTEGER { OFF(0), ON(1) }
    MAX-ACCESS      	read-write
    STATUS          	current
    DESCRIPTION     	"Enable/Disable SNMP Trap"
    ::= { trapinfo 1 }

sysTrapIpAddress1       OBJECT-TYPE
    SYNTAX		IpAddr
    MAX-ACCESS      	read-write
    STATUS          	current
    DESCRIPTION     	"Trap Destination IP Address"
    ::= { trapinfo 2 }

sysTrapIpAddress2       OBJECT-TYPE
    SYNTAX		IpAddr
    MAX-ACCESS      	read-write
    STATUS          	current
    DESCRIPTION     	"Trap Destination IP Address 2"
    ::= { trapinfo 3 }

sysTrapCommStr          OBJECT-TYPE
    SYNTAX		DisplayString (SIZE(1..32))
    MAX-ACCESS      	read-write
    STATUS          	current
    DESCRIPTION     	"Trap community string"
    ::= { trapinfo 4 }

image          		OBJECT IDENTIFIER ::= { sys 18 }

sysImageUpgrade		OBJECT-TYPE
    SYNTAX		INTEGER { FPGA(0), LINUX(1), ROOTFS(2), PIC(3), RFM(4)}
    MAX-ACCESS		read-write
    STATUS		current
    DESCRIPTION		"Upgrade specified image"
    ::= { image 1 }

sysImageToggle		OBJECT-TYPE
    SYNTAX		INTEGER { CURRENT(0), TOGGLE(1) }
    MAX-ACCESS		read-write
    STATUS		current
    DESCRIPTION		"Toggle to previous image"
    ::= { image 2 }

sysImageUpgradeStatus	OBJECT-TYPE
    SYNTAX		INTEGER { SUCCESS(0), FAILED(1), INPROGRESS(2) }
    MAX-ACCESS		read-only
    STATUS		current
    DESCRIPTION		"Get the current image upgrade progress status"
    ::= { image 3 }

sysRPSEnable            OBJECT-TYPE
    SYNTAX		INTEGER { OFF(0), ON(1) }
    MAX-ACCESS      	read-write
    STATUS          	current
    DESCRIPTION     	"Enable/Disable rapid port shutdown feature"
    ::= { sys 19 }

sysSmartMode            OBJECT-TYPE
    SYNTAX		INTEGER { OFF(0), ON(1) }
    MAX-ACCESS      	read-write
    STATUS          	current
    DESCRIPTION     	"Enable/Disable Smart mode"
    ::= { sys 20 }

sysResetDefaultIP       OBJECT-TYPE
    SYNTAX          	INTEGER { NA(0), RESET(1) }
    MAX-ACCESS      	read-write
    STATUS          	current
    DESCRIPTION     	"Reset ipconfig to default IP"
    ::= { sys 21 }

license       		OBJECT IDENTIFIER ::= { sys 22 }

sysLicense1Enable       OBJECT-TYPE
    SYNTAX		DisplayString
    MAX-ACCESS      	read-write
    STATUS          	current
    DESCRIPTION     	"Display current license key 1 status"
    ::= { license 1 }

sysLicense2Enable       OBJECT-TYPE
    SYNTAX		DisplayString
    MAX-ACCESS      	read-write
    STATUS          	current
    DESCRIPTION     	"Display current license key 2 status"
    ::= { license 2 }

sysConfigOption         OBJECT-TYPE
    SYNTAX              INTEGER { EXPORT(0), IMPORT(1), REMOVE(2) }
    MAX-ACCESS          read-write
    STATUS              current
    DESCRIPTION         "Perform config export, import or remove configuration
file"
    ::= { sys 23 }

diagnostic          	OBJECT IDENTIFIER ::= { sys 24 }

sysDiagnostic           OBJECT-TYPE
    SYNTAX              INTEGER { NONE(0), DIAGNOSTIC(1) }
    MAX-ACCESS          read-write
    STATUS              current
    DESCRIPTION         "Run diagnostic and put the data in a file"
    ::= { diagnostic 1 }

sysDiagnosticStatus     OBJECT-TYPE
    SYNTAX              INTEGER { SUCCESS(0), NOTREADY(1) }
    MAX-ACCESS          read-only
    STATUS              current
    DESCRIPTION         "Display current status of diagnostic command"
    ::= { diagnostic 2 }

syslog                  OBJECT IDENTIFIER ::= { sys 25 }

sysSyslogExport         OBJECT-TYPE
    SYNTAX              INTEGER { NONE(0), EXPORT(1) }
    MAX-ACCESS          read-write
    STATUS              current
    DESCRIPTION         "export syslog into a file"
    ::= { syslog 1 }

sysSyslogLevel          OBJECT-TYPE
    SYNTAX              INTEGER { NOSYSLOG(0), LEVEL0(1), LEVEL1(2), LEVEL01(3),
LEVEL2(4), LEVEL02(5), LEVEL12(6), LEVEL012(7) }
    MAX-ACCESS          read-write
    STATUS              current
    DESCRIPTION         "bitmap value for the loglevel"
    ::= { syslog 2 }

sysClearCounter         OBJECT-TYPE
        SYNTAX          INTEGER {  NONE(0), CLEAR(1) }
        MAX-ACCESS      read-write
        STATUS          current
        DESCRIPTION     "Clear current counters"
        ::= { sys 26 } 

standby                  OBJECT IDENTIFIER ::= { sys 27 }

sysStandbyLink         OBJECT-TYPE
        SYNTAX          INTEGER 
        MAX-ACCESS      read-only
        STATUS          current
        DESCRIPTION     "Standby unit link status"
        ::= { standby 1 } 

sysStandbyPll         OBJECT-TYPE
        SYNTAX          INTEGER
        MAX-ACCESS      read-only
        STATUS          current
        DESCRIPTION     "Standby link ODU¢PLL status"
        ::= { standby 2 } 

sysStandbyRSSI         OBJECT-TYPE
        SYNTAX          INTEGER 
        MAX-ACCESS      read-only
        STATUS          current
        DESCRIPTION     "Standby link RSSI value"
        ::= { standby 3 } 

sysEgressMargin         OBJECT-TYPE
        SYNTAX          INTEGER 
        MAX-ACCESS      read-write
        STATUS          current
        DESCRIPTION     "Configure Egress Margin"
        ::= { sys 28 } 

END
