TRANGO-APEX-MODEM-MIB DEFINITIONS ::= BEGIN

IMPORTS
	MODULE-IDENTITY,
	OBJECT-TYPE,
	OBJECT-IDENTITY,
	Unsigned32,
	NOTIFICATION-TYPE,
        apex
                FROM TRANGO-APEX-MIB	        
        DisplayString
		FROM SNMPv2-TC
        IpAddress, Opaque
	        FROM SNMPv2-SMI
	MODULE-COMPLIANCE
		FROM SNMPv2-CONF;
	
-- *******************************************************************
-- ** PVG310 Modem Information ** trango.twb.apex.pvg
-- *******************************************************************

modem			OBJECT IDENTIFIER ::= { apex 2 }

modemLoopbackMode	OBJECT-TYPE
    	SYNTAX		INTEGER { OFF(0), DIGITAL(1), IF(2), RFGEN(3), RFREFL(4) }
	MAX-ACCESS	read-write
	STATUS		current
	DESCRIPTION	"Set/Display the Loopback Mode"
	::= { modem 1 }

modemDataPattern	OBJECT-TYPE
    	SYNTAX		INTEGER { EXT(0), INT(1) }
	MAX-ACCESS	read-write
	STATUS		current
	DESCRIPTION	"Set/Display the current Loopback Pattern (source)"
	::= { modem 2 }

modemBER   		OBJECT-TYPE
	SYNTAX  	DisplayString
	MAX-ACCESS	read-only
	STATUS		current
	DESCRIPTION	"Read current Bit Error Rate"
	::= { modem 3 }

modemMSE   		OBJECT-TYPE
	SYNTAX  	INTEGER
	MAX-ACCESS	read-only
	STATUS		current
	DESCRIPTION	"Read current Mean Squared Error"
	::= { modem 4 }

modemFER   		OBJECT-TYPE
	SYNTAX  	DisplayString
	MAX-ACCESS	read-only
	STATUS		current
	DESCRIPTION	"Read current Mean Squared Error"
	::= { modem 5 }

lock			OBJECT IDENTIFIER ::= { modem 6 }

modemLockStatus   	OBJECT-TYPE
	SYNTAX  	INTEGER { UNLOCKED(0), LOCKED(1), PROGRESS(2) } 
	MAX-ACCESS	read-only
	STATUS		current
	DESCRIPTION	"Read current Internal Automatic Gain Correction"
	::= { lock 1 }

modemTimingLock   	OBJECT-TYPE
	SYNTAX  	INTEGER { NOTLOCKED(0), LOCKED(1) }
	MAX-ACCESS	read-only
	STATUS		current
	DESCRIPTION	"Indicate RX Timing Lock status"
	::= { lock 2 }

modemPreambleLock   	OBJECT-TYPE
	SYNTAX  	INTEGER { NOTLOCKED(0), LOCKED(1) }
	MAX-ACCESS	read-only
	STATUS		current
	DESCRIPTION	"Indicate Preamble Lock status"
	::= { lock 3 }

modemLdpcLock   	OBJECT-TYPE
	SYNTAX  	INTEGER { NOTLOCKED(0), LOCKED(1) }
	MAX-ACCESS	read-only
	STATUS		current
	DESCRIPTION	"Indicate LDPC Lock status"
	::= { lock 4 }


modemReserved 		OBJECT-TYPE
	SYNTAX  	INTEGER 
	MAX-ACCESS	read-only
	STATUS		current
	DESCRIPTION	"Reserved"
	::= { lock 5 }

acm			OBJECT IDENTIFIER ::= { modem 7 }

modemACMEnable		OBJECT-TYPE	
	SYNTAX  	INTEGER { DISABLED(0), ENABLED(1) }
	MAX-ACCESS	read-write
	STATUS		current
	DESCRIPTION	"Enable/Disable Adaptive Modulation feature"
	::= { acm 1 }

acmprofile		OBJECT IDENTIFIER ::= { acm 2 }

modemACMProfileQPSKEnable		OBJECT-TYPE	
	SYNTAX  	INTEGER { DISABLED(0), ENABLED(1) }
	MAX-ACCESS	read-write
	STATUS		current
	DESCRIPTION	"Enable/Disable ACM QPSK profile"
	::= { acmprofile 1 }

modemACMProfileQAM16Enable		OBJECT-TYPE	
	SYNTAX  	INTEGER { DISABLED(0), ENABLED(1) }
	MAX-ACCESS	read-write
	STATUS		current
	DESCRIPTION	"Enable/Disable ACM QAM16 profile"
	::= { acmprofile 2 }

modemACMProfileQAM32Enable		OBJECT-TYPE	
	SYNTAX  	INTEGER { DISABLED(0), ENABLED(1) }
	MAX-ACCESS	read-write
	STATUS		current
	DESCRIPTION	"Enable/Disable ACM QAM32 profile"
	::= { acmprofile 3 }

modemACMProfileQAM64Enable		OBJECT-TYPE	
	SYNTAX  	INTEGER { DISABLED(0), ENABLED(1) }
	MAX-ACCESS	read-write
	STATUS		current
	DESCRIPTION	"Enable/Disable ACM QAM64 profile"
	::= { acmprofile 4 }

modemACMProfileQAM128Enable		OBJECT-TYPE	
	SYNTAX  	INTEGER { DISABLED(0), ENABLED(1) }
	MAX-ACCESS	read-write
	STATUS		current
	DESCRIPTION	"Enable/Disable ACM QAM128 profile"
	::= { acmprofile 5 }

modemACMProfileQAM256Enable		OBJECT-TYPE	
	SYNTAX  	INTEGER { DISABLED(0), ENABLED(1) }
	MAX-ACCESS	read-write
	STATUS		current
	DESCRIPTION	"Enable/Disable ACM QAM256 profile"
	::= { acmprofile 6 }

acmMSEImprove		OBJECT IDENTIFIER ::= { acm 3 }

modemACMQPSKMSEImprove		OBJECT-TYPE	
	SYNTAX  	Opaque
	MAX-ACCESS	read-write
	STATUS		current
	DESCRIPTION	"MSE Improve threshold for QPSK profile"
	::= { acmMSEImprove 1 }

modemACMQAM16MSEImprove		OBJECT-TYPE	
	SYNTAX  	Opaque
	MAX-ACCESS	read-write
	STATUS		current
	DESCRIPTION	"MSE Improve threshold for QAM16 profile"
	::= { acmMSEImprove 2 }

modemACMQAM32MSEImprove		OBJECT-TYPE	
	SYNTAX  	Opaque
	MAX-ACCESS	read-write
	STATUS		current
	DESCRIPTION	"MSE Improve threshold for QAM32 profile"
	::= { acmMSEImprove 3 }

modemACMQAM64MSEImprove		OBJECT-TYPE	
	SYNTAX  	Opaque
	MAX-ACCESS	read-write
	STATUS		current
	DESCRIPTION	"MSE Improve threshold for QAM64 profile"
	::= { acmMSEImprove 4 }

modemACMQAM128MSEImprove		OBJECT-TYPE	
	SYNTAX  	Opaque
	MAX-ACCESS	read-write
	STATUS		current
	DESCRIPTION	"MSE Improve threshold for QAM128 profile"
	::= { acmMSEImprove 5 }

modemACMQAM256MSEImprove		OBJECT-TYPE	
	SYNTAX  	Opaque
	MAX-ACCESS	read-write
	STATUS		current
	DESCRIPTION	"MSE Improve threshold for QAM256 profile"
	::= { acmMSEImprove 6 }

acmMSEDegrade		OBJECT IDENTIFIER ::= { acm 4 }

modemACMQPSKMSEDegrade		OBJECT-TYPE	
	SYNTAX  	Opaque
	MAX-ACCESS	read-write
	STATUS		current
	DESCRIPTION	"MSE Degrade threshold for QPSK profile"
	::= { acmMSEDegrade 1 }

modemACMQAM16MSEDegrade		OBJECT-TYPE	
	SYNTAX  	Opaque
	MAX-ACCESS	read-write
	STATUS		current
	DESCRIPTION	"MSE Degrade threshold for QAM16 profile"
	::= { acmMSEDegrade 2 }

modemACMQAM32MSEDegrade		OBJECT-TYPE	
	SYNTAX  	Opaque
	MAX-ACCESS	read-write
	STATUS		current
	DESCRIPTION	"MSE Degrade threshold for QAM32 profile"
	::= { acmMSEDegrade 3 }

modemACMQAM64MSEDegrade		OBJECT-TYPE	
	SYNTAX  	Opaque
	MAX-ACCESS	read-write
	STATUS		current
	DESCRIPTION	"MSE Degrade threshold for QAM64 profile"
	::= { acmMSEDegrade 4 }

modemACMQAM128MSEDegrade		OBJECT-TYPE	
	SYNTAX  	Opaque
	MAX-ACCESS	read-write
	STATUS		current
	DESCRIPTION	"MSE Degrade threshold for QAM128 profile"
	::= { acmMSEDegrade 5 }

modemACMQAM256MSEDegrade		OBJECT-TYPE	
	SYNTAX  	Opaque
	MAX-ACCESS	read-write
	STATUS		current
	DESCRIPTION	"MSE Degrade threshold for QAM256 profile"
	::= { acmMSEDegrade 6 }

profile			OBJECT IDENTIFIER ::= { modem 8 }

modemACMTxProfile	OBJECT-TYPE	
	SYNTAX  	INTEGER
	MAX-ACCESS	read-write
	STATUS		current
	DESCRIPTION	"ACM Tx Profile"
	::= { profile 1 }

modemACMRxProfile	OBJECT-TYPE	
	SYNTAX  	INTEGER
	MAX-ACCESS	read-write
	STATUS		current
	DESCRIPTION	"ACM Rx Profile"
	::= { profile 2 }

END
