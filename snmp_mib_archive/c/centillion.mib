-- MIB created 9/24/97 17:32:31, by
--   SMIC (the next generation) version 1.6.31, December 11, 1994.
-- CHANGE LOG
-- 092497 schiang
--   ***** NOTE ***** 
--   Changed the definition of AtmAddr to (0..20) due to smic
--   compiler restriction, BUT THE AGENT FOLLOWS THE STATNDARD
--   DEFINITIONS of (0|8|20).
--
--   Changed AtmIlmiNetworkPrefix to OCTET STRING(SIZE(8 .. 13))
--   due to smic restriction.
--
--   Added atmMIB and atmMIBObjects and modified the definition
--   for atmTCMIB and atmTrafficDescriptorTypes.
--   'smic' does not accept {mib-2 37 3} nor {mib-2 37 1 1}
--

ATM-TC-MIB DEFINITIONS ::= BEGIN

-- From file: "atm-tc.mi2"
-- Compile options "4 G A M"

IMPORTS
    Integer32, TimeTicks
            FROM SNMPv2-SMI-v1
    mib-2
            FROM RFC1213-MIB;

atmMIB        OBJECT IDENTIFIER ::= {mib-2 37}
atmMIBObjects OBJECT IDENTIFIER ::= { atmMIB 1 }

atmTCMIB      OBJECT IDENTIFIER ::= { atmMIB 3}

-- atmTCMIB OBJECT IDENTIFIER ::= {mib-2 37 3}
-- MODULE-IDENTITY
--  LastUpdated
--    9701080200Z
--  OrgName
--    IETF AToMMIB Working Group
--  ContactInfo
--              Michael Noto
--      Postal:  Network Equipment Technologies
--               800 Saginaw Drive RM 21.1.111
--               Redwood City, CA 94063
--               USA
--      Tel:     +1 415 569-7134
--      E-mail:  mike_noto@net.com
--    
--               Ethan Mickey Spiegel
--      Postal:  Cisco Systems
--               170 W. Tasman Dr.
--               San Jose, CA 95134
--               USA
--      Tel:     +1 408 526 6408
--      E-mail:  mspiegel@cisco.com
--    
--               Kaj Tesink
--      Postal:  Bell Communications Research
--               331 Newman Springs Road
--               Red Bank, NJ 07701
--               USA
--      Tel:     +1 908 758 5254
--      Fax:     +1 908 758 4177
--      E-mail:  kaj@cc.bellcore.com
--  Descr
--    This MIB Module provides Textuanl Coventions
--    and OBJECT-IDENTITY Objects to be used by
--    ATM systems.


-- 092497 schiang
-- Following is the output from smicn however is not acceptable
-- by smic thus need some work around.
--atmTrafficDescriptorTypes OBJECT IDENTIFIER ::= { mib-2 37 1 1 }

atmTrafficDescriptorTypes OBJECT IDENTIFIER ::= { atmMIBObjects 1 }

-- All other and new OBJECT IDENTITIES go here:
atmObjectIdentities OBJECT IDENTIFIER ::= { atmTCMIB 1 }

atmNoTrafficDescriptor OBJECT IDENTIFIER ::= { atmTrafficDescriptorTypes 1 }
-- OBJECT-IDENTITY
--  Status
--    obsolete
--  Descr
--    This identifies the no ATM traffic
--    descriptor type.  Parameters 1, 2, 3, 4,
--    and 5 are not used.  This traffic descriptor
--    type can be used for best effort traffic.

atmNoClpNoScr OBJECT IDENTIFIER ::= { atmTrafficDescriptorTypes 2 }
-- OBJECT-IDENTITY
--  Status
--    mandatory
--  Descr
--    This traffic descriptor type is for no CLP
--    and no Sustained Cell Rate.  The use of the
--    parameter vector for this type:
--    Parameter 1: peak cell rate in cells/second
--                 for CLP=0+1 traffic
--    Parameter 2: CDVT in tenths of microseconds
--    Parameter 3: not used
--    Parameter 4: not used
--    Parameter 5: not used.
--    
--    This traffic descriptor type is applicable to
--    CBR connections following the UNI 3.0/3.1
--    conformance definition for PCR CLP=0+1 [3,4].
--    These CBR connections differ from CBR.1
--    connections [13] in that the CLR objective
--    applies only to the CLP=0 cell flow.
--    
--    This traffic descriptor type is also
--    applicable to connections following the UBR.1
--    conformance definition [13].

atmClpNoTaggingNoScr OBJECT IDENTIFIER ::= { atmTrafficDescriptorTypes 3 }
-- OBJECT-IDENTITY
--  Status
--    obsolete
--  Descr
--    This traffic descriptor is for CLP without
--    tagging and no Sustained Cell Rate.  The use
--    of the parameter vector for this type:
--    Parameter 1: peak cell rate in cells/second
--                 for CLP=0+1 traffic
--    Parameter 2: peak cell rate in cells/second
--                 for CLP=0 traffic
--    Parameter 3: not used
--    Parameter 4: not used
--    Parameter 5: not used.

atmClpTaggingNoScr OBJECT IDENTIFIER ::= { atmTrafficDescriptorTypes 4 }
-- OBJECT-IDENTITY
--  Status
--    obsolete
--  Descr
--    This traffic descriptor is for CLP with
--    tagging and no Sustained Cell Rate.  The use
--    of the parameter vector for this type:
--    Parameter 1: peak cell rate in cells/second
--                 for CLP=0+1 traffic
--    Parameter 2: peak cell rate in cells/second
--                 for CLP=0 traffic, excess
--                 tagged as CLP=1
--    Parameter 3: not used
--    Parameter 4: not used
--    Parameter 5: not used.

atmNoClpScr OBJECT IDENTIFIER ::= { atmTrafficDescriptorTypes 5 }
-- OBJECT-IDENTITY
--  Status
--    mandatory
--  Descr
--    This traffic descriptor type is for no CLP
--    with Sustained Cell Rate.  The use of the
--    parameter vector for this type:
--    Parameter 1: peak cell rate in cells/second
--                 for CLP=0+1 traffic
--    Parameter 2: sustainable cell rate in cells/second
--                 for CLP=0+1 traffic
--    Parameter 3: maximum burst size in cells
--    Parameter 4: CDVT in tenths of microseconds
--    Parameter 5: not used.
--    
--    This traffic descriptor type is applicable
--    to VBR connections following the UNI 3.0/3.1
--    conformance definition for PCR CLP=0+1 and
--    SCR CLP=0+1 [3,4].  These VBR connections
--    differ from VBR.1 connections [13] in that
--    the CLR objective applies only to the CLP=0
--    cell flow.

atmClpNoTaggingScr OBJECT IDENTIFIER ::= { atmTrafficDescriptorTypes 6 }
-- OBJECT-IDENTITY
--  Status
--    mandatory
--  Descr
--    This traffic descriptor type is for CLP with
--    Sustained Cell Rate and no tagging.  The use
--    of the parameter vector for this type:
--    Parameter 1: peak cell rate in cells/second
--                 for CLP=0+1 traffic
--    Parameter 2: sustainable cell rate in cells/second
--                 for CLP=0 traffic
--    Parameter 3: maximum burst size in cells
--    Parameter 4: CDVT in tenths of microseconds
--    Parameter 5: not used.
--    
--    This traffic descriptor type is applicable to
--    connections following the VBR.2 conformance
--    definition [13].

atmClpTaggingScr OBJECT IDENTIFIER ::= { atmTrafficDescriptorTypes 7 }
-- OBJECT-IDENTITY
--  Status
--    mandatory
--  Descr
--    This traffic descriptor type is for CLP with
--    tagging and Sustained Cell Rate.  The use of
--    the parameter vector for this type:
--    Parameter 1: peak cell rate in cells/second
--                 for CLP=0+1 traffic
--    Parameter 2: sustainable cell rate in cells/second
--                 for CLP=0 traffic, excess tagged as
--                 CLP=1
--    Parameter 3: maximum burst size in cells
--    Parameter 4: CDVT in tenths of microseconds
--    Parameter 5: not used.
--    
--    This traffic descriptor type is applicable to
--    connections following the VBR.3 conformance
--    definition [13].

atmClpNoTaggingMcr OBJECT IDENTIFIER ::= { atmTrafficDescriptorTypes 8 }
-- OBJECT-IDENTITY
--  Status
--    mandatory
--  Descr
--    This traffic descriptor type is for CLP with
--    Minimum Cell Rate and no tagging.  The use of
--    the parameter vector for this type:
--    Parameter 1: peak cell rate in cells/second
--                 for CLP=0+1 traffic
--    Parameter 2: CDVT in tenths of microseconds
--    Parameter 3: minimum cell rate in cells/second
--    Parameter 4: unused
--    Parameter 5: unused.
--    
--    This traffic descriptor type is applicable to
--    connections following the ABR conformance
--    definition [13].

atmClpTransparentNoScr OBJECT IDENTIFIER ::= { atmTrafficDescriptorTypes 9 }
-- OBJECT-IDENTITY
--  Status
--    mandatory
--  Descr
--    This traffic descriptor type is for the CLP-
--    transparent model [13] and no Sustained Cell Rate.
--    The use of the parameter vector for this type:
--    Parameter 1: peak cell rate in cells/second
--                 for CLP=0+1 traffic
--    Parameter 2: CDVT in tenths of microseconds
--    Parameter 3: not used
--    Parameter 4: not used
--    Parameter 5: not used.
--    
--    This traffic descriptor type is applicable to
--    connections following the CBR.1 conformance
--    definition [13].
--    
--    Connections specifying this traffic descriptor
--    type will be rejected at UNI 3.0 or UNI 3.1
--    interfaces.  For a similar traffic descriptor
--    type that can be accepted at UNI 3.0 and
--    UNI 3.1 interfaces, see atmNoClpNoScr.

atmClpTransparentScr OBJECT IDENTIFIER ::= { atmTrafficDescriptorTypes 10 }
-- OBJECT-IDENTITY
--  Status
--    mandatory
--  Descr
--    This traffic descriptor type is for the CLP-
--    transparent model [13] with Sustained Cell Rate.
--    The use of the parameter vector for this type:
--    Parameter 1: peak cell rate in cells/second
--                 for CLP=0+1 traffic
--    Parameter 2: sustainable cell rate in cells/second
--                 for CLP=0+1 traffic
--    Parameter 3: maximum burst size in cells
--    Parameter 4: CDVT in tenths of microseconds
--    Parameter 5: not used.
--    
--    This traffic descriptor type is applicable to
--    connections following the VBR.1 conformance
--    definition [13].
--    
--    Connections specifying this traffic descriptor
--    type will be rejected at UNI 3.0 or UNI 3.1
--    interfaces.  For a similar traffic descriptor
--    type that can be accepted at UNI 3.0 and
--    UNI 3.1 interfaces, see atmNoClpScr.

atmNoClpTaggingNoScr OBJECT IDENTIFIER ::= { atmTrafficDescriptorTypes 11 }
-- OBJECT-IDENTITY
--  Status
--    mandatory
--  Descr
--    This traffic descriptor type is for no CLP
--    with tagging and no Sustained Cell Rate.  The
--    use of the parameter vector for this type:
--    Parameter 1: peak cell rate in cells/second
--                 for CLP=0+1 traffic
--    Parameter 2: CDVT in tenths of microseconds
--    Parameter 3: not used
--    Parameter 4: not used
--    Parameter 5: not used.
--    
--    This traffic descriptor type is applicable to
--    connections following the UBR.2 conformance
--    definition [13].

AtmAddr ::= OCTET STRING(SIZE(0..20))
--AtmAddr ::= OCTET STRING(SIZE(0 | 8 | 20))
-- TEXTUAL-CONVENTION
--  DspHint
--    1x
--  Status
--    mandatory
--  Descr
--    The ATM address used by the network entity.
--    The address types are: no address (0 octets),
--    E.164 (8 octets), and NSAP (20 octets).
--    Note: The E.164 address is encoded in BCD
--    format.

AtmConnCastType ::= INTEGER {
        p2p(1),
        p2mpRoot(2),
        p2mpLeaf(3)
        }
-- TEXTUAL-CONVENTION
--  Status
--    mandatory
--  Descr
--    The type of topology of a connection (point-
--    to-point, point-to-multipoint). In the case
--    of point-to-multipoint, the orientation of
--    this VPL or VCL in the connection.
--    On a host:
--    - p2mpRoot indicates that the host
--      is the root of the p2mp connection.
--    - p2mpLeaf indicates that the host
--      is a leaf of the p2mp connection.
--    On a switch:
--    - p2mpRoot indicates that cells received
--      by the switching fabric from the interface
--      are from the root of the p2mp connection.
--    - p2mpLeaf indicates that cells transmitted
--      to the interface from the switching fabric
--      are to the leaf of the p2mp connection.

AtmConnKind ::= INTEGER {
        pvc(1),
        svcIncoming(2),
        svcOutgoing(3),
        spvcInitiator(4),
        spvcTarget(5)
        }
-- TEXTUAL-CONVENTION
--  Status
--    mandatory
--  Descr
--    The use of call control. The use is as
--    follows:
--       pvc(1)
--          Virtual link of a PVC. Should not be
--          used in an PVC/SVC (i.e., SPVC)
--          crossconnect.
--       svcIncoming(2)
--          Virtual link established after a
--          received signaling request to setup
--          an SVC.
--       svcOutgoing(3)
--          Virtual link established after a
--          transmitted or forwarded signaling
--          request to setup an SVC.
--       spvcInitiator(4)
--          Virtual link at the PVC side of an
--          SVC/PVC crossconnect, where the
--          switch is the initiator of the SPVC
--          setup.
--       spvcTarget(5)
--          Virtual link at the PVC side of an
--          SVC/PVC crossconnect, where the
--          switch is the target of the SPVC
--          setup.
--    
--    An spvcInitiator is always cross-connected to
--    an svcOutgoing, and an spvcTarget is always
--    cross-connected to an svcIncoming.

AtmIlmiNetworkPrefix ::= OCTET STRING(SIZE(8..13))
--AtmIlmiNetworkPrefix ::= OCTET STRING(SIZE(8 | 13))
-- TEXTUAL-CONVENTION
--  Status
--    mandatory
--  Descr
--    A network prefix used for ILMI address
--    registration.  In the case of ATM endsystem
--    addresses (AESAs), the network prefix is the first
--    13 octets of the address which includes the AFI,
--    IDI, and HO-DSP fields.  In the case of native
--    E.164 addresses, the network prefix is the entire
--    E.164 address encoded in 8 octets, as if it were
--    an E.164 IDP in an ATM endsystem address
--    structure.
--  Refer
--    ATM Forum ILMI 4.0 Section 9,
--     ATM Forum UNI Signalling 4.0 Section 3

AtmInterfaceType ::= INTEGER {
        other(1),
        autoConfig(2),
        ituDss2(3),
        atmfUni3Dot0(4),
        atmfUni3Dot1(5),
        atmfUni4Dot0(6),
        atmfIispUni3Dot0(7),
        atmfIispUni3Dot1(8),
        atmfIispUni4Dot0(9),
        atmfPnni1Dot0(10),
        atmfBici2Dot0(11),
        atmfUniPvcOnly(12),
        atmfNniPvcOnly(13)
        }
-- TEXTUAL-CONVENTION
--  Status
--    mandatory
--  Descr
--    The connection setup procedures used for the
--    identified interface.
--    
--    Other: Connection setup procedures other than
--       those listed below.
--    
--    Auto-configuration:
--       Indicates that the connection setup
--       procedures are to be determined dynamically,
--       or that determination has not yet been
--       completed. One such mechanism is via ATM
--       Forum ILMI auto-configuration procedures.
--    
--    ITU-T DSS2:
--    -  ITU-T Recommendation Q.2931, Broadband
--       Integrated Service Digital Network (B-ISDN)
--       Digital Subscriber Signalling System No.2
--       (DSS2) User-Network Interface (UNI) Layer 3
--       Specification for Basic Call/Connection
--       Control (September 1994) [5]
--    -  ITU-T Draft Recommendation Q.2961,
--       B-ISDN DSS 2 Support of Additional Traffic
--       Parameters (May 1995) [8]
--    
--    -  ITU-T Draft Recommendation Q.2971,
--       B-ISDN DSS 2 User Network Interface Layer 3
--       Specification for Point-to-multipoint
--       Call/connection Control (May 1995) [9]
--    
--    ATM Forum UNI 3.0:
--       ATM Forum, ATM User-Network Interface,
--       Version 3.0 (UNI 3.0) Specification,
--       (1994) [3].
--    
--    ATM Forum UNI 3.1:
--       ATM Forum, ATM User-Network Interface,
--       Version 3.1 (UNI 3.1) Specification,
--       (November 1994) [4].
--    
--    ATM Forum UNI Signalling 4.0:
--       ATM Forum, ATM User-Network Interface (UNI)
--       Signalling Specification Version 4.0,
--       af-sig-0061.000 (June 1996) [7].
--    
--    ATM Forum IISP (based on UNI 3.0 or UNI 3.1) :
--       Interim Inter-switch Signaling Protocol
--       (IISP) Specification, Version 1.0,
--       af-pnni-0026.000, (December 1994) [10].
--    
--    ATM Forum PNNI 1.0 :
--       ATM Forum, Private Network-Network Interface
--       Specification, Version 1.0, af-pnni-0055.000,
--       (March 1996) [6].
--    
--    ATM Forum B-ICI:
--       ATM Forum, B-ICI Specification, Version 2.0,
--       af-bici-0013.002, (November 1995) [11].
--    
--    ATM Forum UNI PVC Only:
--       An ATM Forum compliant UNI with the
--       signalling disabled.
--    
--    ATM Forum NNI PVC Only:
--       An ATM Forum compliant NNI with the
--       signalling disabled.

AtmServiceCategory ::= INTEGER {
        other(1),
        cbr(2),
        rtVbr(3),
        nrtVbr(4),
        abr(5),
        ubr(6)
        }
-- TEXTUAL-CONVENTION
--  Status
--    mandatory
--  Descr
--    The service category for a connection.
--  Refer
--    ATM Forum Traffic Management 4.0.

AtmSigDescrParamIndex ::= INTEGER(0..2147483647)
-- TEXTUAL-CONVENTION
--  Status
--    mandatory
--  Descr
--    The value of this object identifies a row in the
--    atmSigDescrParamTable. The value 0 signifies that
--    none of the signalling parameters defined in the
--    atmSigDescrParamTable are applicable.

AtmTrafficDescrParamIndex ::= INTEGER(0..2147483647)
-- TEXTUAL-CONVENTION
--  Status
--    mandatory
--  Descr
--    The value of this object identifies a row in the
--    atmTrafficDescrParamTable. The value 0 signifies
--    that no row has been identified.

AtmVcIdentifier ::= INTEGER(0..65535)
-- TEXTUAL-CONVENTION
--  Status
--    mandatory
--  Descr
--    The VCI value for a VCL. The maximum VCI value
--    cannot exceed the value allowable by
--    atmInterfaceMaxVciBits defined in ATM-MIB.

AtmVpIdentifier ::= INTEGER(0..4095)
-- TEXTUAL-CONVENTION
--  Status
--    mandatory
--  Descr
--    The VPI value for a VPL or VCL. The value VPI=0
--    is only allowed for a VCL. For ATM UNIs supporting
--    VPCs the VPI value ranges from 1 to 255. For ATM
--    UNIs supporting VCCs the VPI value ranges from 0
--    to 255.  For ATM NNIs the VPI value ranges from 0
--    to 4095.  The maximum VPI value cannot exceed the
--    value allowable by atmInterfaceMaxVpiBits defined
--    in ATM-MIB.

AtmVorXAdminStatus ::= INTEGER {
        up(1),
        down(2)
        }
-- TEXTUAL-CONVENTION
--  Status
--    mandatory
--  Descr
--    The value determines the desired administrative
--    status of a virtual link or cross-connect. The up
--    and down states indicate that the traffic flow is
--    enabled or disabled respectively on the virtual
--    link or cross-connect.

AtmVorXLastChange ::= TimeTicks
-- TEXTUAL-CONVENTION
--  Status
--    mandatory
--  Descr
--    The value of MIB II's sysUpTime at the time this
--    virtual link or cross-connect entered its current
--    operational state. If the current state was
--    entered prior to the last re-initialization of the
--    agent then this object contains a zero value.

AtmVorXOperStatus ::= INTEGER {
        up(1),
        down(2),
        unknown(3)
        }
-- TEXTUAL-CONVENTION
--  Status
--    mandatory
--  Descr
--    The value determines the operational status of a
--    virtual link or cross-connect. The up and down
--    states indicate that the traffic flow is enabled
--    or disabled respectively on the virtual link or
--    cross-connect. The unknown state indicates that
--    the state of it cannot be determined. The state
--    will be down or unknown if the supporting ATM
--    interface(s) is down or unknown respectively.


END

-- MIB created 9/24/97 11:30:14, by
--   SMIC (the next generation) version 1.6.31, December 11, 1994.
-- CHANGE LOG
-- 092497 schiang
-- Removed experimental from IMPORTS
-- Moved atmMIB and atmMIBObjects object identifiers to ATM-TC-MIB
-- Changed to import ifIndex from rfc1213.

ATM-MIB DEFINITIONS ::= BEGIN

-- From file: "atm1.mi2"
-- Compile options "4 G A M"

IMPORTS
    IpAddress
	    FROM RFC1155-SMI 
    Counter32, Integer32
            FROM SNMPv2-SMI-v1
    OBJECT-TYPE
            FROM RFC-1212
    mib-2, ifIndex
            FROM RFC1213-MIB
    DisplayString, RowStatus
            FROM SNMPv2-TC-v1
    InterfaceIndex
            FROM IF-MIB
    atmMIB, atmMIBObjects 
	    FROM ATM-TC-MIB 

    AtmAddr, AtmConnKind, AtmConnCastType, AtmServiceCategory, 
    AtmTrafficDescrParamIndex, AtmVpIdentifier, AtmVcIdentifier, 
    AtmVorXAdminStatus, AtmVorXLastChange, AtmVorXOperStatus, 
    atmNoTrafficDescriptor
            FROM ATM-TC-MIB;

--atmMIB OBJECT IDENTIFIER ::= { experimental 41 }
-- MODULE-IDENTITY
--  LastUpdated
--    9701081122Z
--  OrgName
--    IETF AToM MIB Working Group
--  ContactInfo
--              Kaj Tesink
--      Postal:  Bellcore
--               331 Newman Springs Road
--               Red Bank, NJ 07701
--      Tel:     908-758-5254
--      Fax:     908-758-4177
--      E-mail:  kaj@cc.bellcore.com
--  Descr
--    This is the MIB Module for ATM and AAL5-related
--     objects for managing ATM interfaces, ATM virtual
--     links, ATM cross-connects, AAL5 entities, and
--     and AAL5 connections.
--  RevDate
--    9406072245Z
--  RevDescr
--    RFC1695

atmMIBConformance OBJECT IDENTIFIER ::= { atmMIB 2 }
atmMIBGroups    OBJECT IDENTIFIER ::= { atmMIBConformance 1 }
atmMIBCompliances OBJECT IDENTIFIER ::= { atmMIBConformance 2 }

atmInterfaceConfTable OBJECT-TYPE
    SYNTAX SEQUENCE OF AtmInterfaceConfEntry
    ACCESS not-accessible
    STATUS mandatory
    DESCRIPTION
        "This table contains ATM local interface
         configuration parameters, one entry per ATM
         interface port."
    ::= { atmMIBObjects 2 }

atmInterfaceConfEntry OBJECT-TYPE
    SYNTAX AtmInterfaceConfEntry
    ACCESS not-accessible
    STATUS mandatory
    DESCRIPTION
        "This list contains ATM interface configuration
         parameters and state variables and is indexed
         by ifIndex values of ATM interfaces."
    INDEX { ifIndex }
    ::= { atmInterfaceConfTable 1 }

AtmInterfaceConfEntry ::= SEQUENCE {
    atmInterfaceMaxVpcs INTEGER,
    atmInterfaceMaxVccs INTEGER,
    atmInterfaceConfVpcs INTEGER,
    atmInterfaceConfVccs INTEGER,
    atmInterfaceMaxActiveVpiBits INTEGER,
    atmInterfaceMaxActiveVciBits INTEGER,
    atmInterfaceIlmiVpi AtmVpIdentifier,
    atmInterfaceIlmiVci AtmVcIdentifier,
    atmInterfaceAddressType INTEGER,
    atmInterfaceAdminAddr AtmAddr,
    atmInterfaceMyNeighborIpAddress IpAddress,
    atmInterfaceMyNeighborIfName DisplayString,
    atmInterfaceCurrentMaxVpiBits INTEGER,
    atmInterfaceCurrentMaxVciBits INTEGER,
    atmInterfaceSubscrAddress AtmAddr
    }

atmInterfaceMaxVpcs OBJECT-TYPE
    SYNTAX INTEGER(0..4096)
    ACCESS read-write
    STATUS mandatory
    DESCRIPTION
        "The maximum number of VPCs (PVPCs and SVPCs)
         supported at this ATM interface. At the ATM UNI,
         the maximum number of VPCs (PVPCs and SVPCs)
         ranges from 0 to 256 only."
    ::= { atmInterfaceConfEntry 1 }

atmInterfaceMaxVccs OBJECT-TYPE
    SYNTAX INTEGER(0..65536)
    ACCESS read-write
    STATUS mandatory
    DESCRIPTION
        "The maximum number of VCCs (PVCCs and SVCCs)
         supported at this ATM interface."
    ::= { atmInterfaceConfEntry 2 }

atmInterfaceConfVpcs OBJECT-TYPE
    SYNTAX INTEGER(0..4096)
    ACCESS read-only
    STATUS mandatory
    DESCRIPTION
        "The number of VPCs (PVPC, Soft PVPC and SVPC)
         currently in use at this ATM interface.  It includes
         the number of PVPCs and Soft PVPCs that are configured
         at the interface, plus the number of SVPCs
         that are currently  established at the
         interface.
        
         At the ATM UNI, the configured number of
         VPCs (PVPCs and SVPCs) can range from
         0 to 256 only."
    ::= { atmInterfaceConfEntry 3 }

atmInterfaceConfVccs OBJECT-TYPE
    SYNTAX INTEGER(0..65536)
    ACCESS read-only
    STATUS mandatory
    DESCRIPTION
        "The number of VCCs (PVCC, Soft PVCC and SVCC)
         currently in use at this ATM interface.  It includes
         the number of PVCCs and Soft PVCCs that are configured
         at the interface, plus the number of SVCCs
         that are currently  established at the
         interface."
    ::= { atmInterfaceConfEntry 4 }

atmInterfaceMaxActiveVpiBits OBJECT-TYPE
    SYNTAX INTEGER(0..12)
    ACCESS read-write
    STATUS mandatory
    DESCRIPTION
        "The  maximum number of active VPI bits
         configured for use at the ATM interface.
         At the ATM UNI, the maximum number of active
         VPI bits configured for use ranges from
         0 to 8 only."
    ::= { atmInterfaceConfEntry 5 }

atmInterfaceMaxActiveVciBits OBJECT-TYPE
    SYNTAX INTEGER(0..16)
    ACCESS read-write
    STATUS mandatory
    DESCRIPTION
        "The maximum number of active VCI bits
         configured for use at this ATM interface."
    ::= { atmInterfaceConfEntry 6 }

atmInterfaceIlmiVpi OBJECT-TYPE
    SYNTAX AtmVpIdentifier
--    Rsyntax INTEGER(0..4095)
    ACCESS read-write
    STATUS mandatory
    DESCRIPTION
        "The VPI value of the VCC supporting
         the ILMI at this ATM interface.  If the values of
         atmInterfaceIlmiVpi and atmInterfaceIlmiVci are
         both equal to zero then the ILMI is not
         supported at this ATM interface."
    DEFVAL { 0 }
    ::= { atmInterfaceConfEntry 7 }

atmInterfaceIlmiVci OBJECT-TYPE
    SYNTAX AtmVcIdentifier
--    Rsyntax INTEGER(0..65535)
    ACCESS read-write
    STATUS mandatory
    DESCRIPTION
        "The VCI value of the VCC supporting
         the ILMI at this ATM interface.  If the values of
         atmInterfaceIlmiVpi and atmInterfaceIlmiVci are
         both equal to zero then the ILMI is not
         supported at this ATM interface."
    DEFVAL { 16 }
    ::= { atmInterfaceConfEntry 8 }

atmInterfaceAddressType OBJECT-TYPE
    SYNTAX INTEGER {
        private(1),
        nsapE164(2),
        nativeE164(3),
        other(4)
        }
    ACCESS read-only
    STATUS deprecated
    DESCRIPTION
        "The type of primary ATM address configured
         for use at this ATM interface."
    ::= { atmInterfaceConfEntry 9 }

atmInterfaceAdminAddr OBJECT-TYPE
    SYNTAX AtmAddr
--    Rsyntax OCTET STRING(SIZE(0 | 8 | 20))
    ACCESS read-only
    STATUS deprecated
    DESCRIPTION
        "The primary address assigned for administrative purposes,
         for example, an address associated with the
         service provider side of a public network UNI
         (thus, the value of this address corresponds
         with the value of ifPhysAddress at the host side).
         If this interface has no assigned administrative
         address, or when the address used for
         administrative purposes is the same as that used
         for ifPhysAddress, then this is an octet string of
         zero length."
    ::= { atmInterfaceConfEntry 10 }

atmInterfaceMyNeighborIpAddress OBJECT-TYPE
    SYNTAX IpAddress
    ACCESS read-write
    STATUS mandatory
    DESCRIPTION
        "The IP address of the neighbor system connected to
         the  far end of this interface, to which a Network
         Management Station can send SNMP messages, as IP
         datagrams sent to UDP port 161, in order to access
         network management information concerning the
         operation of that system.  Note that the value
         of this object may be obtained in different ways,
         e.g., by manual configuration, or through ILMI
         interaction with the neighbor system."
    ::= { atmInterfaceConfEntry 11 }

atmInterfaceMyNeighborIfName OBJECT-TYPE
    SYNTAX DisplayString
--    Rsyntax OCTET STRING(SIZE(0..255))
    ACCESS read-write
    STATUS mandatory
    DESCRIPTION
        "The textual name of the interface on the neighbor
         system on the far end of this interface, and to
         which this interface connects.  If the neighbor
         system is manageable through SNMP and supports
         the object ifName, the value of this object must
         be identical with that of ifName for the ifEntry
         of the lowest level physical interface
         for this port.  If this interface does not have a
         textual name, the value of this object is a zero
         length string.  Note that the value of this object
         may be obtained in different ways, e.g., by manual
         configuration, or through ILMI interaction with
         the neighbor system."
    ::= { atmInterfaceConfEntry 12 }

atmInterfaceCurrentMaxVpiBits OBJECT-TYPE
    SYNTAX INTEGER(0..12)
    ACCESS read-only
    STATUS mandatory
    DESCRIPTION
        "The maximum number of VPI Bits that may
         currently be used at this ATM interface.
         The value is the minimum of
         atmInterfaceMaxActiveVpiBits, and the
         atmInterfaceMaxActiveVpiBits of the interface's
         UNI/NNI peer.
         If the interface does not negotiate with
         its peer to determine the number of VPI Bits
         that can be used on the interface, then the
         value of this object must equal
         atmInterfaceMaxActiveVpiBits."
    ::= { atmInterfaceConfEntry 13 }

atmInterfaceCurrentMaxVciBits OBJECT-TYPE
    SYNTAX INTEGER(0..16)
    ACCESS read-only
    STATUS mandatory
    DESCRIPTION
        "The maximum number of VCI Bits that may
         currently be used at this ATM interface.
         The value is the minimum of
         atmInterfaceMaxActiveVciBits, and the
         atmInterfaceMaxActiveVpiBits of the interface's
         UNI/NNI peer.
        
         If the interface does not negotiate with
         its peer to determine the number of VCI Bits
         that can be used on the interface, then the
         value of this object must equal
         atmInterfaceMaxActiveVciBits."
    ::= { atmInterfaceConfEntry 14 }

atmInterfaceSubscrAddress OBJECT-TYPE
    SYNTAX AtmAddr
--    Rsyntax OCTET STRING(SIZE(0 | 8 | 20))
    ACCESS read-write
    STATUS mandatory
    DESCRIPTION
        "The identifier assigned by a service provider
         to the network side of a public network UNI.
         If this interface has no assigned service provider
         address, or for other interfaces this is an octet string
         of zero length."
    ::= { atmInterfaceConfEntry 15 }

atmInterfaceDs3PlcpTable OBJECT-TYPE
    SYNTAX SEQUENCE OF AtmInterfaceDs3PlcpEntry
    ACCESS not-accessible
    STATUS mandatory
    DESCRIPTION
        "This table contains ATM interface DS3 PLCP
         parameters and state variables, one entry per
         ATM interface port."
    ::= { atmMIBObjects 3 }

atmInterfaceDs3PlcpEntry OBJECT-TYPE
    SYNTAX AtmInterfaceDs3PlcpEntry
    ACCESS not-accessible
    STATUS mandatory
    DESCRIPTION
        "This list contains DS3 PLCP parameters and
         state variables at the ATM interface and is
         indexed by the ifIndex value of the ATM interface."
    INDEX { ifIndex }
    ::= { atmInterfaceDs3PlcpTable 1 }

AtmInterfaceDs3PlcpEntry ::= SEQUENCE {
    atmInterfaceDs3PlcpSEFSs Counter32,
    atmInterfaceDs3PlcpAlarmState INTEGER,
    atmInterfaceDs3PlcpUASs Counter32
    }

atmInterfaceDs3PlcpSEFSs OBJECT-TYPE
    SYNTAX Counter32
    ACCESS read-only
    STATUS mandatory
    DESCRIPTION
        "The number of DS3 PLCP Severely Errored Framing
         Second (SEFS). Each SEFS represents a
         one-second interval which contains
         one or more SEF event."
    ::= { atmInterfaceDs3PlcpEntry 1 }

atmInterfaceDs3PlcpAlarmState OBJECT-TYPE
    SYNTAX INTEGER {
        noAlarm(1),
        receivedFarEndAlarm(2),
        incomingLOF(3)
        }
    ACCESS read-only
    STATUS mandatory
    DESCRIPTION
        "This variable indicates if there is an
         alarm present for the DS3 PLCP.  The value
         receivedFarEndAlarm means that the DS3 PLCP
         has received an incoming Yellow
         Signal, the value incomingLOF means that
         the DS3 PLCP has declared a loss of frame (LOF)
         failure condition, and the value noAlarm
         means that there are no alarms present.
         Transition from the failure to the no alarm state
         occurs when no defects (e.g., LOF) are received
         for more than 10 seconds."
    ::= { atmInterfaceDs3PlcpEntry 2 }

atmInterfaceDs3PlcpUASs OBJECT-TYPE
    SYNTAX Counter32
    ACCESS read-only
    STATUS mandatory
    DESCRIPTION
        "The counter associated with the number of
         Unavailable Seconds encountered by the PLCP."
    ::= { atmInterfaceDs3PlcpEntry 3 }

atmInterfaceTCTable OBJECT-TYPE
    SYNTAX SEQUENCE OF AtmInterfaceTCEntry
    ACCESS not-accessible
    STATUS mandatory
    DESCRIPTION
        "This table contains ATM interface TC
         Sublayer parameters and state variables,
         one entry per ATM interface port."
    ::= { atmMIBObjects 4 }

atmInterfaceTCEntry OBJECT-TYPE
    SYNTAX AtmInterfaceTCEntry
    ACCESS not-accessible
    STATUS mandatory
    DESCRIPTION
        "This list contains TC Sublayer parameters
         and state variables at the ATM interface and is
         indexed by the ifIndex value of the ATM interface."
    INDEX { ifIndex }
    ::= { atmInterfaceTCTable 1 }

AtmInterfaceTCEntry ::= SEQUENCE {
    atmInterfaceOCDEvents Counter32,
    atmInterfaceTCAlarmState INTEGER
    }

atmInterfaceOCDEvents OBJECT-TYPE
    SYNTAX Counter32
    ACCESS read-only
    STATUS mandatory
    DESCRIPTION
        "The number of times the Out of Cell
         Delineation (OCD) events occur.  If seven
         consecutive ATM cells have Header Error
         Control (HEC) violations, an OCD event occurs.
         A high number of OCD events may indicate a
         problem with the TC Sublayer."
    ::= { atmInterfaceTCEntry 1 }

atmInterfaceTCAlarmState OBJECT-TYPE
    SYNTAX INTEGER {
        noAlarm(1),
        lcdFailure(2)
        }
    ACCESS read-only
    STATUS mandatory
    DESCRIPTION
        "This variable indicates if there is an
         alarm present for the TC Sublayer.  The value
         lcdFailure(2) indicates that the TC Sublayer
         is currently in the Loss of Cell Delineation
         (LCD) defect maintenance state.  The value
         noAlarm(1) indicates that the TC Sublayer
         is currently not in the LCD defect
         maintenance state."
    ::= { atmInterfaceTCEntry 2 }

atmTrafficDescrParamTable OBJECT-TYPE
    SYNTAX SEQUENCE OF AtmTrafficDescrParamEntry
    ACCESS not-accessible
    STATUS mandatory
    DESCRIPTION
        "This table contains information on ATM traffic
         descriptor type and the associated parameters."
    ::= { atmMIBObjects 5 }

atmTrafficDescrParamEntry OBJECT-TYPE
    SYNTAX AtmTrafficDescrParamEntry
    ACCESS not-accessible
    STATUS mandatory
    DESCRIPTION
        "This list contains ATM traffic descriptor
         type and the associated parameters."
    INDEX { atmTrafficDescrParamIndex }
    ::= { atmTrafficDescrParamTable 1 }

AtmTrafficDescrParamEntry ::= SEQUENCE {
    atmTrafficDescrParamIndex AtmTrafficDescrParamIndex,
    atmTrafficDescrType OBJECT IDENTIFIER,
    atmTrafficDescrParam1 Integer32,
    atmTrafficDescrParam2 Integer32,
    atmTrafficDescrParam3 Integer32,
    atmTrafficDescrParam4 Integer32,
    atmTrafficDescrParam5 Integer32,
    atmTrafficQoSClass INTEGER,
    atmTrafficDescrRowStatus RowStatus,
    atmServiceCategory AtmServiceCategory
    }

atmTrafficDescrParamIndex OBJECT-TYPE
    SYNTAX AtmTrafficDescrParamIndex
--    Rsyntax INTEGER(0..2147483647)
    ACCESS not-accessible
    STATUS mandatory
    DESCRIPTION
        "This object is used by the virtual link
         table (i.e., VPL or VCL table)
         to identify the row of this table.
         When creating a new row in the table
         the value of this index may be obtained
         by retrieving the value of
         atmTrafficDescrParamIndexNext."
    ::= { atmTrafficDescrParamEntry 1 }

atmTrafficDescrType OBJECT-TYPE
    SYNTAX OBJECT IDENTIFIER
    ACCESS read-write
    STATUS mandatory
    DESCRIPTION
        "The value of this object identifies the type
         of ATM traffic descriptor.
         The type may indicate no traffic descriptor or
         traffic descriptor with one or more parameters.
         These parameters are specified as a parameter
         vector, in the corresponding instances of the
         objects:
             atmTrafficDescrParam1
             atmTrafficDescrParam2
             atmTrafficDescrParam3
             atmTrafficDescrParam4
             atmTrafficDescrParam5."
    DEFVAL { atmNoTrafficDescriptor }
    ::= { atmTrafficDescrParamEntry 2 }

atmTrafficDescrParam1 OBJECT-TYPE
    SYNTAX Integer32
    ACCESS read-write
    STATUS mandatory
    DESCRIPTION
        "The first parameter of the ATM traffic descriptor
         used according to the value of
         atmTrafficDescrType."
    DEFVAL { 0 }
    ::= { atmTrafficDescrParamEntry 3 }

atmTrafficDescrParam2 OBJECT-TYPE
    SYNTAX Integer32
    ACCESS read-write
    STATUS mandatory
    DESCRIPTION
        "The second parameter of the ATM traffic descriptor
         used according to the value of
         atmTrafficDescrType."
    DEFVAL { 0 }
    ::= { atmTrafficDescrParamEntry 4 }

atmTrafficDescrParam3 OBJECT-TYPE
    SYNTAX Integer32
    ACCESS read-write
    STATUS mandatory
    DESCRIPTION
        "The third parameter of the ATM traffic descriptor
         used according to the value of atmTrafficDescrType."
    DEFVAL { 0 }
    ::= { atmTrafficDescrParamEntry 5 }

atmTrafficDescrParam4 OBJECT-TYPE
    SYNTAX Integer32
    ACCESS read-write
    STATUS mandatory
    DESCRIPTION
        "The fourth parameter of the ATM traffic descriptor
         used according to the value of
         atmTrafficDescrType."
    DEFVAL { 0 }
    ::= { atmTrafficDescrParamEntry 6 }

atmTrafficDescrParam5 OBJECT-TYPE
    SYNTAX Integer32
    ACCESS read-write
    STATUS mandatory
    DESCRIPTION
        "The fifth parameter of the ATM traffic descriptor
         used according to the value of
         atmTrafficDescrType."
    DEFVAL { 0 }
    ::= { atmTrafficDescrParamEntry 7 }

atmTrafficQoSClass OBJECT-TYPE
    SYNTAX INTEGER(0..255)
    ACCESS read-write
    STATUS deprecated
    DESCRIPTION
        "The value of this object identifies the QoS Class.
         Four Service classes have been
         specified in the ATM Forum UNI Specification:
         Service Class A: Constant bit rate video and
                          Circuit emulation
         Service Class B: Variable bit rate video/audio
         Service Class C: Connection-oriented data
         Service Class D: Connectionless data
         Four QoS classes numbered 1, 2, 3, and 4 have
         been specified with the aim to support service
         classes A, B, C, and D respectively.
         An unspecified QoS Class numbered `0' is used
         for best effort traffic."
    DEFVAL { 0 }
    ::= { atmTrafficDescrParamEntry 8 }

atmTrafficDescrRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create
         a new row or modify or delete an
         existing row in this table."
    DEFVAL { active }
    ::= { atmTrafficDescrParamEntry 9 }

atmServiceCategory OBJECT-TYPE
    SYNTAX AtmServiceCategory
--    Rsyntax INTEGER {
--        other(1),
--        cbr(2),
--        rtVbr(3),
--        nrtVbr(4),
--        abr(5),
--        ubr(6)
--        }
    ACCESS read-write
    STATUS mandatory
    DESCRIPTION
        " The ATM service category."
    DEFVAL { ubr }
    ::= { atmTrafficDescrParamEntry 10 }

atmVplTable OBJECT-TYPE
    SYNTAX SEQUENCE OF AtmVplEntry
    ACCESS not-accessible
    STATUS mandatory
    DESCRIPTION
        "The Virtual Path Link (VPL) table.  A
         bi-directional VPL is modeled as one entry
         in this table."
    ::= { atmMIBObjects 6 }

atmVplEntry OBJECT-TYPE
    SYNTAX AtmVplEntry
    ACCESS not-accessible
    STATUS mandatory
    DESCRIPTION
        "An entry in the VPL table.  This entry is
         used to model a bi-directional VPL.
         To create a VPL at an ATM interface,
         either of the following procedures are used:
        
         Negotiated VPL establishment
        
        (1) The management application creates
           a VPL entry in the atmVplTable
           by setting atmVplRowStatus to createAndWait(5).
           This may fail for the following reasons:
           - The selected VPI value is unavailable,
           - The selected VPI value is in use.
           Otherwise, the agent creates a row and
           reserves the VPI value on that port.
        
        (2) The manager selects an existing row(s) in the
           atmTrafficDescrParamTable,
           thereby, selecting a set of self-consistent
           ATM traffic parameters and the service category
           for receive and transmit directions of the VPL.
        
        (2a) If no suitable row(s) in the
           atmTrafficDescrParamTable exists,
           the manager must create a new row(s)
           in that table.
        
        (2b) The manager characterizes the VPL's traffic
           parameters through setting the
           atmVplReceiveTrafficDescrIndex and the
           atmVplTransmitTrafficDescrIndex values
           in the VPL table, which point to the rows
           containing desired ATM traffic parameter values
           in the atmTrafficDescrParamTable.  The agent
           will check the availability of resources and
           may refuse the request.
           If the transmit and receive service categories
           are inconsistent, the agent should refuse the
           request.
        
        (3) The manager activates the VPL by setting the
           the atmVplRowStatus to active(1).
           If this set is successful, the agent has
           reserved the resources to satisfy the requested
           traffic parameter values and the service category
           for that VPL.
        
        (4) If the VPL terminates a VPC in the ATM host
           or switch, the manager turns on the
           atmVplAdminStatus to up(1) to turn the VPL
           traffic flow on.  Otherwise, the
           atmVpCrossConnectTable  must be used
           to cross-connect the VPL to another VPL(s)
           in an ATM switch or network.
        
         One-Shot VPL Establishment
        
         A VPL may also be established in one step by a
         set-request with all necessary VPL parameter
         values and atmVplRowStatus set to createAndGo(4).
        
         In contrast to the negotiated VPL establishment
         which allows for detailed error checking
         (i.e., set errors are explicitly linked to
         particular resource acquisition failures),
         the one-shot VPL establishment
         performs the setup on one operation but
         does not have the advantage of step-wise
         error checking.
        
         VPL Retirement
        
         A VPL is released by setting atmVplRowStatus to
         destroy(6), and the agent may release all
         associated resources."
    INDEX { ifIndex, atmVplVpi }
    ::= { atmVplTable 1 }

AtmVplEntry ::= SEQUENCE {
    atmVplVpi AtmVpIdentifier,
    atmVplAdminStatus AtmVorXAdminStatus,
    atmVplOperStatus AtmVorXOperStatus,
    atmVplLastChange AtmVorXLastChange,
    atmVplReceiveTrafficDescrIndex AtmTrafficDescrParamIndex,
    atmVplTransmitTrafficDescrIndex AtmTrafficDescrParamIndex,
    atmVplCrossConnectIdentifier INTEGER,
    atmVplRowStatus RowStatus,
    atmVplCastType AtmConnCastType,
    atmVplConnKind AtmConnKind
    }

atmVplVpi OBJECT-TYPE
    SYNTAX AtmVpIdentifier
--    Rsyntax INTEGER(0..4095)
    ACCESS not-accessible
    STATUS mandatory
    DESCRIPTION
        "The VPI value of the VPL."
    ::= { atmVplEntry 1 }

atmVplAdminStatus OBJECT-TYPE
    SYNTAX AtmVorXAdminStatus
--    Rsyntax INTEGER {
--        up(1),
--        down(2)
--        }
    ACCESS read-write
    STATUS mandatory
    DESCRIPTION
        "This object is implemented only for a VPL
         which terminates a VPC (i.e., one which is
         NOT cross-connected to other VPLs).
         Its value specifies the desired
         administrative state of the VPL."
    DEFVAL { down }
    ::= { atmVplEntry 2 }

atmVplOperStatus OBJECT-TYPE
    SYNTAX AtmVorXOperStatus
--    Rsyntax INTEGER {
--        up(1),
--        down(2),
--        unknown(3)
--        }
    ACCESS read-only
    STATUS mandatory
    DESCRIPTION
        "The current operational status of the VPL."
    ::= { atmVplEntry 3 }

atmVplLastChange OBJECT-TYPE
    SYNTAX AtmVorXLastChange
--    Rsyntax TimeTicks
    ACCESS read-only
    STATUS mandatory
    DESCRIPTION
        "The value of sysUpTime at the time this
         VPL entered its current operational state."
    ::= { atmVplEntry 4 }

atmVplReceiveTrafficDescrIndex OBJECT-TYPE
    SYNTAX AtmTrafficDescrParamIndex
--    Rsyntax INTEGER(0..2147483647)
    ACCESS read-write
    STATUS mandatory
    DESCRIPTION
        "The value of this object identifies the row
         in the atmTrafficDescrParamTable which
         applies to the receive direction of the VPL."
    DEFVAL { 0 }
    ::= { atmVplEntry 5 }

atmVplTransmitTrafficDescrIndex OBJECT-TYPE
    SYNTAX AtmTrafficDescrParamIndex
--    Rsyntax INTEGER(0..2147483647)
    ACCESS read-write
    STATUS mandatory
    DESCRIPTION
        "The value of this object identifies the row
         in the atmTrafficDescrParamTable which
         applies to the transmit direction of the VPL."
    DEFVAL { 0 }
    ::= { atmVplEntry 6 }

atmVplCrossConnectIdentifier OBJECT-TYPE
    SYNTAX INTEGER(0..2147483647)
    ACCESS read-only
    STATUS mandatory
    DESCRIPTION
        "This object is implemented only for a VPL
         which is cross-connected to other VPLs
         that belong to the same VPC.  All such
         associated VPLs have the same value of this
         object, and all their cross-connections are
         identified by entries in the
         atmVpCrossConnectTable for which
         atmVpCrossConnectIndex has the same value.
         The value of this object is initialized by the
         agent after the associated entries in the
         atmVpCrossConnectTable have been created."
    ::= { atmVplEntry 7 }

atmVplRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create, delete
         or modify a row in this table.
         To create a new VCL, this object is
         initially set to 'createAndWait' or
         'createAndGo'.  This object should not be
         set to 'active' unless the following columnar
         objects have been set to their desired value
         in this row:
         atmVplReceiveTrafficDescrIndex and
         atmVplTransmitTrafficDescrIndex."
    DEFVAL { active }
    ::= { atmVplEntry 8 }

atmVplCastType OBJECT-TYPE
    SYNTAX AtmConnCastType
--    Rsyntax INTEGER {
--        p2p(1),
--        p2mpRoot(2),
--        p2mpLeaf(3)
--        }
    ACCESS read-write
    STATUS mandatory
    DESCRIPTION
        "The connection topology type."
    DEFVAL { p2p }
    ::= { atmVplEntry 9 }

atmVplConnKind OBJECT-TYPE
    SYNTAX AtmConnKind
--    Rsyntax INTEGER {
--        pvc(1),
--        svcIncoming(2),
--        svcOutgoing(3),
--        spvcInitiator(4),
--        spvcTarget(5)
--        }
    ACCESS read-write
    STATUS mandatory
    DESCRIPTION
        "The use of call control."
    DEFVAL { pvc }
    ::= { atmVplEntry 10 }

atmVclTable OBJECT-TYPE
    SYNTAX SEQUENCE OF AtmVclEntry
    ACCESS not-accessible
    STATUS mandatory
    DESCRIPTION
        "The Virtual Channel Link (VCL) table.  A
         bi-directional VCL is modeled as one entry
         in this table."
    ::= { atmMIBObjects 7 }

atmVclEntry OBJECT-TYPE
    SYNTAX AtmVclEntry
    ACCESS not-accessible
    STATUS mandatory
    DESCRIPTION
        "An entry in the VCL table. This entry is
         used to model a bi-directional VCL.
         To create a VCL at an ATM interface,
         either of the following procedures are used:
        
         Negotiated VCL establishment
        
        (1) The management application creates
           a VCL entry in the atmVclTable
           by setting atmVclRowStatus to createAndWait(5).
           This may fail for the following reasons:
           - The selected VPI/VCI values are unavailable,
           - The selected VPI/VCI values are in use.
           Otherwise, the agent creates a row and
           reserves the VPI/VCI values on that port.
        
        (2) The manager selects an existing row(s) in the
           atmTrafficDescrParamTable,
           thereby, selecting a set of self-consistent
           ATM traffic parameters and the service category
           for receive and transmit directions of the VCL.
        
        (2a) If no suitable row(s) in the
           atmTrafficDescrParamTable exists,
           the manager must create a new row(s)
           in that table.
        
        (2b) The manager characterizes the VCL's traffic
           parameters through setting the
           atmVclReceiveTrafficDescrIndex and the
           atmVclTransmitTrafficDescrIndex values
           in the VCL table, which point to the rows
           containing desired ATM traffic parameter values
           in the atmTrafficDescrParamTable.  The agent
           will check the availability of resources and
           may refuse the request.
           If the transmit and receive service categories
           are inconsistent, the agent should refuse the
           request.
        
        (3) The manager activates the VCL by setting the
           the atmVclRowStatus to active(1) (for
           requirements on this activation see the
           description of atmVclRowStatus).
           If this set is successful, the agent has
           reserved the resources to satisfy the requested
           traffic parameter values and the service category
           for that VCL.
        (4) If the VCL terminates a VCC in the ATM host
           or switch, the manager turns on the
           atmVclAdminStatus to up(1) to turn the VCL
           traffic flow on.  Otherwise, the
           atmVcCrossConnectTable  must be used
           to cross-connect the VCL to another VCL(s)
           in an ATM switch or network.
        
        One-Shot VCL Establishment
        
        A VCL may also be established in one step by a
        set-request with all necessary VCL parameter
        values and atmVclRowStatus set to createAndGo(4).
        
        In contrast to the negotiated VCL establishment
        which allows for detailed error checking
        (i.e., set errors are explicitly linked to
        particular resource acquisition failures),
        the one-shot VCL establishment
        performs the setup on one operation but
        does not have the advantage of step-wise
        error checking.
        
        VCL Retirement
        
        A VCL is released by setting atmVclRowStatus to
        destroy(6), and the agent may release all
        associated resources."
    INDEX { ifIndex, atmVclVpi, atmVclVci }
    ::= { atmVclTable 1 }

AtmVclEntry ::= SEQUENCE {
    atmVclVpi AtmVpIdentifier,
    atmVclVci AtmVcIdentifier,
    atmVclAdminStatus AtmVorXAdminStatus,
    atmVclOperStatus AtmVorXOperStatus,
    atmVclLastChange AtmVorXLastChange,
    atmVclReceiveTrafficDescrIndex AtmTrafficDescrParamIndex,
    atmVclTransmitTrafficDescrIndex AtmTrafficDescrParamIndex,
    atmVccAalType INTEGER,
    atmVccAal5CpcsTransmitSduSize INTEGER,
    atmVccAal5CpcsReceiveSduSize INTEGER,
    atmVccAal5EncapsType INTEGER,
    atmVclCrossConnectIdentifier INTEGER,
    atmVclRowStatus RowStatus,
    atmVclCastType AtmConnCastType,
    atmVclConnKind AtmConnKind
    }

atmVclVpi OBJECT-TYPE
    SYNTAX AtmVpIdentifier
--    Rsyntax INTEGER(0..4095)
    ACCESS not-accessible
    STATUS mandatory
    DESCRIPTION
        "The VPI value of the VCL."
    ::= { atmVclEntry 1 }

atmVclVci OBJECT-TYPE
    SYNTAX AtmVcIdentifier
--    Rsyntax INTEGER(0..65535)
    ACCESS not-accessible
    STATUS mandatory
    DESCRIPTION
        "The VCI value of the VCL."
    ::= { atmVclEntry 2 }

atmVclAdminStatus OBJECT-TYPE
    SYNTAX AtmVorXAdminStatus
--    Rsyntax INTEGER {
--        up(1),
--        down(2)
--        }
    ACCESS read-write
    STATUS mandatory
    DESCRIPTION
        "This object is implemented only for a VCL which
         terminates a VCC (i.e., one which is NOT
         cross-connected to other VCLs). Its value
         specifies the desired administrative state of
         the VCL."
    DEFVAL { down }
    ::= { atmVclEntry 3 }

atmVclOperStatus OBJECT-TYPE
    SYNTAX AtmVorXOperStatus
--    Rsyntax INTEGER {
--        up(1),
--        down(2),
--        unknown(3)
--        }
    ACCESS read-only
    STATUS mandatory
    DESCRIPTION
        "The current operational status of the VCL."
    ::= { atmVclEntry 4 }

atmVclLastChange OBJECT-TYPE
    SYNTAX AtmVorXLastChange
--    Rsyntax TimeTicks
    ACCESS read-only
    STATUS mandatory
    DESCRIPTION
        "The value of sysUpTime at the time this VCL
         entered its current operational state."
    ::= { atmVclEntry 5 }

atmVclReceiveTrafficDescrIndex OBJECT-TYPE
    SYNTAX AtmTrafficDescrParamIndex
--    Rsyntax INTEGER(0..2147483647)
    ACCESS read-write
    STATUS mandatory
    DESCRIPTION
        "The value of this object identifies the row
         in the ATM Traffic Descriptor Table which
         applies to the receive direction of this VCL."
    DEFVAL { 0 }
    ::= { atmVclEntry 6 }

atmVclTransmitTrafficDescrIndex OBJECT-TYPE
    SYNTAX AtmTrafficDescrParamIndex
--    Rsyntax INTEGER(0..2147483647)
    ACCESS read-write
    STATUS mandatory
    DESCRIPTION
        "The value of this object identifies the row
         of the ATM Traffic Descriptor Table which applies
         to the transmit direction of this VCL."
    DEFVAL { 0 }
    ::= { atmVclEntry 7 }

atmVccAalType OBJECT-TYPE
    SYNTAX INTEGER {
        aal1(1),
        aal34(2),
        aal5(3),
        other(4),
        unknown(5)
        }
    ACCESS read-write
    STATUS mandatory
    DESCRIPTION
        "An instance of this object only exists when the
         local VCL end-point is also the VCC end-point,
         and AAL is in use.
         The type of AAL used on this VCC.
         The AAL type includes AAL1, AAL3/4,
         and AAL5. The other(4) may be user-defined
         AAL type.  The unknown type indicates that
         the AAL type cannot be determined."
    DEFVAL { aal5 }
    ::= { atmVclEntry 8 }

atmVccAal5CpcsTransmitSduSize OBJECT-TYPE
    SYNTAX INTEGER(1..65535)
    ACCESS read-write
    STATUS mandatory
    DESCRIPTION
        "An instance of this object only exists when the
         local VCL end-point is also the VCC end-point,
         and AAL5 is in use.
         The maximum AAL5 CPCS SDU size in octets that is
         supported on the transmit direction of this VCC."
    DEFVAL { 9188 }
    ::= { atmVclEntry 9 }

atmVccAal5CpcsReceiveSduSize OBJECT-TYPE
    SYNTAX INTEGER(1..65535)
    ACCESS read-write
    STATUS mandatory
    DESCRIPTION
        "An instance of this object only exists when the
         local VCL end-point is also the VCC end-point,
         and AAL5 is in use.
         The maximum AAL5 CPCS SDU size in octets that is
         supported on the receive direction of this VCC."
    DEFVAL { 9188 }
    ::= { atmVclEntry 10 }

atmVccAal5EncapsType OBJECT-TYPE
    SYNTAX INTEGER {
        vcMultiplexRoutedProtocol(1),
        vcMultiplexBridgedProtocol8023(2),
        vcMultiplexBridgedProtocol8025(3),
        vcMultiplexBridgedProtocol8026(4),
        vcMultiplexLANemulation8023(5),
        vcMultiplexLANemulation8025(6),
        llcEncapsulation(7),
        multiprotocolFrameRelaySscs(8),
        other(9),
        unknown(10)
        }
    ACCESS read-write
    STATUS mandatory
    DESCRIPTION
        "An instance of this object only exists when the
         local VCL end-point is also the VCC end-point,
         and AAL5 is in use.
         The type of data encapsulation used over
         the AAL5 SSCS layer. The definitions reference
         RFC 1483 Multiprotocol Encapsulation
         over ATM AAL5 and to the ATM Forum
         LAN Emulation specification."
    DEFVAL { llcEncapsulation }
    ::= { atmVclEntry 11 }

atmVclCrossConnectIdentifier OBJECT-TYPE
    SYNTAX INTEGER(0..2147483647)
    ACCESS read-only
    STATUS mandatory
    DESCRIPTION
        "This object is implemented only for a VCL
         which is cross-connected to other VCLs
         that belong to the same VCC.  All such
         associated VCLs have the same value of this
         object, and all their cross-connections are
         identified by entries in the
         atmVcCrossConnectTable for which
         atmVcCrossConnectIndex has the same value.
         The value of this object is initialized by the
         agent after the associated entries in the
         atmVcCrossConnectTable have been created."
    ::= { atmVclEntry 12 }

atmVclRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create, delete or
         modify a row in this table.  To create
         a new VCL, this object is initially set
         to 'createAndWait' or 'createAndGo'.
         This object should not be
         set to 'active' unless the following columnar
         objects have been set to their desired value
         in this row:
         atmVclReceiveTrafficDescrIndex,
         atmVclTransmitTrafficDescrIndex.
         In addition, if the local VCL end-point
         is also the VCC end-point:
         atmVccAalType.
         In addition, for AAL5 connections only:
         atmVccAal5CpcsTransmitSduSize,
         atmVccAal5CpcsReceiveSduSize, and
         atmVccAal5EncapsType. (The existence
         of these objects imply the AAL connection type.)"
    DEFVAL { active }
    ::= { atmVclEntry 13 }

atmVclCastType OBJECT-TYPE
    SYNTAX AtmConnCastType
--    Rsyntax INTEGER {
--        p2p(1),
--        p2mpRoot(2),
--        p2mpLeaf(3)
--        }
    ACCESS read-write
    STATUS mandatory
    DESCRIPTION
        "The connection topology type."
    DEFVAL { p2p }
    ::= { atmVclEntry 14 }

atmVclConnKind OBJECT-TYPE
    SYNTAX AtmConnKind
--    Rsyntax INTEGER {
--        pvc(1),
--        svcIncoming(2),
--        svcOutgoing(3),
--        spvcInitiator(4),
--        spvcTarget(5)
--        }
    ACCESS read-write
    STATUS mandatory
    DESCRIPTION
        "The use of call control."
    DEFVAL { pvc }
    ::= { atmVclEntry 15 }

atmVpCrossConnectIndexNext OBJECT-TYPE
    SYNTAX INTEGER(0..2147483647)
    ACCESS read-only
    STATUS mandatory
    DESCRIPTION
        "This object contains an appropriate value to
         be used for atmVpCrossConnectIndex when creating
         entries in the atmVpCrossConnectTable.  The value
         0 indicates that no unassigned entries are
         available. To obtain the atmVpCrossConnectIndex
         value for a new entry, the manager issues a
         management protocol retrieval operation to obtain
         the current value of this object.  After each
         retrieval, the agent should modify the value to
         the next unassigned index."
    ::= { atmMIBObjects 8 }

atmVpCrossConnectTable OBJECT-TYPE
    SYNTAX SEQUENCE OF AtmVpCrossConnectEntry
    ACCESS not-accessible
    STATUS mandatory
    DESCRIPTION
        "The ATM VP Cross Connect table.  A bi-
         directional VP cross-connect which
         cross-connects two VPLs is modeled
         as one entry in this table."
    ::= { atmMIBObjects 9 }

atmVpCrossConnectEntry OBJECT-TYPE
    SYNTAX AtmVpCrossConnectEntry
    ACCESS not-accessible
    STATUS mandatory
    DESCRIPTION
        "An entry in the ATM VP Cross Connect table.
         This entry is used to model a bi-directional
         ATM VP cross-connect which cross-connects
         two VPLs.
        
         Step-wise Procedures to set up a VP Cross-connect
        
         Once the entries in the atmVplTable are created,
         the following procedures are used
         to cross-connect the VPLs together.
        
        (1) The manager obtains a unique
            atmVpCrossConnectIndex by reading the
            atmVpCrossConnectIndexNext object.
        
        (2) Next, the manager creates a set of one
            or more rows in the ATM VP Cross Connect
            Table, one for each cross-connection between
            two VPLs.  Each row is indexed by the ATM
            interface port numbers and VPI values of the
            two ends of that cross-connection.
            This set of rows specifies the topology of the
            VPC cross-connect and is identified by a single
            value of atmVpCrossConnectIndex.
        
         Negotiated VP Cross-Connect Establishment
        
        (2a) The manager creates a row in this table by
            setting atmVpCrossConnectRowStatus to
            createAndWait(5).  The agent checks the
            requested topology and the mutual sanity of
            the ATM traffic parameters and
            service categories, i.e., the row creation
            fails if:
            - the requested topology is incompatible with
              associated values of atmVplCastType,
            - the requested topology is not supported
              by the agent,
            - the traffic/service category parameter values
              associated with the requested row are
              incompatible with those of already existing
              rows for this VP cross-connect.
            [For example, for setting up
            a point-to-point VP cross-connect, the
            ATM traffic parameters in the receive direction
            of a VPL at the low end of the cross-connect
            must equal to the traffic parameters in the
            transmit direction of the other VPL at the
            high end of the cross-connect,
            otherwise, the row creation fails.]
            The agent also checks for internal errors
            in building the cross-connect.
        
            The atmVpCrossConnectIndex values in the
            corresponding atmVplTable rows are filled
            in by the agent at this point.
        
        (2b) The manager promotes the row in the
            atmVpCrossConnectTable by setting
            atmVpCrossConnectRowStatus to active(1).  If
            this set is successful, the agent has reserved
            the resources specified by the ATM traffic
            parameter and Service category values
            for each direction of the VP cross-connect
            in an ATM switch or network.
        
        (3) The manager sets the
            atmVpCrossConnectAdminStatus to up(1) in all
            rows of this VP cross-connect to turn the
            traffic flow on.
        
        
         One-Shot VP Cross-Connect Establishment
        
         A VP cross-connect may also be established in
         one step by a set-request with all necessary
         parameter values and atmVpCrossConnectRowStatus
         set to createAndGo(4).
        
         In contrast to the negotiated VP cross-connect
         establishment which allows for detailed error
         checking (i.e., set errors are explicitly linked
         to particular resource acquisition failures),
         the one-shot VP cross-connect establishment
         performs the setup on one operation but does not
         have the advantage of step-wise error checking.
        
         VP Cross-Connect Retirement
        
         A VP cross-connect identified by a particular
         value of atmVpCrossConnectIndex is released by:
        
        (1) Setting atmVpCrossConnectRowStatus of all
            rows identified by this value of
            atmVpCrossConnectIndex to destroy(6).
            The agent may release all
            associated resources, and the
            atmVpCrossConnectIndex values in the
            corresponding atmVplTable row are removed.
            Note that a situation when only a subset of
            the associated rows are deleted corresponds
            to a VP topology change.
        
        (2) After deletion of the appropriate
            atmVpCrossConnectEntries, the manager may
            set atmVplRowStatus to destroy(6) the
            associated VPLs.  The agent releases
            the resources and removes the associated
            rows in the atmVplTable.
        
         VP Cross-connect Reconfiguration
        
         At the discretion of the agent, a VP
         cross-connect may be reconfigured by
         adding and/or deleting leafs to/from
         the VP topology as per the VP cross-connect
         establishment/retirement procedures.
         Reconfiguration of traffic/service category parameter
         values requires release of the VP cross-connect
         before those parameter values may by changed
         for individual VPLs."
    INDEX { atmVpCrossConnectIndex, atmVpCrossConnectLowIfIndex, atmVpCrossConnectLowVpi, atmVpCrossConnectHighIfIndex, atmVpCrossConnectHighVpi }
    ::= { atmVpCrossConnectTable 1 }

AtmVpCrossConnectEntry ::= SEQUENCE {
    atmVpCrossConnectIndex INTEGER,
    atmVpCrossConnectLowIfIndex InterfaceIndex,
    atmVpCrossConnectLowVpi AtmVpIdentifier,
    atmVpCrossConnectHighIfIndex InterfaceIndex,
    atmVpCrossConnectHighVpi AtmVpIdentifier,
    atmVpCrossConnectAdminStatus AtmVorXAdminStatus,
    atmVpCrossConnectL2HOperStatus AtmVorXOperStatus,
    atmVpCrossConnectH2LOperStatus AtmVorXOperStatus,
    atmVpCrossConnectL2HLastChange AtmVorXLastChange,
    atmVpCrossConnectH2LLastChange AtmVorXLastChange,
    atmVpCrossConnectRowStatus RowStatus
    }

atmVpCrossConnectIndex OBJECT-TYPE
    SYNTAX INTEGER(1..2147483647)
    ACCESS not-accessible
    STATUS mandatory
    DESCRIPTION
        "A unique value to identify this VP cross-connect."
    ::= { atmVpCrossConnectEntry 1 }

atmVpCrossConnectLowIfIndex OBJECT-TYPE
    SYNTAX InterfaceIndex
--    Rsyntax Integer32
    ACCESS not-accessible
    STATUS mandatory
    DESCRIPTION
        "The ifIndex value of the ATM interface for
         this VP cross-connect. The term low implies
         that this ATM interface has the numerically lower
         ifIndex value than the other ATM interface
         identified in the same atmVpCrossConnectEntry."
    ::= { atmVpCrossConnectEntry 2 }

atmVpCrossConnectLowVpi OBJECT-TYPE
    SYNTAX AtmVpIdentifier
--    Rsyntax INTEGER(0..4095)
    ACCESS not-accessible
    STATUS mandatory
    DESCRIPTION
        "The VPI value at the ATM interface
         associated with the VP cross-connect that is
         identified by atmVpCrossConnectLowIfIndex."
    ::= { atmVpCrossConnectEntry 3 }

atmVpCrossConnectHighIfIndex OBJECT-TYPE
    SYNTAX InterfaceIndex
--    Rsyntax Integer32
    ACCESS not-accessible
    STATUS mandatory
    DESCRIPTION
        "The ifIndex value of the ATM interface for
         this VP cross-connect. The term high implies that
         this ATM interface has the numerically higher
         ifIndex value than the  other ATM interface
         identified in the same atmVpCrossConnectEntry."
    ::= { atmVpCrossConnectEntry 4 }

atmVpCrossConnectHighVpi OBJECT-TYPE
    SYNTAX AtmVpIdentifier
--    Rsyntax INTEGER(0..4095)
    ACCESS not-accessible
    STATUS mandatory
    DESCRIPTION
        "The VPI value at the ATM interface
         associated with the VP cross-connect that is
         identified by atmVpCrossConnectHighIfIndex."
    ::= { atmVpCrossConnectEntry 5 }

atmVpCrossConnectAdminStatus OBJECT-TYPE
    SYNTAX AtmVorXAdminStatus
--    Rsyntax INTEGER {
--        up(1),
--        down(2)
--        }
    ACCESS read-write
    STATUS mandatory
    DESCRIPTION
        "The desired administrative status of this
         bi-directional VP cross-connect."
    DEFVAL { down }
    ::= { atmVpCrossConnectEntry 6 }

atmVpCrossConnectL2HOperStatus OBJECT-TYPE
    SYNTAX AtmVorXOperStatus
--    Rsyntax INTEGER {
--        up(1),
--        down(2),
--        unknown(3)
--        }
    ACCESS read-only
    STATUS mandatory
    DESCRIPTION
        "The operational status of the VP cross-connect
         in one direction; (i.e., from the low to
         high direction)."
    ::= { atmVpCrossConnectEntry 7 }

atmVpCrossConnectH2LOperStatus OBJECT-TYPE
    SYNTAX AtmVorXOperStatus
--    Rsyntax INTEGER {
--        up(1),
--        down(2),
--        unknown(3)
--        }
    ACCESS read-only
    STATUS mandatory
    DESCRIPTION
        "The operational status of the VP cross-connect
         in one direction; (i.e., from the high to
         low direction)."
    ::= { atmVpCrossConnectEntry 8 }

atmVpCrossConnectL2HLastChange OBJECT-TYPE
    SYNTAX AtmVorXLastChange
--    Rsyntax TimeTicks
    ACCESS read-only
    STATUS mandatory
    DESCRIPTION
        "The value of sysUpTime at the time this
         VP cross-connect entered its current operational
         state in the low to high direction."
    ::= { atmVpCrossConnectEntry 9 }

atmVpCrossConnectH2LLastChange OBJECT-TYPE
    SYNTAX AtmVorXLastChange
--    Rsyntax TimeTicks
    ACCESS read-only
    STATUS mandatory
    DESCRIPTION
        "The value of sysUpTime at the time this
        VP cross-connect entered its current operational
        in the high to low direction."
    ::= { atmVpCrossConnectEntry 10 }

atmVpCrossConnectRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this entry in the
         atmVpCrossConnectTable.  This object is used to
         create a cross-connect for cross-connecting
         VPLs which are created using the atmVplTable
         or to change or delete an existing cross-connect.
         This object must be initially set
         to `createAndWait' or 'createAndGo'.
         To turn on a VP cross-connect,
         the atmVpCrossConnectAdminStatus
         is set to `up'."
    DEFVAL { active }
    ::= { atmVpCrossConnectEntry 11 }

atmVcCrossConnectIndexNext OBJECT-TYPE
    SYNTAX INTEGER(0..2147483647)
    ACCESS read-only
    STATUS mandatory
    DESCRIPTION
        "This object contains an appropriate value to
         be used for atmVcCrossConnectIndex when creating
         entries in the atmVcCrossConnectTable.  The value
         0 indicates that no unassigned entries are
         available. To obtain the atmVpCrossConnectIndex
         value for a new entry, the manager issues a
         management protocol retrieval operation to obtain
         the current value of this object.  After each
         retrieval, the agent should modify the value to
         the next unassigned index."
    ::= { atmMIBObjects 10 }

atmVcCrossConnectTable OBJECT-TYPE
    SYNTAX SEQUENCE OF AtmVcCrossConnectEntry
    ACCESS not-accessible
    STATUS mandatory
    DESCRIPTION
        "The ATM VC Cross Connect table.  A bi-
         directional VC cross-connect which
         cross-connects two end points (i.e., VCLs)
         is modeled as one entry in this table."
    ::= { atmMIBObjects 11 }

atmVcCrossConnectEntry OBJECT-TYPE
    SYNTAX AtmVcCrossConnectEntry
    ACCESS not-accessible
    STATUS mandatory
    DESCRIPTION
        "An entry in the ATM VC Cross Connect table.
         This entry is used to model a bi-directional ATM
         VC cross-connect cross-connecting two end points.
        
         Step-wise Procedures to set up a VC Cross-connect
        
         Once the entries in the atmVclTable are created,
         the following procedures are used
         to cross-connect the VCLs together to
         form a VCC segment.
        
        (1) The manager obtains a unique
            atmVcCrossConnectIndex by reading the
            atmVcCrossConnectIndexNext object.
        
        (2) Next, the manager creates a set of one
            or more rows in the ATM VC Cross Connect
            Table, one for each cross-connection between
            two VCLs.  Each row is indexed by the ATM
            interface port numbers and VPI/VCI values of
            the two ends of that cross-connection.
            This set of rows specifies the topology of the
            VCC cross-connect and is identified by a single
            value of atmVcCrossConnectIndex.
        
         Negotiated VC Cross-Connect Establishment
        
        (2a) The manager creates a row in this table by
            setting atmVcCrossConnectRowStatus to
            createAndWait(5).  The agent checks the
            requested topology and the mutual sanity of
            the ATM traffic parameters and
            service categories, i.e., the row creation
            fails if:
            - the requested topology is incompatible with
              associated values of atmVclCastType,
            - the requested topology is not supported
              by the agent,
            - the traffic/service category parameter values
              associated with the requested row are
              incompatible with those of already existing
              rows for this VC cross-connect.
            [For example, for setting up
            a point-to-point VC cross-connect, the
            ATM traffic parameters in the receive direction
            of a VCL at the low end of the cross-connect
            must equal to the traffic parameters in the
            transmit direction of the other VCL at the
            high end of the cross-connect,
            otherwise, the row creation fails.]
            The agent also checks for internal errors
            in building the cross-connect.
        
            The atmVcCrossConnectIndex values in the
            corresponding atmVclTable rows are filled
            in by the agent at this point.
        
        (2b) The manager promotes the row in the
            atmVcCrossConnectTable by setting
            atmVcCrossConnectRowStatus to active(1).  If
            this set is successful, the agent has reserved
            the resources specified by the ATM traffic
            parameter and Service category values
            for each direction of the VC cross-connect
            in an ATM switch or network.
        
        (3) The manager sets the
            atmVcCrossConnectAdminStatus to up(1)
            in all rows of this VC cross-connect to
            turn the traffic flow on.
        
        
         One-Shot VC Cross-Connect Establishment
        
         A VC cross-connect may also be established in
         one step by a set-request with all necessary
         parameter values and atmVcCrossConnectRowStatus
         set to createAndGo(4).
        
         In contrast to the negotiated VC cross-connect
         establishment which allows for detailed error
         checking i.e., set errors are explicitly linked to
         particular resource acquisition failures), the
         one-shot VC cross-connect establishment
         performs the setup on one operation but does
         not have the advantage of step-wise error
         checking.
        
         VC Cross-Connect Retirement
        
         A VC cross-connect identified by a particular
         value of atmVcCrossConnectIndex is released by:
        
        (1) Setting atmVcCrossConnectRowStatus of all rows
            identified by this value of
            atmVcCrossConnectIndex to destroy(6).
            The agent may release all
            associated resources, and the
            atmVcCrossConnectIndex values in the
            corresponding atmVclTable row are removed.
            Note that a situation when only a subset of
            the associated rows are deleted corresponds
            to a VC topology change.
        
        (2) After deletion of the appropriate
            atmVcCrossConnectEntries, the manager may
            set atmVclRowStatus to destroy(6) the
            associated VCLs.  The agent releases
            the resources and removes the associated
            rows in the atmVclTable.
        
         VC Cross-Connect Reconfiguration
        
         At the discretion of the agent, a VC
         cross-connect may be reconfigured by
         adding and/or deleting leafs to/from
         the VC topology as per the VC cross-connect
         establishment/retirement procedures.
         Reconfiguration of traffic/service category parameter
         values requires release of the VC cross-connect
         before those parameter values may by changed
         for individual VCLs."
    INDEX { atmVcCrossConnectIndex, atmVcCrossConnectLowIfIndex, atmVcCrossConnectLowVpi, atmVcCrossConnectLowVci, atmVcCrossConnectHighIfIndex, atmVcCrossConnectHighVpi, atmVcCrossConnectHighVci }
    ::= { atmVcCrossConnectTable 1 }

AtmVcCrossConnectEntry ::= SEQUENCE {
    atmVcCrossConnectIndex INTEGER,
    atmVcCrossConnectLowIfIndex InterfaceIndex,
    atmVcCrossConnectLowVpi AtmVpIdentifier,
    atmVcCrossConnectLowVci AtmVcIdentifier,
    atmVcCrossConnectHighIfIndex InterfaceIndex,
    atmVcCrossConnectHighVpi AtmVpIdentifier,
    atmVcCrossConnectHighVci AtmVcIdentifier,
    atmVcCrossConnectAdminStatus AtmVorXAdminStatus,
    atmVcCrossConnectL2HOperStatus AtmVorXOperStatus,
    atmVcCrossConnectH2LOperStatus AtmVorXOperStatus,
    atmVcCrossConnectL2HLastChange AtmVorXLastChange,
    atmVcCrossConnectH2LLastChange AtmVorXLastChange,
    atmVcCrossConnectRowStatus RowStatus
    }

atmVcCrossConnectIndex OBJECT-TYPE
    SYNTAX INTEGER(1..2147483647)
    ACCESS not-accessible
    STATUS mandatory
    DESCRIPTION
        "A unique value to identify this VC cross-connect."
    ::= { atmVcCrossConnectEntry 1 }

atmVcCrossConnectLowIfIndex OBJECT-TYPE
    SYNTAX InterfaceIndex
--    Rsyntax Integer32
    ACCESS not-accessible
    STATUS mandatory
    DESCRIPTION
        "The ifIndex value of the ATM interface for this
         VC cross-connect. The term low implies
         that this ATM interface has the numerically lower
         ifIndex value than the other ATM interface
         identified in the same atmVcCrossConnectEntry."
    ::= { atmVcCrossConnectEntry 2 }

atmVcCrossConnectLowVpi OBJECT-TYPE
    SYNTAX AtmVpIdentifier
--    Rsyntax INTEGER(0..4095)
    ACCESS not-accessible
    STATUS mandatory
    DESCRIPTION
        "The VPI value at the ATM interface
         associated with the VC cross-connect that is
         identified by atmVcCrossConnectLowIfIndex."
    ::= { atmVcCrossConnectEntry 3 }

atmVcCrossConnectLowVci OBJECT-TYPE
    SYNTAX AtmVcIdentifier
--    Rsyntax INTEGER(0..65535)
    ACCESS not-accessible
    STATUS mandatory
    DESCRIPTION
        "The VCI value at the ATM interface
         associated with this VC cross-connect that is
         identified by atmVcCrossConnectLowIfIndex."
    ::= { atmVcCrossConnectEntry 4 }

atmVcCrossConnectHighIfIndex OBJECT-TYPE
    SYNTAX InterfaceIndex
--    Rsyntax Integer32
    ACCESS not-accessible
    STATUS mandatory
    DESCRIPTION
        "The ifIndex value for the ATM interface for
         this VC cross-connect. The term high implies
         that this ATM interface has the numerically higher
         ifIndex value than the other ATM interface
         identified in the same atmVcCrossConnectEntry."
    ::= { atmVcCrossConnectEntry 5 }

atmVcCrossConnectHighVpi OBJECT-TYPE
    SYNTAX AtmVpIdentifier
--    Rsyntax INTEGER(0..4095)
    ACCESS not-accessible
    STATUS mandatory
    DESCRIPTION
        "The VPI value at the ATM interface
         associated with the VC cross-connect that is
         identified by atmVcCrossConnectHighIfIndex."
    ::= { atmVcCrossConnectEntry 6 }

atmVcCrossConnectHighVci OBJECT-TYPE
    SYNTAX AtmVcIdentifier
--    Rsyntax INTEGER(0..65535)
    ACCESS not-accessible
    STATUS mandatory
    DESCRIPTION
        "The VCI value at the ATM interface
         associated with the VC cross-connect that is
         identified by atmVcCrossConnectHighIfIndex."
    ::= { atmVcCrossConnectEntry 7 }

atmVcCrossConnectAdminStatus OBJECT-TYPE
    SYNTAX AtmVorXAdminStatus
--    Rsyntax INTEGER {
--        up(1),
--        down(2)
--        }
    ACCESS read-write
    STATUS mandatory
    DESCRIPTION
        "The desired administrative status of this
         bi-directional VC cross-connect."
    DEFVAL { down }
    ::= { atmVcCrossConnectEntry 8 }

atmVcCrossConnectL2HOperStatus OBJECT-TYPE
    SYNTAX AtmVorXOperStatus
--    Rsyntax INTEGER {
--        up(1),
--        down(2),
--        unknown(3)
--        }
    ACCESS read-only
    STATUS mandatory
    DESCRIPTION
        "The current operational status of the
         VC cross-connect in one direction; (i.e.,
         from the low to high direction)."
    ::= { atmVcCrossConnectEntry 9 }

atmVcCrossConnectH2LOperStatus OBJECT-TYPE
    SYNTAX AtmVorXOperStatus
--    Rsyntax INTEGER {
--        up(1),
--        down(2),
--        unknown(3)
--        }
    ACCESS read-only
    STATUS mandatory
    DESCRIPTION
        "The current operational status of the
         VC cross-connect in one direction; (i.e.,
         from the high to low direction)."
    ::= { atmVcCrossConnectEntry 10 }

atmVcCrossConnectL2HLastChange OBJECT-TYPE
    SYNTAX AtmVorXLastChange
--    Rsyntax TimeTicks
    ACCESS read-only
    STATUS mandatory
    DESCRIPTION
        "The value of sysUpTime at the time this
         VC cross-connect entered its current
         operational state in low to high direction."
    ::= { atmVcCrossConnectEntry 11 }

atmVcCrossConnectH2LLastChange OBJECT-TYPE
    SYNTAX AtmVorXLastChange
--    Rsyntax TimeTicks
    ACCESS read-only
    STATUS mandatory
    DESCRIPTION
        "The value of sysUpTime at the time this
         VC cross-connect entered its current
         operational state in high to low direction."
    ::= { atmVcCrossConnectEntry 12 }

atmVcCrossConnectRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this entry in the
         atmVcCrossConnectTable.  This object is used to
         create a new cross-connect for cross-connecting
         VCLs which are created using the atmVclTable
         or to change or delete existing cross-connect.
         This object must be initially set to
         `createAndWait' or 'createAndGo'.
         To turn on a VC cross-connect,
         the atmVcCrossConnectAdminStatus
         is set to `up'."
    DEFVAL { active }
    ::= { atmVcCrossConnectEntry 13 }

aal5VccTable OBJECT-TYPE
    SYNTAX SEQUENCE OF Aal5VccEntry
    ACCESS not-accessible
    STATUS mandatory
    DESCRIPTION
        "This table contains AAL5 VCC performance
         parameters."
    ::= { atmMIBObjects 12 }

aal5VccEntry OBJECT-TYPE
    SYNTAX Aal5VccEntry
    ACCESS not-accessible
    STATUS mandatory
    DESCRIPTION
        "This list contains the AAL5 VCC
         performance parameters."
    INDEX { ifIndex, aal5VccVpi, aal5VccVci }
    ::= { aal5VccTable 1 }

Aal5VccEntry ::= SEQUENCE {
    aal5VccVpi AtmVpIdentifier,
    aal5VccVci AtmVcIdentifier,
    aal5VccCrcErrors Counter32,
    aal5VccSarTimeOuts Counter32,
    aal5VccOverSizedSDUs Counter32
    }

aal5VccVpi OBJECT-TYPE
    SYNTAX AtmVpIdentifier
--    Rsyntax INTEGER(0..4095)
    ACCESS not-accessible
    STATUS mandatory
    DESCRIPTION
        "The VPI value of the AAL5 VCC at the
         interface identified by the ifIndex."
    ::= { aal5VccEntry 1 }

aal5VccVci OBJECT-TYPE
    SYNTAX AtmVcIdentifier
--    Rsyntax INTEGER(0..65535)
    ACCESS not-accessible
    STATUS mandatory
    DESCRIPTION
        "The VCI value of the AAL5 VCC at the
         interface identified by the ifIndex."
    ::= { aal5VccEntry 2 }

aal5VccCrcErrors OBJECT-TYPE
    SYNTAX Counter32
    ACCESS read-only
    STATUS mandatory
    DESCRIPTION
        "The number of AAL5 CPCS PDUs received with
         CRC-32 errors on this AAL5 VCC at the
         interface associated with an AAL5 entity."
    ::= { aal5VccEntry 3 }

aal5VccSarTimeOuts OBJECT-TYPE
    SYNTAX Counter32
    ACCESS read-only
    STATUS mandatory
    DESCRIPTION
        "The number of partially re-assembled AAL5
         CPCS PDUs which were discarded
         on this AAL5 VCC at the interface associated
         with an AAL5 entity because they
         were not fully re-assembled within the
         required time period.  If the re-assembly
         timer is not supported, then this object
         contains a zero value."
    ::= { aal5VccEntry 4 }

aal5VccOverSizedSDUs OBJECT-TYPE
    SYNTAX Counter32
    ACCESS read-only
    STATUS mandatory
    DESCRIPTION
        "The number of AAL5 CPCS PDUs discarded
         on this AAL5 VCC at the interface
         associated with an AAL5 entity because the
         AAL5 SDUs were too large."
    ::= { aal5VccEntry 5 }

atmTrafficDescrParamIndexNext OBJECT-TYPE
    SYNTAX INTEGER(0..2147483647)
    ACCESS read-only
    STATUS mandatory
    DESCRIPTION
        "This object contains an appropriate value to
         be used for atmTrafficDescrParamIndex when
         creating entries in the
         atmTrafficDescrParamTable.
         The value 0 indicates that no unassigned
         entries are available. To obtain the
         atmTrafficDescrParamIndex value for a new
         entry, the manager issues a management
         protocol retrieval operation to obtain the
         current value of this object.  After each
         retrieval, the agent should modify the value
         to the next unassigned index."
    ::= { atmMIBObjects 13 }

atmInterfaceDs3PlcpGroup OBJECT IDENTIFIER ::= { atmMIBGroups 3 }
-- OBJECT-GROUP
--  Status
--    mandatory
--  Descr
--    A collection of objects providing information
--     about DS3 PLCP layer at an ATM interface.
--  objects
--    atmInterfaceDs3PlcpSEFSs, atmInterfaceDs3PlcpAlarmState, 
--    atmInterfaceDs3PlcpUASs

atmInterfaceTCGroup OBJECT IDENTIFIER ::= { atmMIBGroups 4 }
-- OBJECT-GROUP
--  Status
--    mandatory
--  Descr
--    A collection of objects providing information
--     about TC sublayer at an ATM interface.
--  objects
--    atmInterfaceOCDEvents, atmInterfaceTCAlarmState

aal5VccGroup OBJECT IDENTIFIER ::= { atmMIBGroups 9 }
-- OBJECT-GROUP
--  Status
--    mandatory
--  Descr
--    A collection of objects providing
--     AAL5 configuration and performance statistics
--     of a VCC.
--  objects
--    atmVccAal5CpcsTransmitSduSize, atmVccAal5CpcsReceiveSduSize, 
--    atmVccAal5EncapsType, aal5VccCrcErrors, aal5VccSarTimeOuts, 
--    aal5VccOverSizedSDUs

atmInterfaceConfGroup2 OBJECT IDENTIFIER ::= { atmMIBGroups 10 }
-- OBJECT-GROUP
--  Status
--    mandatory
--  Descr
--    A collection of objects providing configuration
--     information about an ATM interface.
--  objects
--    atmInterfaceMaxVpcs, atmInterfaceMaxVccs, 
--    atmInterfaceConfVpcs, atmInterfaceConfVccs, 
--    atmInterfaceMaxActiveVpiBits, atmInterfaceMaxActiveVciBits, 
--    atmInterfaceIlmiVpi, atmInterfaceIlmiVci, 
--    atmInterfaceMyNeighborIpAddress, atmInterfaceMyNeighborIfName, 
--    atmInterfaceCurrentMaxVpiBits, atmInterfaceCurrentMaxVciBits, 
--    atmInterfaceSubscrAddress

atmTrafficDescrGroup2 OBJECT IDENTIFIER ::= { atmMIBGroups 11 }
-- OBJECT-GROUP
--  Status
--    mandatory
--  Descr
--    A collection of objects providing information
--     about ATM traffic descriptor type and
--     the associated parameters.
--  objects
--    atmTrafficDescrType, atmTrafficDescrParam1, 
--    atmTrafficDescrParam2, atmTrafficDescrParam3, 
--    atmTrafficDescrParam4, atmTrafficDescrParam5, 
--    atmTrafficDescrRowStatus, atmServiceCategory, 
--    atmTrafficDescrParamIndexNext

atmVpcTerminationGroup2 OBJECT IDENTIFIER ::= { atmMIBGroups 12 }
-- OBJECT-GROUP
--  Status
--    mandatory
--  Descr
--    A collection of objects providing information
--     about a VPL at an ATM interface which
--     terminates a VPC (i.e., one which is NOT
--     cross-connected to other VPLs).
--  objects
--    atmVplOperStatus, atmVplAdminStatus, atmVplLastChange, 
--    atmVplReceiveTrafficDescrIndex, 
--    atmVplTransmitTrafficDescrIndex, atmVplRowStatus, 
--    atmVplCastType, atmVplConnKind

atmVccTerminationGroup2 OBJECT IDENTIFIER ::= { atmMIBGroups 13 }
-- OBJECT-GROUP
--  Status
--    mandatory
--  Descr
--    A collection of objects providing information
--     about a VCL at an ATM interface
--     which terminates a VCC (i.e., one which is
--     NOT cross-connected to other VCLs).
--  objects
--    atmVclOperStatus, atmVclAdminStatus, atmVclLastChange, 
--    atmVclReceiveTrafficDescrIndex, 
--    atmVclTransmitTrafficDescrIndex, atmVccAalType, 
--    atmVclRowStatus, atmVclCastType, atmVclConnKind

atmVplCrossConnectGroup OBJECT IDENTIFIER ::= { atmMIBGroups 14 }
-- OBJECT-GROUP
--  Status
--    mandatory
--  Descr
--    A collection of objects providing
--     information about the VPLs that
--     are cross-connected together.
--  objects
--    atmVplReceiveTrafficDescrIndex, 
--    atmVplTransmitTrafficDescrIndex, atmVplOperStatus, 
--    atmVplRowStatus, atmVplCastType, atmVplConnKind

atmVpPvcCrossConnectGroup OBJECT IDENTIFIER ::= { atmMIBGroups 15 }
-- OBJECT-GROUP
--  Status
--    mandatory
--  Descr
--    A collection of objects providing
--     information about a VP cross-connect
--     for PVCs. These objects are not used
--     for Soft PVCs or SVCs.
--  objects
--    atmVpCrossConnectAdminStatus, atmVpCrossConnectL2HOperStatus, 
--    atmVpCrossConnectH2LOperStatus, 
--    atmVpCrossConnectL2HLastChange, 
--    atmVpCrossConnectH2LLastChange, atmVpCrossConnectRowStatus, 
--    atmVplCrossConnectIdentifier, atmVpCrossConnectIndexNext

atmVclCrossConnectGroup OBJECT IDENTIFIER ::= { atmMIBGroups 16 }
-- OBJECT-GROUP
--  Status
--    mandatory
--  Descr
--    A collection of objects providing
--     information about the VCLs that
--     are cross-connected together.
--  objects
--    atmVclReceiveTrafficDescrIndex, 
--    atmVclTransmitTrafficDescrIndex, atmVclOperStatus, 
--    atmVclRowStatus, atmVclCastType, atmVclConnKind

atmVcPvcCrossConnectGroup OBJECT IDENTIFIER ::= { atmMIBGroups 17 }
-- OBJECT-GROUP
--  Status
--    mandatory
--  Descr
--    A collection of objects providing
--     information about a VC cross-connect
--     for PVCs. These objects are not used
--     for Soft PVCs or SVCs.
--  objects
--    atmVcCrossConnectAdminStatus, atmVcCrossConnectL2HOperStatus, 
--    atmVcCrossConnectH2LOperStatus, 
--    atmVcCrossConnectL2HLastChange, 
--    atmVcCrossConnectH2LLastChange, atmVcCrossConnectRowStatus, 
--    atmVclCrossConnectIdentifier, atmVcCrossConnectIndexNext

atmInterfaceConfGroup OBJECT IDENTIFIER ::= { atmMIBGroups 1 }
-- OBJECT-GROUP
--  Status
--    deprecated
--  Descr
--    A collection of objects providing configuration
--     information about an ATM interface.
--  objects
--    atmInterfaceMaxVpcs, atmInterfaceMaxVccs, 
--    atmInterfaceConfVpcs, atmInterfaceConfVccs, 
--    atmInterfaceMaxActiveVpiBits, atmInterfaceMaxActiveVciBits, 
--    atmInterfaceIlmiVpi, atmInterfaceIlmiVci, 
--    atmInterfaceAddressType, atmInterfaceAdminAddr, 
--    atmInterfaceMyNeighborIpAddress, atmInterfaceMyNeighborIfName

atmTrafficDescrGroup OBJECT IDENTIFIER ::= { atmMIBGroups 2 }
-- OBJECT-GROUP
--  Status
--    deprecated
--  Descr
--    A collection of objects providing information
--     about ATM traffic descriptor type and
--     the associated parameters.
--  objects
--    atmTrafficDescrType, atmTrafficDescrParam1, 
--    atmTrafficDescrParam2, atmTrafficDescrParam3, 
--    atmTrafficDescrParam4, atmTrafficDescrParam5, 
--    atmTrafficQoSClass, atmTrafficDescrRowStatus

atmVpcTerminationGroup OBJECT IDENTIFIER ::= { atmMIBGroups 5 }
-- OBJECT-GROUP
--  Status
--    deprecated
--  Descr
--    A collection of objects providing
--     information about a VPL at an ATM interface
--     which terminates a VPC
--     (i.e., one which is NOT cross-connected
--     to other VPLs).
--  objects
--    atmVplOperStatus, atmVplAdminStatus, atmVplLastChange, 
--    atmVplReceiveTrafficDescrIndex, 
--    atmVplTransmitTrafficDescrIndex, atmVplRowStatus

atmVccTerminationGroup OBJECT IDENTIFIER ::= { atmMIBGroups 6 }
-- OBJECT-GROUP
--  Status
--    deprecated
--  Descr
--    A collection of objects providing information
--     about a VCL at an ATM interface
--     which terminates a VCC (i.e., one which is
--     NOT cross-connected to other VCLs).
--  objects
--    atmVclOperStatus, atmVclAdminStatus, atmVclLastChange, 
--    atmVclReceiveTrafficDescrIndex, 
--    atmVclTransmitTrafficDescrIndex, atmVccAalType, 
--    atmVclRowStatus

atmVpCrossConnectGroup OBJECT IDENTIFIER ::= { atmMIBGroups 7 }
-- OBJECT-GROUP
--  Status
--    deprecated
--  Descr
--    A collection of objects providing
--     information about a VP cross-connect
--     and the associated VPLs that are
--     cross-connected together.
--  objects
--    atmVplReceiveTrafficDescrIndex, 
--    atmVplTransmitTrafficDescrIndex, atmVplOperStatus, 
--    atmVplRowStatus, atmVpCrossConnectAdminStatus, 
--    atmVpCrossConnectL2HOperStatus, 
--    atmVpCrossConnectH2LOperStatus, 
--    atmVpCrossConnectL2HLastChange, 
--    atmVpCrossConnectH2LLastChange, atmVpCrossConnectRowStatus, 
--    atmVplCrossConnectIdentifier, atmVpCrossConnectIndexNext

atmVcCrossConnectGroup OBJECT IDENTIFIER ::= { atmMIBGroups 8 }
-- OBJECT-GROUP
--  Status
--    deprecated
--  Descr
--    A collection of objects providing
--     information about a VC cross-connect
--     and the associated VCLs that are
--     cross-connected together.
--  objects
--    atmVclReceiveTrafficDescrIndex, 
--    atmVclTransmitTrafficDescrIndex, atmVclOperStatus, 
--    atmVclRowStatus, atmVcCrossConnectAdminStatus, 
--    atmVcCrossConnectL2HOperStatus, 
--    atmVcCrossConnectH2LOperStatus, 
--    atmVcCrossConnectL2HLastChange, 
--    atmVcCrossConnectH2LLastChange, atmVcCrossConnectRowStatus, 
--    atmVclCrossConnectIdentifier, atmVcCrossConnectIndexNext

atmMIBCompliance2 OBJECT IDENTIFIER ::= { atmMIBCompliances 2 }
-- MODULE-COMPLIANCE
--  Status
--    mandatory
--  Descr
--    The compliance statement for SNMP entities
--     including networks which have ATM and
--     AAL5 interfaces.
--  Module
--    >>current<<
--   MandGroup
--    atmInterfaceConfGroup2
--   MandGroup
--    atmTrafficDescrGroup2
--   ObjVar
--    atmInterfaceMaxVpcs
--   ObjVar
--    atmInterfaceMaxVccs
--   ObjVar
--    atmInterfaceMaxActiveVpiBits
--   ObjVar
--    atmInterfaceMaxActiveVciBits
--   ObjVar
--    atmInterfaceIlmiVpi
--   ObjVar
--    atmInterfaceIlmiVci
--   ObjVar
--    atmInterfaceMyNeighborIpAddress
--   ObjVar
--    atmInterfaceMyNeighborIfName
--   ObjVar
--    atmInterfaceSubscrAddress
--   ObjVar
--    atmTrafficDescrParamIndexNext
--   ObjVar
--    atmTrafficDescrType
--   ObjVar
--    atmTrafficDescrParam1
--   ObjVar
--    atmTrafficDescrParam2
--   ObjVar
--    atmTrafficDescrParam3
--   ObjVar
--    atmTrafficDescrParam4
--   ObjVar
--    atmTrafficDescrParam5
--   ObjVar
--    atmServiceCategory
--   ObjVar
--    atmTrafficDescrRowStatus
--   OptGroup
--    atmInterfaceDs3PlcpGroup
--   OptGroup
--    atmInterfaceTCGroup
--   OptGroup
--    atmVpcTerminationGroup2
--   OptGroup
--    atmVplCrossConnectGroup
--   OptGroup
--    atmVpPvcCrossConnectGroup
--   ObjVar
--    atmVplAdminStatus
--   ObjVar
--    atmVplReceiveTrafficDescrIndex
--   ObjVar
--    atmVplTransmitTrafficDescrIndex
--   ObjVar
--    atmVplRowStatus
--   ObjVar
--    atmVplCastType
--   ObjVar
--    atmVplConnKind
--   ObjVar
--    atmVpCrossConnectAdminStatus
--   ObjVar
--    atmVpCrossConnectRowStatus
--   OptGroup
--    atmVccTerminationGroup2
--   OptGroup
--    atmVclCrossConnectGroup
--   OptGroup
--    atmVcPvcCrossConnectGroup
--   ObjVar
--    atmVclAdminStatus
--   ObjVar
--    atmVclReceiveTrafficDescrIndex
--   ObjVar
--    atmVclTransmitTrafficDescrIndex
--   ObjVar
--    atmVccAalType
--   ObjVar
--    atmVclRowStatus
--   ObjVar
--    atmVclCastType
--   ObjVar
--    atmVclConnKind
--   ObjVar
--    atmVcCrossConnectAdminStatus
--   ObjVar
--    atmVcCrossConnectRowStatus
--   OptGroup
--    aal5VccGroup
--   ObjVar
--    atmVccAal5CpcsTransmitSduSize
--   ObjVar
--    atmVccAal5CpcsReceiveSduSize
--   ObjVar
--    atmVccAal5EncapsType

atmMIBCompliance OBJECT IDENTIFIER ::= { atmMIBCompliances 1 }
-- MODULE-COMPLIANCE
--  Status
--    deprecated
--  Descr
--    The compliance statement for SNMP entities
--     including networks which have ATM and
--     AAL5 interfaces.
--  Module
--    >>current<<
--   MandGroup
--    atmInterfaceConfGroup
--   MandGroup
--    atmTrafficDescrGroup
--   ObjVar
--    atmInterfaceMaxVpcs
--   ObjVar
--    atmInterfaceMaxVccs
--   ObjVar
--    atmInterfaceMaxActiveVpiBits
--   ObjVar
--    atmInterfaceMaxActiveVciBits
--   ObjVar
--    atmInterfaceIlmiVpi
--   ObjVar
--    atmInterfaceIlmiVci
--   ObjVar
--    atmInterfaceMyNeighborIpAddress
--   ObjVar
--    atmInterfaceMyNeighborIfName
--   ObjVar
--    atmTrafficDescrType
--   ObjVar
--    atmTrafficDescrParam1
--   ObjVar
--    atmTrafficDescrParam2
--   ObjVar
--    atmTrafficDescrParam3
--   ObjVar
--    atmTrafficDescrParam4
--   ObjVar
--    atmTrafficDescrParam5
--   ObjVar
--    atmTrafficQoSClass
--   ObjVar
--    atmTrafficDescrRowStatus
--   OptGroup
--    atmInterfaceDs3PlcpGroup
--   OptGroup
--    atmInterfaceTCGroup
--   OptGroup
--    atmVpcTerminationGroup
--   OptGroup
--    atmVpCrossConnectGroup
--   ObjVar
--    atmVplAdminStatus
--   ObjVar
--    atmVplReceiveTrafficDescrIndex
--   ObjVar
--    atmVplTransmitTrafficDescrIndex
--   ObjVar
--    atmVplRowStatus
--   ObjVar
--    atmVpCrossConnectAdminStatus
--   ObjVar
--    atmVpCrossConnectRowStatus
--   OptGroup
--    atmVccTerminationGroup
--   OptGroup
--    atmVcCrossConnectGroup
--   ObjVar
--    atmVclAdminStatus
--   ObjVar
--    atmVclReceiveTrafficDescrIndex
--   ObjVar
--    atmVclTransmitTrafficDescrIndex
--   ObjVar
--    atmVccAalType
--   ObjVar
--    atmVclRowStatus
--   ObjVar
--    atmVcCrossConnectAdminStatus
--   ObjVar
--    atmVcCrossConnectRowStatus
--   OptGroup
--    aal5VccGroup
--   ObjVar
--    atmVccAal5CpcsTransmitSduSize
--   ObjVar
--    atmVccAal5CpcsReceiveSduSize
--   ObjVar
--    atmVccAal5EncapsType


END

ATM2-MIB DEFINITIONS ::= BEGIN

-- From file: "atm2.mi2"
-- Compile options "4 G A M"

IMPORTS
    Gauge32, Counter32, Integer32
            FROM SNMPv2-SMI-v1
    OBJECT-TYPE
            FROM RFC-1212
    TRAP-TYPE
            FROM RFC-1215
    ifIndex
	    FROM RFC1213-MIB
    TruthValue, RowStatus, TimeStamp, DisplayString
            FROM SNMPv2-TC-v1
    InterfaceIndex
            FROM IF-MIB
    atmMIB, atmMIBObjects
	    FROM ATM-TC-MIB
    atmVpCrossConnectIndex, atmVpCrossConnectLowIfIndex, atmVpCrossConnectLowVpi,
    atmVpCrossConnectHighIfIndex, atmVpCrossConnectHighVpi
	    FROM ATM-MIB
    atmVcCrossConnectIndex, atmVcCrossConnectLowIfIndex, atmVcCrossConnectLowVpi, 
    atmVcCrossConnectLowVci, atmVcCrossConnectHighIfIndex, atmVcCrossConnectHighVpi,
    atmVcCrossConnectHighVci
	    FROM ATM-MIB
    atmInterfaceConfEntry, atmVplEntry, atmVplVpi, 
    atmVplOperStatus, atmVclEntry, atmVclVpi, atmVclVci, 
    atmVclOperStatus, atmVpCrossConnectEntry, 
    atmVcCrossConnectEntry
            FROM ATM-MIB
    AtmAddr, AtmSigDescrParamIndex, AtmInterfaceType, 
    AtmIlmiNetworkPrefix, AtmVcIdentifier, AtmVpIdentifier, 
    AtmTrafficDescrParamIndex
            FROM ATM-TC-MIB;


  atm2MIB OBJECT IDENTIFIER ::= { atmMIBObjects 14}

--atm2MIB OBJECT IDENTIFIER ::= { experimental XX }
-- MODULE-IDENTITY
--  LastUpdated
--    9612051200Z
--  OrgName
--    IETF AToMMIB Working Group
--  ContactInfo
--              Faye Ly
--      Postal:  3Com Networks Inc.
--               Santa Clara, CA 95052
--               US
--      Tel:     +1 408 764 6576
--      Fax:     +1 408 495 2599
--      E-Mail:  faye@3com.com
--    
--               Michael Noto
--      Postal:  Network Equipment Technologies
--               800 Saginaw Drive RM 21.1.111
--               Redwood City, CA 94063
--               US
--      Tel:     +1 415 569 7143
--      Fax:     +1 908 758 4177
--      E-mail:  mike_noto@net.com
--    
--               Andrew Smith
--      Postal:  Extreme Networks
--               1601 S. De Anza Blvd, #220
--               Cupertino, CA 95014
--               US
--      Tel:     +1 408 342 0985
--      Fax:     +1 408 342 0989
--      E-Mail:  ansmith@ix.netcom.com
--    
--               Ethan Mickey Spiegel
--      Postal:  Cisco Systems
--               170 W. Tasman Drive
--               San Jose, CA 95134-1706
--      Tel:     +1 408 526 6408
--      Fax:     +1 408 526 6488
--      E-Mail:  mspiegel@cisco.com
--    
--               Kaj Tesink
--      Postal:  Bell Communications Research
--               331 Newman Springs Road
--               Red Bank, NJ 07701
--               US
--      Tel:     +1 908 758 5254
--      Fax:     +1 908 758 4177
--      E-mail:  kaj@cc.bellcore.com
--  Descr
--    This MIB Module is a supplement to the
--    ATM-MIB [1].

atm2MIBObjects  OBJECT IDENTIFIER ::= { atm2MIB 1 }
atm2MIBTraps    OBJECT IDENTIFIER ::= { atm2MIB 2 }
atmPvcTraps     OBJECT IDENTIFIER ::= { atm2MIBTraps 1 }
atmPvcTrapsPrefix OBJECT IDENTIFIER ::= { atmPvcTraps 0 }
atm2MIBConformance OBJECT IDENTIFIER ::= { atm2MIB 3 }
atm2MIBGroups   OBJECT IDENTIFIER ::= { atm2MIBConformance 1 }
atm2MIBCompliances OBJECT IDENTIFIER ::= { atm2MIBConformance 2 }

atmSvcVpCrossConnectTable OBJECT-TYPE
    SYNTAX SEQUENCE OF AtmSvcVpCrossConnectEntry
    ACCESS not-accessible
    STATUS mandatory
    DESCRIPTION
        "The ATM SVPC Cross Connect table.  A
        bi-directional VP cross-connect between two
        switched VPLs is modeled as one entry in this
        table.  A Soft PVPC cross-connect, between a
        soft permanent VPL and a switched VPL, is
        also modeled as one entry in this table."
    ::= { atm2MIBObjects 1 }

atmSvcVpCrossConnectEntry OBJECT-TYPE
    SYNTAX AtmSvcVpCrossConnectEntry
    ACCESS not-accessible
    STATUS mandatory
    DESCRIPTION
        "An entry in the ATM SVPC Cross Connect table.
        This entry is used to model a bi-directional
        ATM VP cross-connect between two VPLs."
    INDEX { atmSvcVpCrossConnectIndex, atmSvcVpCrossConnectLowIfIndex, atmSvcVpCrossConnectLowVpi, atmSvcVpCrossConnectHighIfIndex, atmSvcVpCrossConnectHighVpi }
    ::= { atmSvcVpCrossConnectTable 1 }

AtmSvcVpCrossConnectEntry ::= SEQUENCE {
    atmSvcVpCrossConnectIndex INTEGER,
    atmSvcVpCrossConnectLowIfIndex InterfaceIndex,
    atmSvcVpCrossConnectLowVpi AtmVpIdentifier,
    atmSvcVpCrossConnectHighIfIndex InterfaceIndex,
    atmSvcVpCrossConnectHighVpi AtmVpIdentifier,
    atmSvcVpCrossConnectCreationTime TimeStamp,
    atmSvcVpCrossConnectRowStatus RowStatus
    }

atmSvcVpCrossConnectIndex OBJECT-TYPE
    SYNTAX INTEGER(1..2147483647)
    ACCESS not-accessible
    STATUS mandatory
    DESCRIPTION
        "A unique value to identify this SVPC cross-connect."
    ::= { atmSvcVpCrossConnectEntry 1 }

atmSvcVpCrossConnectLowIfIndex OBJECT-TYPE
    SYNTAX InterfaceIndex
--    Rsyntax Integer32
    ACCESS not-accessible
    STATUS mandatory
    DESCRIPTION
        "The value of this object is equal to MIB II's
        ifIndex value of the ATM interface port for this
        SVPC cross-connect.  The term low implies
        that this ATM interface has the numerically lower
        ifIndex value than the other ATM interface
        identified in the same atmSvcVpCrossConnectEntry."
    ::= { atmSvcVpCrossConnectEntry 2 }

atmSvcVpCrossConnectLowVpi OBJECT-TYPE
    SYNTAX AtmVpIdentifier
--    Rsyntax INTEGER(0..4095)
    ACCESS not-accessible
    STATUS mandatory
    DESCRIPTION
        "The value of this object is equal to the VPI
        value associated with the SVPC cross-connect
        at the ATM interface that is identified by
        atmSvcVpCrossConnectLowIfIndex.  The VPI value
        cannot exceed the number supported by the
        atmInterfaceMaxVpiBits at the low ATM interface
        port."
    ::= { atmSvcVpCrossConnectEntry 3 }

atmSvcVpCrossConnectHighIfIndex OBJECT-TYPE
    SYNTAX InterfaceIndex
--    Rsyntax Integer32
    ACCESS not-accessible
    STATUS mandatory
    DESCRIPTION
        "The value of this object is equal to MIB II's
         ifIndex value of the ATM interface port for
         this SVC VP cross-connect.  The term high
         implies that this ATM interface has the
         numerically higher ifIndex value than the
         other ATM interface identified in the same
         atmSvcVpCrossConnectEntry."
    ::= { atmSvcVpCrossConnectEntry 4 }

atmSvcVpCrossConnectHighVpi OBJECT-TYPE
    SYNTAX AtmVpIdentifier
--    Rsyntax INTEGER(0..4095)
    ACCESS not-accessible
    STATUS mandatory
    DESCRIPTION
        "The value of this object is equal to the VPI
         value associated with the SVPC cross-connect
         at the ATM interface that is identified by
         atmSvcVpCrossConnectHighIfIndex.  The VPI value
         cannot exceed the number supported by the
         atmInterfaceMaxVpiBits at the high ATM interface
         port."
    ::= { atmSvcVpCrossConnectEntry 5 }

atmSvcVpCrossConnectCreationTime OBJECT-TYPE
    SYNTAX TimeStamp
--    Rsyntax TimeTicks
    ACCESS read-only
    STATUS mandatory
    DESCRIPTION
        "The value of MIB II's sysUpTime object
         at the time this bi-directional SVPC
         cross-connect was created.  If the current
         state was entered prior to the last
         re-initialization of the agent, then this
         object contains a zero value."
    ::= { atmSvcVpCrossConnectEntry 6 }

atmSvcVpCrossConnectRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to delete rows in the
        atmSvcVpCrossConnectTable."
    ::= { atmSvcVpCrossConnectEntry 7 }

atmSvcVcCrossConnectTable OBJECT-TYPE
    SYNTAX SEQUENCE OF AtmSvcVcCrossConnectEntry
    ACCESS not-accessible
    STATUS mandatory
    DESCRIPTION
        "The ATM SVCC Cross Connect table.  A
         bi-directional VC cross-connect between two
         switched VCLs is modeled as one entry in
         this table.  A Soft PVCC cross-connect,
         between a soft permanent VCL and a switched
         VCL, is also modeled as one entry in this
         table."
    ::= { atm2MIBObjects 2 }

atmSvcVcCrossConnectEntry OBJECT-TYPE
    SYNTAX AtmSvcVcCrossConnectEntry
    ACCESS not-accessible
    STATUS mandatory
    DESCRIPTION
        "An entry in the ATM SVCC Cross Connect table.
         This entry is used to model a bi-directional ATM
         VC cross-connect between two VCLs."
    INDEX { atmSvcVcCrossConnectIndex, atmSvcVcCrossConnectLowIfIndex, atmSvcVcCrossConnectLowVpi, atmSvcVcCrossConnectLowVci, atmSvcVcCrossConnectHighIfIndex, atmSvcVcCrossConnectHighVpi, atmSvcVcCrossConnectHighVci }
    ::= { atmSvcVcCrossConnectTable 1 }

AtmSvcVcCrossConnectEntry ::= SEQUENCE {
    atmSvcVcCrossConnectIndex INTEGER,
    atmSvcVcCrossConnectLowIfIndex InterfaceIndex,
    atmSvcVcCrossConnectLowVpi AtmVpIdentifier,
    atmSvcVcCrossConnectLowVci AtmVcIdentifier,
    atmSvcVcCrossConnectHighIfIndex InterfaceIndex,
    atmSvcVcCrossConnectHighVpi AtmVpIdentifier,
    atmSvcVcCrossConnectHighVci AtmVcIdentifier,
    atmSvcVcCrossConnectCreationTime TimeStamp,
    atmSvcVcCrossConnectRowStatus RowStatus
    }

atmSvcVcCrossConnectIndex OBJECT-TYPE
    SYNTAX INTEGER(1..2147483647)
    ACCESS not-accessible
    STATUS mandatory
    DESCRIPTION
        "A unique value to identify this SVCC cross-connect."
    ::= { atmSvcVcCrossConnectEntry 1 }

atmSvcVcCrossConnectLowIfIndex OBJECT-TYPE
    SYNTAX InterfaceIndex
--    Rsyntax Integer32
    ACCESS not-accessible
    STATUS mandatory
    DESCRIPTION
        "The value of this object is equal to MIB II's
         ifIndex value of the ATM interface port for this
         SVCC cross-connect.  The term low implies that
         this ATM interface has the numerically lower
         ifIndex value than the other ATM interface
         identified in the same atmSvcVcCrossConnectEntry."
    ::= { atmSvcVcCrossConnectEntry 2 }

atmSvcVcCrossConnectLowVpi OBJECT-TYPE
    SYNTAX AtmVpIdentifier
--    Rsyntax INTEGER(0..4095)
    ACCESS not-accessible
    STATUS mandatory
    DESCRIPTION
        "The value of this object is equal to the VPI
         value associated with the SVCC cross-connect
         at the ATM interface that is identified by
         atmSvcVcCrossConnectLowIfIndex.  The VPI value
         cannot exceed the number supported by the
         atmInterfaceMaxVpiBits at the low ATM interface
         port."
    ::= { atmSvcVcCrossConnectEntry 3 }

atmSvcVcCrossConnectLowVci OBJECT-TYPE
    SYNTAX AtmVcIdentifier
--    Rsyntax INTEGER(0..65535)
    ACCESS not-accessible
    STATUS mandatory
    DESCRIPTION
        "The value of this object is equal to the VCI
         value associated with the SVCC cross-connect
         at the ATM interface that is identified by
         atmSvcVcCrossConnectLowIfIndex.  The VCI value
         cannot exceed the number supported by the
         atmInterfaceMaxVciBits at the low ATM interface
         port."
    ::= { atmSvcVcCrossConnectEntry 4 }

atmSvcVcCrossConnectHighIfIndex OBJECT-TYPE
    SYNTAX InterfaceIndex
--    Rsyntax Integer32
    ACCESS not-accessible
    STATUS mandatory
    DESCRIPTION
        "The value of this object is equal to MIB II's
         ifIndex value for the ATM interface port for
         this SVCC cross-connect.  The term high implies
         that this ATM interface has the numerically
         higher ifIndex value than the other ATM interface
         identified in the same atmSvcVcCrossConnectEntry."
    ::= { atmSvcVcCrossConnectEntry 5 }

atmSvcVcCrossConnectHighVpi OBJECT-TYPE
    SYNTAX AtmVpIdentifier
--    Rsyntax INTEGER(0..4095)
    ACCESS not-accessible
    STATUS mandatory
    DESCRIPTION
        "The value of this object is equal to the VPI
         value associated with the SVCC cross-connect
         at the ATM interface that is identified by
         atmSvcVcCrossConnectHighIfIndex.  The VPI value
         cannot exceed the number supported by the
         atmInterfaceMaxVpiBits at the high ATM interface
         port."
    ::= { atmSvcVcCrossConnectEntry 6 }

atmSvcVcCrossConnectHighVci OBJECT-TYPE
    SYNTAX AtmVcIdentifier
--    Rsyntax INTEGER(0..65535)
    ACCESS not-accessible
    STATUS mandatory
    DESCRIPTION
        "The value of this object is equal to the VCI
         value associated with the SVCC cross-connect
         at the ATM interface that is identified by
         atmSvcVcCrossConnectHighIfIndex.  The VCI value
         cannot exceed the number supported by the
         atmInterfaceMaxVciBits at the high ATM interface
         port."
    ::= { atmSvcVcCrossConnectEntry 7 }

atmSvcVcCrossConnectCreationTime OBJECT-TYPE
    SYNTAX TimeStamp
--    Rsyntax TimeTicks
    ACCESS read-only
    STATUS mandatory
    DESCRIPTION
        "The value of MIB II's sysUpTime object
         at the time this bi-directional SVCC
         cross-connect was created.  If the current
         state was entered prior to the last
         re-initialization of the agent, then this
         object contains a zero value."
    ::= { atmSvcVcCrossConnectEntry 8 }

atmSvcVcCrossConnectRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to delete rows in the
        atmSvcVcCrossConnectTable."
    ::= { atmSvcVcCrossConnectEntry 9 }

atmSigStatTable OBJECT-TYPE
    SYNTAX SEQUENCE OF AtmSigStatEntry
    ACCESS not-accessible
    STATUS mandatory
    DESCRIPTION
        "This table contains ATM interface signalling monitoring
         , one entry per ATM signalling interface."
    ::= { atm2MIBObjects 3 }

atmSigStatEntry OBJECT-TYPE
    SYNTAX AtmSigStatEntry
    ACCESS not-accessible
    STATUS mandatory
    DESCRIPTION
        "This list contains signalling statistics variables."
    INDEX { ifIndex }
    ::= { atmSigStatTable 1 }

AtmSigStatEntry ::= SEQUENCE {
    atmSigSSCOPConEvents Counter32,
    atmSigSSCOPErrdPdus Counter32,
    atmSigDetectSetupAttempts Counter32,
    atmSigEmitSetupAttempts Counter32,
    atmSigDetectUnavailRoutes Counter32,
    atmSigEmitUnavailRoutes Counter32,
    atmSigDetectUnavailResrcs Counter32,
    atmSigEmitUnavailResrcs Counter32,
    atmSigDetectCldPtyEvents Counter32,
    atmSigEmitCldPtyEvents Counter32,
    atmSigDetectMsgErrors Counter32,
    atmSigEmitMsgErrors Counter32,
    atmSigDetectClgPtyEvents Counter32,
    atmSigEmitClgPtyEvents Counter32,
    atmSigDetectTimerExpireds Counter32,
    atmSigEmitTimerExpireds Counter32,
    atmSigDetectRestarts Counter32,
    atmSigEmitRestarts Counter32,
    atmSigInEstabls Counter32,
    atmSigOutEstabls Counter32
    }

atmSigSSCOPConEvents OBJECT-TYPE
    SYNTAX Counter32
    ACCESS read-only
    STATUS mandatory
    DESCRIPTION
        "SSCOP Connection Events Counter.  This
        counter counts the sum of the following errors:
        
        1) SSCOP Connection Disconnect Counter
        
        The abnormal occurrence of this event is
        characterized by the expiry of Timer_NO_RESPONSE.
        (This event is communicated to the layer management
        with MAA-ERROR code P.  See ITU-T Q.2110 [13].)
        
        2) SSCOP Connection Initiation Failure
        
        This condition indicates the inability to establish
        an SSCOP connection.  This event occurs whenever the
        number of expiries of the connection control timer
        (Timer_CC) exceeds the MaxCC or upon receipt of a
        connection reject message BGREJ PDU.  (This event is
        communicated to layer management with MAA-ERROR
        code O.  See ITU-T Q.2110.)
        
        3) SSCOP Connection Re-Establ/Resynch
        
        This event occurs upon receipt of a BGN PDU or RESYNC
        PDU."
    ::= { atmSigStatEntry 1 }

atmSigSSCOPErrdPdus OBJECT-TYPE
    SYNTAX Counter32
    ACCESS read-only
    STATUS mandatory
    DESCRIPTION
        "SSCOP Errored PDUs Counter.  This counter counts the
        sum of the following errors:
        
        1) Invalid PDUs.
           These are defined in SSCOP and consist of PDUs
           with incorrect length (MAA-ERROR code U),
           undefined PDU type code or not 32-bit aligned.
        
        2) PDUs that result in MAA error codes and are
           discarded
           See Errors A-M and Q-T defined in ITU-T Q.2110 [13]."
    ::= { atmSigStatEntry 2 }

atmSigDetectSetupAttempts OBJECT-TYPE
    SYNTAX Counter32
    ACCESS read-only
    STATUS mandatory
    DESCRIPTION
        "Call Setup Attempts Counter.  This counter counts
        the number of call setup attempts(both successful
        and unsuccessful) detected on this interface."
    ::= { atmSigStatEntry 3 }

atmSigEmitSetupAttempts OBJECT-TYPE
    SYNTAX Counter32
    ACCESS read-only
    STATUS mandatory
    DESCRIPTION
        "Call Setup Attempts Counter.  This counter counts the
        number of call setup attempts(both successful and
        unsuccessful) transmitted on this interface."
    ::= { atmSigStatEntry 4 }

atmSigDetectUnavailRoutes OBJECT-TYPE
    SYNTAX Counter32
    ACCESS read-only
    STATUS mandatory
    DESCRIPTION
        "Number of Route Unavailability detected on this
        interface. This counter is incremented when a RELEASE,
        RELEASE COMPLETE (only when not preceded by a RELEASE
        mesg for the same call), ADD PARTY REJECT, or STATUS
        message that contains one of the following cause code
        values is received (Note: These cause values apply to
        both UNI3.0 and UNI3.1):
        
        
        Cause Value            Meaning
        
           1            unallocated (unassigned) number
           2            no route to specified transit network
           3            no route to destination
        
        NOTE:  For this counter, RELEASE COMPLETE
        messages that are a reply to a previous RELEASE
        message and contain the same cause value, are
        redundant (for counting purposes) and should not
        be counted."
    ::= { atmSigStatEntry 5 }

atmSigEmitUnavailRoutes OBJECT-TYPE
    SYNTAX Counter32
    ACCESS read-only
    STATUS mandatory
    DESCRIPTION
        "Number of Route Unavailability transmitted from this
        interface. This counter is incremented when a RELEASE,
        RELEASE COMPLETE (only when not preceded by a RELEASE
        mesg for the same call), ADD PARTY REJECT, or STATUS
        message that contains one of the following cause code
        values is transmitted (Note: These cause values apply
        to both UNI3.0 and UNI3.1):
        
        
        Cause Value            Meaning
        
           1            unallocated (unassigned) number
           2            no route to specified transit network
           3            no route to destination
        
        NOTE:  For this counter, RELEASE COMPLETE
        messages that are a reply to a previous RELEASE
        message and contain the same cause value, are
        redundant (for counting purposes) and should not
        be counted."
    ::= { atmSigStatEntry 6 }

atmSigDetectUnavailResrcs OBJECT-TYPE
    SYNTAX Counter32
    ACCESS read-only
    STATUS mandatory
    DESCRIPTION
        "Number of Resource Unavailability detected on this
        interfrace.  This counter is incremented when a
        RELEASE, RELEASE COMPLETE (only when not preceded by a
        RELEASE mesg for the same call), ADD PARTY REJECT, or
        STATUS message that contains one of the following cause
        code values is received (Note: These cause values apply
        to both UNI3.0 and UNI3.1 unless otherwise stated):
        
        Cause Value          Meaning
        
           35          requested VPCI/VCI not available
           37          user cell rate not available (UNI3.1
                       only)
           38          network out of order
           41          temporary failure
           45          no VPCI/VCI available
           47          resource unavailable, unspecified
           49          Quality of Service unavailable
           51          user cell rate not available (UNI3.0
                       only)
           58          bearer capability not presently
                       available
           63          Service or option not available,
                       unspecified
           92          too many pending add party requests
        
        NOTE:  For this counter, RELEASE COMPLETE
        messages that are a reply to a previous RELEASE
        message and contain the same cause value, are
        redundant (for counting purposes) and should not
        be counted."
    ::= { atmSigStatEntry 7 }

atmSigEmitUnavailResrcs OBJECT-TYPE
    SYNTAX Counter32
    ACCESS read-only
    STATUS mandatory
    DESCRIPTION
        "Number of Resource Unavailability transmitted from
        this interfrace.  This counter is incremented when a
        RELEASE, RELEASE COMPLETE (only when not preceded by a
        RELEASE mesg for the same call), ADD PARTY REJECT, or
        STATUS message that contains one of the following cause
        code values is transmitted (Note: These cause values
        apply to both UNI3.0 and UNI3.1 unless otherwise
        stated):
        
        Cause Value          Meaning
        
           35          requested VPCI/VCI not available
           37          user cell rate not available (UNI3.1
                       only)
           38          network out of order
           41          temporary failure
           45          no VPCI/VCI available
           47          resource unavailable, unspecified
           49          Quality of Service unavailable
           51          user cell rate not available (UNI3.0
                       only)
           58          bearer capability not presently
                       available
           63          Service or option not available,
                       unspecified
           92          too many pending add party requests
        
        NOTE:  For this counter, RELEASE COMPLETE
        messages that are a reply to a previous RELEASE
        message and contain the same cause value, are
        redundant (for counting purposes) and should not
        be counted."
    ::= { atmSigStatEntry 8 }

atmSigDetectCldPtyEvents OBJECT-TYPE
    SYNTAX Counter32
    ACCESS read-only
    STATUS mandatory
    DESCRIPTION
        "Number of Called Party Responsible For Unsuccessful
        Call detected on this interface. This counter is
        incremented when a RELEASE, RELEASE COMPLETE (only when
        not preceded by a RELEASE mesg for the same call), ADD
        PARTY REJECT, or STATUS message that contains one of
        the following cause code values is received (Note:
        These cause values apply to both UNI3.0 and UNI3.1):
        
        Cause Value         Meaning
        
           17           user busy
           18           no user responding
           21           call rejected
           22           number changed
           23           user rejects all calls with calling
                        line id restriction (CLIR)
           27           destination out of order
           31           normal, unspecified
           88           incompatible destination
        
        NOTE:  For this counter, RELEASE COMPLETE
        messages that are a reply to a previous RELEASE
        message and contain the same cause value, are
        redundant (for counting purposes) and should not
        be counted.
        
        Note: Cause Value #30 'response to STATUS ENQUIRY'
        was not included in this memo since it did not apply
        to a hard failure."
    ::= { atmSigStatEntry 9 }

atmSigEmitCldPtyEvents OBJECT-TYPE
    SYNTAX Counter32
    ACCESS read-only
    STATUS mandatory
    DESCRIPTION
        "Number of Called Party Responsible For Unsuccessful Call
        transmitted from this interface. This counter is
        incremented when a RELEASE, RELEASE COMPLETE (only
        when not preceded by a RELEASE mesg for the same call),
        ADD PARTY REJECT, or STATUS message that contains one
        of the following cause code values is
        transmitted (Note: These cause values apply to both
        UNI3.0 and UNI3.1):
        
        Cause Value         Meaning
        
           17           user busy
           18           no user responding
           21           call rejected
           22           number changed
           23           user rejects all calls with calling
                        line id restriction (CLIR)
           27           destination out of order
           31           normal, unspecified
           88           incompatible destination
        
        NOTE:  For this counter, RELEASE COMPLETE
        messages that are a reply to a previous RELEASE
        message and contain the same cause value, are
        redundant (for counting purposes) and should not
        be counted.
        
        Note: Cause Value #30 'response to STATUS ENQUIRY'
        was not included in this memo since it did not apply
        to a hard failure."
    ::= { atmSigStatEntry 10 }

atmSigDetectMsgErrors OBJECT-TYPE
    SYNTAX Counter32
    ACCESS read-only
    STATUS mandatory
    DESCRIPTION
        "Number of Incorrect Messages detected on this
        interface.  The Incorrect Messages Counter reflects any
        sort of incorrect information in a message.  This
        includes:
        
        - RELEASE, RELEASE COMPLETE, ADD PARTY REJECT,
          and STATUS messages transmitted, that contain any of
          the Cause values listed below.
        
        - Ignored messages.  These messages are dropped
          because the message was so damaged that it could
          not be further processed.  A list of dropped
          messages is compiled below:
        
           1.  Message with invalid protocol discriminator
        
           2.  Message with errors in the call reference I.E.
                - Bits 5-8 of the first octet not equal to
                  '0000'
                - Bits 1-4 of the first octet indicating a
                  length other than 3 octets
                - RELEASE COMPLETE message received with a
                  call reference that does not relate to a
                  call active or in progress
                - SETUP message received with call reference
                  flag incorrectly set to 1
                - SETUP message received with a call
                  reference for a call that is already
                  active or in progress.
        
           3.  Message too short
        
        
        The following cause values are monitored by this
        counter (Note: These cause values apply to both UNI3.0
        and UNI3.1 unless otherwise stated):
        
        Cause Value     Meaning
        
           10     VPCI/VCI unacceptable (UNI3.0 only)
           36     VPCI/VCI assignment failure (UNI3.1 only)
           81     invalid call reference value
           82     identified channel does not exist
           89     invalid endpoint reference
           96     mandatory information element is missing
           97     message type non-existent or not
                  implemented
           99     information element non-existent or not
                  implemented
           100    invalid information element contents
           101    message not compatible with call state
           104    incorrect message length
           111    protocol error, unspecified
        
           NOTE:  For this counter, RELEASE COMPLETE
           messages that are a reply to a previous RELEASE
           message and contain the same cause value, are
           redundant (for counting purposes) and should not
           be counted."
    ::= { atmSigStatEntry 11 }

atmSigEmitMsgErrors OBJECT-TYPE
    SYNTAX Counter32
    ACCESS read-only
    STATUS mandatory
    DESCRIPTION
        "Number of Incorrect Messages transmitted on this
        interface.  The Incorrect Messages Counter reflects any
        sort of incorrect information in a message.  This
        includes:
        
        
        - RELEASE, RELEASE COMPLETE, ADD PARTY REJECT,
          and STATUS messages transmitted or
          received, that contain any of the Cause values
          listed below.
        
        - Ignored messages.  These messages are dropped
          because the message was so damaged that it could
          not be further processed.  A list of dropped
          messages is compiled below:
        
           1.  Message with invalid protocol discriminator
        
           2.  Message with errors in the call reference I.E.
                - Bits 5-8 of the first octet not equal to
                  '0000'
                - Bits 1-4 of the first octet indicating a
                  length other than 3 octets
                - RELEASE COMPLETE message received with a
                  call reference that does not relate to a
                  call active or in progress
                - SETUP message received with call reference
                  flag incorrectly set to 1
                - SETUP message received with a call
                  reference for a call that is already
                  active or in progress.
        
           3.  Message too short
        
        
        The following cause values are monitored by this
        counter (Note: These cause values apply to both UNI3.0
        and UNI3.1 unless otherwise stated):
        
        Cause Value     Meaning
        
           10     VPCI/VCI unacceptable (UNI3.0 only)
           36     VPCI/VCI assignment failure (UNI3.1 only)
           81     invalid call reference value
           82     identified channel does not exist
           89     invalid endpoint reference
           96     mandatory information element is missing
           97     message type non-existent or not
                  implemented
           99     information element non-existent or not
                  implemented
           100    invalid information element contents
           101    message not compatible with call state
           104    incorrect message length
           111    protocol error, unspecified
        
           NOTE:  For this counter, RELEASE COMPLETE
           messages that are a reply to a previous RELEASE
           message and contain the same cause value, are
           redundant (for counting purposes) and should not
           be counted."
    ::= { atmSigStatEntry 12 }

atmSigDetectClgPtyEvents OBJECT-TYPE
    SYNTAX Counter32
    ACCESS read-only
    STATUS mandatory
    DESCRIPTION
        "Number of Calling Party Events detected on this
        interface.  This counter monitors error events that
        occur due to the originating user doing something
        wrong. This counter is incremented when a RELEASE,
        RELEASE COMPLETE (only when not preceded by a RELEASE
        mesg for the same call), ADD PARTY REJECT, or STATUS
        message that contains one of the following cause code
        values is received (Note: These cause values apply to
        both UNI3.0 and UNI3.1):
        
        Cause Value     Meaning
        
           28     invalid number format (address incomplete)
           43     access information discarded
           57     bearer capability not authorized
           65     bearer capability not implemented
           73     unsupported combination of traffic
                  parameters
           78     AAL parameters cannot be supported (UNI3.1
                  only)
           91     invalid transit network selection
           93     AAL parameters cannot be supported (UNI3.0
                  only)
        
           NOTE:  For this counter, RELEASE COMPLETE
           messages that are a reply to a previous RELEASE
           message and contain the same cause value, are
           redundant (for counting purposes) and should not
           be counted."
    ::= { atmSigStatEntry 13 }

atmSigEmitClgPtyEvents OBJECT-TYPE
    SYNTAX Counter32
    ACCESS read-only
    STATUS mandatory
    DESCRIPTION
        "Number of Calling Party Events transmitted from this
        interface.  This counter monitors error events that
        occur due to the originating user doing something
        wrong. This counter is incremented when a RELEASE,
        RELEASE COMPLETE (only when not preceded by a RELEASE
        mesg for the same call), ADD PARTY REJECT, or STATUS
        message that contains one of the following cause code
        values is transmitted (Note: These cause values apply
        to both UNI3.0 and UNI3.1):
        
        Cause Value     Meaning
        
           28     invalid number format (address incomplete)
           43     access information discarded
           57     bearer capability not authorized
           65     bearer capability not implemented
           73     unsupported combination of traffic
                  parameters
           78     AAL parameters cannot be supported (UNI3.1
                  only)
           91     invalid transit network selection
           93     AAL parameters cannot be supported (UNI3.0
                  only)
        
           NOTE:  For this counter, RELEASE COMPLETE
           messages that are a reply to a previous RELEASE
           message and contain the same cause value, are
           redundant (for counting purposes) and should not
           be counted."
    ::= { atmSigStatEntry 14 }

atmSigDetectTimerExpireds OBJECT-TYPE
    SYNTAX Counter32
    ACCESS read-only
    STATUS mandatory
    DESCRIPTION
        "Number of Timer Expiries detected on this interface.
        The Timer Expiries Counter provides a count of network
        timer expiries, and to some extent, host or switch
        timer expiries.  The conditions for incrementing this
        counter are:
           - Expiry of any network timer
        
           - Receipt of a RELEASE or RELEASE COMPLETE
             message with Cause #102, 'recovery on
             timer expiry'.
        
        NOTE:  For this counter, RELEASE COMPLETE messages
        that are a reply to a previous RELEASE message and
        contain the same cause value, are redundant (for
        counting purposes) and should not be counted."
    ::= { atmSigStatEntry 15 }

atmSigEmitTimerExpireds OBJECT-TYPE
    SYNTAX Counter32
    ACCESS read-only
    STATUS mandatory
    DESCRIPTION
        "Number of Timer Expiries transmitted from this
        interface.  The Timer Expiries Counter provides a count
        of network timer expiries, and to some extent, host or
        switch timer expiries.  The conditions for incrementing
        this counter are:
           - Expiry of any network timer
        
           - Receipt of a RELEASE or RELEASE COMPLETE
             message with Cause #102, 'recovery on
             timer expiry'.
        
        NOTE:  For this counter, RELEASE COMPLETE messages
        that are a reply to a previous RELEASE message and
        contain the same cause value, are redundant (for
        counting purposes) and should not be counted."
    ::= { atmSigStatEntry 16 }

atmSigDetectRestarts OBJECT-TYPE
    SYNTAX Counter32
    ACCESS read-only
    STATUS mandatory
    DESCRIPTION
        "Number of Restart Activity errors detected on this
        interface.  The Restart Activity Counter provides a
        count of host, switch, or network restart activity.
        This counter is incremented when receiving a RESTART
        message."
    ::= { atmSigStatEntry 17 }

atmSigEmitRestarts OBJECT-TYPE
    SYNTAX Counter32
    ACCESS read-only
    STATUS mandatory
    DESCRIPTION
        "Number of Restart Activity errors transmitted from
        this interface.  The Restart Activity Counter provides
        a count of host, switch, or network restart activity.
        This counter is incremented when transmitting a RESTART
        message."
    ::= { atmSigStatEntry 18 }

atmSigInEstabls OBJECT-TYPE
    SYNTAX Counter32
    ACCESS read-only
    STATUS mandatory
    DESCRIPTION
        "Number of SVC VCCs established at this signalling
        entity for incoming connections."
    ::= { atmSigStatEntry 19 }

atmSigOutEstabls OBJECT-TYPE
    SYNTAX Counter32
    ACCESS read-only
    STATUS mandatory
    DESCRIPTION
        "Number of SVC VCCs established at this signalling
        entity for outgoing connections."
    ::= { atmSigStatEntry 20 }

atmSigSupportTable OBJECT-TYPE
    SYNTAX SEQUENCE OF AtmSigSupportEntry
    ACCESS not-accessible
    STATUS mandatory
    DESCRIPTION
        "This table contains ATM local interface configuration
        parameters, one entry per ATM signalling interface."
    ::= { atm2MIBObjects 4 }

atmSigSupportEntry OBJECT-TYPE
    SYNTAX AtmSigSupportEntry
    ACCESS not-accessible
    STATUS mandatory
    DESCRIPTION
        "This list contains signalling configuration parameters
        and state variables."
    INDEX { ifIndex }
    ::= { atmSigSupportTable 1 }

AtmSigSupportEntry ::= SEQUENCE {
    atmSigSupportClgPtyNumDel INTEGER,
    atmSigSupportClgPtySubAddr INTEGER,
    atmSigSupportCldPtySubAddr INTEGER,
    atmSigSupportHiLyrInfo INTEGER,
    atmSigSupportLoLyrInfo INTEGER,
    atmSigSupportBlliRepeatInd INTEGER,
    atmSigSupportAALInfo INTEGER,
    atmSigSupportPrefCarrier OCTET STRING
    }

atmSigSupportClgPtyNumDel OBJECT-TYPE
    SYNTAX INTEGER {
        enabled(1),
        disabled(2)
        }
    ACCESS read-write
    STATUS mandatory
    DESCRIPTION
        "This object indicates whether the Calling Party Number
        Information Element is transferred to the called party
        address.  The value of this object can be:
          - enabled(1)  This Information Element is transferred
                        to the called party
        
          - disabled(2) This Information Element is NOT
                        transferred to the called party."
    ::= { atmSigSupportEntry 1 }

atmSigSupportClgPtySubAddr OBJECT-TYPE
    SYNTAX INTEGER {
        enabled(1),
        disabled(2)
        }
    ACCESS read-write
    STATUS mandatory
    DESCRIPTION
        "This object indicates whether to accept and transfer
        the Calling Party Subaddress Information Element from
        the calling party to the called party.  Calling party
        subaddress information shall only be transferred to the
        called party if calling party number delivery is
        enabled (i.e., atmSigSupportClgPtyNumDel =
        'enabled(1)'.  The value of this object can be:
          - enabled(1)  This Information Element is transferred
                        to the called party
        
          - disabled(2) This Information Element is NOT
                        transferred to the called party."
    ::= { atmSigSupportEntry 2 }

atmSigSupportCldPtySubAddr OBJECT-TYPE
    SYNTAX INTEGER {
        enabled(1),
        disabled(2)
        }
    ACCESS read-write
    STATUS mandatory
    DESCRIPTION
        "This object indicates whether to accept, transfer, and
        deliver the Called Party Subaddress Information Element
        from the calling party to the called party.  The value
        of this object can be:
          - enabled(1)  This Information Element is transferred
                        to the called party
        
          - disabled(2) This Information Element is NOT
                        transferred to the called party."
    ::= { atmSigSupportEntry 3 }

atmSigSupportHiLyrInfo OBJECT-TYPE
    SYNTAX INTEGER {
        enabled(1),
        disabled(2)
        }
    ACCESS read-write
    STATUS mandatory
    DESCRIPTION
        "This object indicates whether to accept, transfer, and
        deliver the Broadband High Layer Information Element
        from the calling party to the called party.  The value
        of this object can be:
          - enabled(1)  This Information Element is transferred
                        to the called party
        
          - disabled(2) This Information Element is NOT
                        transferred to the called party."
    ::= { atmSigSupportEntry 4 }

atmSigSupportLoLyrInfo OBJECT-TYPE
    SYNTAX INTEGER {
        enabled(1),
        disabled(2)
        }
    ACCESS read-write
    STATUS mandatory
    DESCRIPTION
        "This object indicates whether to accept, transfer, and
        deliver the Broadband Low Layer Information Element
        from the calling party to the called party.  The value
        of this object can be:
          - enabled(1)  This Information Element is transferred
                        to the called party
        
          - disabled(2) This Information Element is NOT
                        transferred to the called party."
    ::= { atmSigSupportEntry 5 }

atmSigSupportBlliRepeatInd OBJECT-TYPE
    SYNTAX INTEGER {
        enabled(1),
        disabled(2)
        }
    ACCESS read-write
    STATUS mandatory
    DESCRIPTION
        "This object indicates whether to accept, transfer, and
        deliver the Broadband Repeat Indicator with two or
        three instances of the Broadband Low Layer Information
        Element for low layer information selection from the
        calling party to the called party.  This object shall
        only be transferred if atmSigSupportLoLyrInfo =
        'enabled(1)'.  The value of this object can be:
          - enabled(1)  This Information Element is transferred
                        to the called party
        
          - disabled(2) This Information Element is NOT
                        transferred to the called party."
    ::= { atmSigSupportEntry 6 }

atmSigSupportAALInfo OBJECT-TYPE
    SYNTAX INTEGER {
        enabled(1),
        disabled(2)
        }
    ACCESS read-write
    STATUS mandatory
    DESCRIPTION
        "This object indicates whether to accept, transfer, and
        deliver the ATM Adaptation Layer Parameters Information
        Element from the calling party to the called party.
        The value of this object can be:
          - enabled(1)  This Information Element is transferred
                        to the called party
        
          - disabled(2) This Information Element is NOT
                        transferred to the called party."
    ::= { atmSigSupportEntry 7 }

atmSigSupportPrefCarrier OBJECT-TYPE
    SYNTAX OCTET STRING
    ACCESS read-write
    STATUS mandatory
    DESCRIPTION
        "This parameter identifies the carrier to which
        intercarrier calls originated from this interface are
        routed when transit network selection information is
        not provided by the calling party.  If a Carrier
        Identification Code (CIC) is used the parameter shall
        contain the CIC.  For three-digit CICs, the first octet
        shall be '0' and the CIC is contained in the three
        following octets.  If the preferred carrier feature is
        not supported the value is a zero-length string."
    ::= { atmSigSupportEntry 8 }

atmSigDescrParamTable OBJECT-TYPE
    SYNTAX SEQUENCE OF AtmSigDescrParamEntry
    ACCESS not-accessible
    STATUS mandatory
    DESCRIPTION
        "A table contains signalling capabilities of VCLs
        except the Traffic Descriptor.  Traffic
        descriptors are described in the
        atmTrafficDescrParamTable."
    REFERENCE
        "ATM Forum User-Network Interface Specification,
        Version 3.1, Section 5.4.5 Variable Length
        Information Elements."
    ::= { atm2MIBObjects 5 }

atmSigDescrParamEntry OBJECT-TYPE
    SYNTAX AtmSigDescrParamEntry
    ACCESS not-accessible
    STATUS mandatory
    DESCRIPTION
        "Each entry in this table represents a set of
        signalling capabilities that can be applied to a
        VCL. There is no requirement for unique entries,
        except that the index must be unique.  Objects
        atmSigDescrParamRowStatus is required during
        creation."
    INDEX { atmSigDescrParamIndex }
    ::= { atmSigDescrParamTable 1 }

AtmSigDescrParamEntry ::= SEQUENCE {
    atmSigDescrParamIndex AtmSigDescrParamIndex,
    atmSigDescrParamAalType INTEGER,
    atmSigDescrParamAalSscsType INTEGER,
    atmSigDescrParamBhliType INTEGER,
    atmSigDescrParamBhliInfo OCTET STRING,
    atmSigDescrParamBbcConnConf INTEGER,
    atmSigDescrParamBlliLayer2 INTEGER,
    atmSigDescrParamBlliLayer3 INTEGER,
    atmSigDescrParamBlliPktSize INTEGER,
    atmSigDescrParamBlliSnapId INTEGER,
    atmSigDescrParamBlliOuiPid OCTET STRING,
    atmSigDescrParamRowStatus RowStatus
    }

atmSigDescrParamIndex OBJECT-TYPE
    SYNTAX AtmSigDescrParamIndex
--    Rsyntax INTEGER(0..2147483647)
    ACCESS not-accessible
    STATUS mandatory
    DESCRIPTION
        "The value of this object is used by the
        atmVclExtTable to identify a row in this table."
    ::= { atmSigDescrParamEntry 1 }

atmSigDescrParamAalType OBJECT-TYPE
    SYNTAX INTEGER {
        other(1),
        aal1(2),
        aal34(3),
        aal5(4),
        userDefined(5)
        }
    ACCESS read-write
    STATUS mandatory
    DESCRIPTION
        "The AAL type. The value of this object is set to
        other(1) when not defined."
    DEFVAL { other }
    ::= { atmSigDescrParamEntry 2 }

atmSigDescrParamAalSscsType OBJECT-TYPE
    SYNTAX INTEGER {
        other(1),
        assured(2),
        nonassured(3),
        frameRelay(4),
        null(5)
        }
    ACCESS read-write
    STATUS mandatory
    DESCRIPTION
        "The SSCS type used by this entry."
    DEFVAL { other }
    ::= { atmSigDescrParamEntry 3 }

atmSigDescrParamBhliType OBJECT-TYPE
    SYNTAX INTEGER {
        other(1),
        iso(2),
        user(3),
        hiProfile(4),
        vendorSpecific(5)
        }
    ACCESS read-write
    STATUS mandatory
    DESCRIPTION
        "The Broadband high layer type."
    DEFVAL { other }
    ::= { atmSigDescrParamEntry 4 }

atmSigDescrParamBhliInfo OBJECT-TYPE
    SYNTAX OCTET STRING(SIZE(0..7))
    ACCESS read-write
    STATUS mandatory
    DESCRIPTION
        "The Broadband high layer information.  When
        atmSigDescrParamBhliType is set to iso(2), the
        value of this object is a zero length string.
        When atmSigDescrParamBhliType is set to
        hiProfile(4), the value of this object is a length
        of 4 octet string containing user to user profile
        identifier.  When atmSigDescrParamBhliType is set
        to    vendorSpecific(4), the value of this object
        is a length of 7 octet string.  The most
        significant 3 octets consist of a globally-
        administered OUI, the least significant 4 octets
        are the vender administered application OUI."
    DEFVAL { ''h }
    ::= { atmSigDescrParamEntry 5 }

atmSigDescrParamBbcConnConf OBJECT-TYPE
    SYNTAX INTEGER {
        ptp(1),
        ptmp(2)
        }
    ACCESS read-write
    STATUS mandatory
    DESCRIPTION
        "The Broadband bearer capability user plane
        connection configuration parameter."
    ::= { atmSigDescrParamEntry 6 }

atmSigDescrParamBlliLayer2 OBJECT-TYPE
    SYNTAX INTEGER {
        other(1),
        iso1745(2),
        q921(3),
        x25linklayer(4),
        x25multilink(5),
        lapb(6),
        hdlcArm(7),
        hdlcNrm(8),
        hdlcAbm(9),
        iso88022(10),
        x75slp(11),
        q922(12),
        userDef(13),
        iso7776(14)
        }
    ACCESS read-write
    STATUS mandatory
    DESCRIPTION
        "The Broadband low layer information, protocol
        type of layer 2.  The value of this object is
        other(1) if layer 2 protocol is not used."
    DEFVAL { other }
    ::= { atmSigDescrParamEntry 7 }

atmSigDescrParamBlliLayer3 OBJECT-TYPE
    SYNTAX INTEGER {
        other(1),
        x25pkt(2),
        isoiec8208(3),
        x223iso8878(4),
        isoiec8473(5),
        t70(6),
        tr9577(7),
        userDef(8)
        }
    ACCESS read-write
    STATUS mandatory
    DESCRIPTION
        "The Broadband low layer information, protocol
        type of layer 3.  The value of this object is
        other(1) if layer 3 protocol is not used."
    DEFVAL { other }
    ::= { atmSigDescrParamEntry 8 }

atmSigDescrParamBlliPktSize OBJECT-TYPE
    SYNTAX INTEGER {
        other(1),
        s16(2),
        s32(3),
        s64(4),
        s128(5),
        s256(6),
        s512(7),
        s1024(8),
        s2048(9),
        s4096(10)
        }
    ACCESS read-write
    STATUS mandatory
    DESCRIPTION
        "The default packet size defined in B-LLI."
    DEFVAL { other }
    ::= { atmSigDescrParamEntry 9 }

atmSigDescrParamBlliSnapId OBJECT-TYPE
    SYNTAX INTEGER {
        other(1),
        true(2),
        false(3)
        }
    ACCESS read-write
    STATUS mandatory
    DESCRIPTION
        "The SNAP ID used for Broadband low layer protocol
        layer 3.  The value of this object is other(1) if
        atmSigDescrParamBlliLayer3 is set to other(1)."
    DEFVAL { other }
    ::= { atmSigDescrParamEntry 10 }

atmSigDescrParamBlliOuiPid OBJECT-TYPE
    SYNTAX OCTET STRING(SIZE(0..5))
    ACCESS read-write
    STATUS mandatory
    DESCRIPTION
        "The OUI/PID encoding for Broadband low layer
        protocol layer 3.  The value of this object is a
        zero length string if atmSigDescrParamBlliLayer3
        is set to none(1).  When used, it is always 5
        octets with the most significant octet as the OUI
        Octet 1 and the least significant octet as the PID
        Octet 2."
    DEFVAL { ''h }
    ::= { atmSigDescrParamEntry 11 }

atmSigDescrParamRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create and delete rows in
        the atmSigDescrParamTable. Writable values are:
        -'createAndWait' which allows manager to create an
        entry first and fill in the parameters later.
        -'active' which allows manager to set the entry to
        be available to users.  -'destroy' which allows
        manager to delete an entry from this table.
        Readable values are: -'createAndWait' which means
        the entry is created but not available to be used.
        -'active' means it is active and ready to be used
        by agent or manager."
    ::= { atmSigDescrParamEntry 12 }

atmIfRegisteredAddrTable OBJECT-TYPE
    SYNTAX SEQUENCE OF AtmIfRegisteredAddrEntry
    ACCESS not-accessible
    STATUS mandatory
    DESCRIPTION
        "This table contains a list of ATM addresses that can
        be used for calls to and from a given interface by a
        switch or service.  The ATM addresses are either
        registered by the endsystem via ILMI or statically
        configured.  This table does not expose PNNI
        reachability information.  ILMI registered addresses
        cannot be deleted using this table.  This table only
        applies to switches and network services."
    ::= { atm2MIBObjects 6 }

atmIfRegisteredAddrEntry OBJECT-TYPE
    SYNTAX AtmIfRegisteredAddrEntry
    ACCESS not-accessible
    STATUS mandatory
    DESCRIPTION
        "An entry in the ATM Interface Registered Address
        table."
    INDEX { ifIndex, atmIfRegAddrAddress }
    ::= { atmIfRegisteredAddrTable 1 }

AtmIfRegisteredAddrEntry ::= SEQUENCE {
    atmIfRegAddrAddress AtmAddr,
    atmIfRegAddrAddressSource INTEGER,
    atmIfRegAddrOrgScope INTEGER,
    atmIfRegAddrRowStatus RowStatus
    }

atmIfRegAddrAddress OBJECT-TYPE
    SYNTAX AtmAddr
--    Rsyntax OCTET STRING(SIZE(0 | 8 | 20))
    ACCESS not-accessible
    STATUS mandatory
    DESCRIPTION
        "An address registered for a given switch or service
        interface."
    ::= { atmIfRegisteredAddrEntry 1 }

atmIfRegAddrAddressSource OBJECT-TYPE
    SYNTAX INTEGER {
        other(1),
        static(2),
        dynamic(3)
        }
    ACCESS read-only
    STATUS mandatory
    DESCRIPTION
        "The type of address source for a given ATM Address.
        The value dynamic(3) is indicated when ILMI is used."
    ::= { atmIfRegisteredAddrEntry 2 }

atmIfRegAddrOrgScope OBJECT-TYPE
    SYNTAX INTEGER {
        localNetwork(1),
        localNetworkPlusOne(2),
        localNetworkPlusTwo(3),
        siteMinusOne(4),
        intraSite(5),
        sitePlusOne(6),
        organizationMinusOne(7),
        intraOrganization(8),
        organizationPlusOne(9),
        communityMinusOne(10),
        intraCommunity(11),
        communityPlusOne(12),
        regional(13),
        interRegional(14),
        global(15)
        }
    ACCESS read-write
    STATUS mandatory
    DESCRIPTION
        "This object indicates the organizational scope for the
        referenced address.  The information of the referenced
        address shall not be distributed outside the indicated
        scope.   Refer to Annex 5.3 of ATM Forum UNI Signalling
        4.0 for guidelines regarding the use of organizational
        scopes.
        
        This value cannot be configured for ILMI-registered
        addresses.
        The default values for organizational scope are
        localNetwork(1) for ATM group addresses, and global(15)
        for individual addresses."
    ::= { atmIfRegisteredAddrEntry 3 }

atmIfRegAddrRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create and delete rows in the
        atmIfRegisteredAddrTable.  Rows created dynamically
        (e.g., ILMI-registered addresses) cannot be deleted
        using this object."
    ::= { atmIfRegisteredAddrEntry 4 }

atmVclAddrTable OBJECT-TYPE
    SYNTAX SEQUENCE OF AtmVclAddrEntry
    ACCESS not-accessible
    STATUS mandatory
    DESCRIPTION
        "This table provides a mapping between the
        atmVclTable and the ATM called party/calling party
        address. This table can be used to retrieve the
        calling party and called party ATM address pair
        for a given Vcl. Note that there can be more than
        one pair of calling party and called party ATM
        addresses for a VCL in a point to multi-point
        call."
    ::= { atm2MIBObjects 7 }

atmVclAddrEntry OBJECT-TYPE
    SYNTAX AtmVclAddrEntry
    ACCESS not-accessible
    STATUS mandatory
    DESCRIPTION
        "Each entry in this table represents a binding
        between a VCL and an ATM address associated with
        this call. This ATM address can be either the
        called party address or the calling party address.
        There can be more than one pair of calling/called
        party ATM addresses associated with the VCL entry
        for point to multi-point calls. Objects
        atmVclAddrAddr, atmVclAddrType, and
        atmVclAddrRowStatus are required during row
        creation."
    INDEX { ifIndex, atmVclVpi, atmVclVci, atmVclAddrAddr }
    ::= { atmVclAddrTable 1 }

AtmVclAddrEntry ::= SEQUENCE {
    atmVclAddrAddr AtmAddr,
    atmVclAddrType INTEGER,
    atmVclAddrRowStatus RowStatus
    }

atmVclAddrAddr OBJECT-TYPE
    SYNTAX AtmAddr
--    Rsyntax OCTET STRING(SIZE(0 | 8 | 20))
    ACCESS not-accessible
    STATUS mandatory
    DESCRIPTION
        "An ATM address on one end of the VCL.  For SVCs,
        the agent supplies the value of this object at
        creation time.  For PVCs, manager can supply the
        value of this object during or after the PVC
        creation."
    ::= { atmVclAddrEntry 1 }

atmVclAddrType OBJECT-TYPE
    SYNTAX INTEGER {
        callingParty(1),
        calledParty(2)
        }
    ACCESS read-write
    STATUS mandatory
    DESCRIPTION
        "The type of ATM Address represented by the object
        atmVclAddrAddr.  Choices are either the calling
        party ATM address or the called party ATM
        address."
    ::= { atmVclAddrEntry 2 }

atmVclAddrRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or destroy an entry
        from this table."
    ::= { atmVclAddrEntry 3 }

atmAddrVclTable OBJECT-TYPE
    SYNTAX SEQUENCE OF AtmAddrVclEntry
    ACCESS not-accessible
    STATUS mandatory
    DESCRIPTION
        "This table provides an alternative way to
        retrieve the atmVclTable.  This table can be used
        to retrieve the indexing to the atmVclTable by an
        ATM address."
    ::= { atm2MIBObjects 8 }

atmAddrVclEntry OBJECT-TYPE
    SYNTAX AtmAddrVclEntry
    ACCESS not-accessible
    STATUS mandatory
    DESCRIPTION
        "Each entry in this table represents an entry in
        the atmVclTable of the ATM MIB [1] by it's ATM
        address.  The ATM address is either the calling or
        called party ATM address of the call.  Entries in
        this table are read only.  They show up when
        entries are created in the atmVclAddrTable."
    INDEX { atmVclAddrAddr, atmAddrVclAtmIfIndex, atmAddrVclVpi, atmAddrVclVci }
    ::= { atmAddrVclTable 1 }

AtmAddrVclEntry ::= SEQUENCE {
    atmAddrVclAtmIfIndex InterfaceIndex,
    atmAddrVclVpi AtmVpIdentifier,
    atmAddrVclVci AtmVcIdentifier,
    atmAddrVclAddrType INTEGER
    }

atmAddrVclAtmIfIndex OBJECT-TYPE
    SYNTAX InterfaceIndex
--    Rsyntax Integer32
    ACCESS not-accessible
    STATUS mandatory
    DESCRIPTION
        "The interface index of the ATM interface where
        this VCL pertains to.  This object combined with
        the atmAddrVclVpi and atmAddrVclVci objects serves
        as an index to the atmVclTable."
    ::= { atmAddrVclEntry 1 }

atmAddrVclVpi OBJECT-TYPE
    SYNTAX AtmVpIdentifier
--    Rsyntax INTEGER(0..4095)
    ACCESS not-accessible
    STATUS mandatory
    DESCRIPTION
        "The VPI value of the VCL.  This object combined
        with the atmAddrVclAtmIfIndex and atmAddrVclVci
        objects serves as an index to the atmVclTable."
    ::= { atmAddrVclEntry 2 }

atmAddrVclVci OBJECT-TYPE
    SYNTAX AtmVcIdentifier
--    Rsyntax INTEGER(0..65535)
    ACCESS not-accessible
    STATUS mandatory
    DESCRIPTION
        "The VCI value of the VCL.  This object combined
        with the atmAddrVclAtmIfIndex and atmAddrVclVpi
        objects serves as an index to the atmVclTable."
    ::= { atmAddrVclEntry 3 }

atmAddrVclAddrType OBJECT-TYPE
    SYNTAX INTEGER {
        callingParty(1),
        calledParty(2)
        }
    ACCESS read-only
    STATUS mandatory
    DESCRIPTION
        "The type of ATM Address represented by the object
        atmVclAddrAddr.  Choices are either calling party
        address or called party address."
    ::= { atmAddrVclEntry 4 }

atmVplStatTable OBJECT-TYPE
    SYNTAX SEQUENCE OF AtmVplStatEntry
    ACCESS not-accessible
    STATUS mandatory
    DESCRIPTION
        "This table contains all statistic counters per
        VPL.  It is used to monitor the usage of the VPL
        in terms of incoming cells and outgoing cells."
    ::= { atm2MIBObjects 9 }

atmVplStatEntry OBJECT-TYPE
    SYNTAX AtmVplStatEntry
    ACCESS not-accessible
    STATUS mandatory
    DESCRIPTION
        "Each entry in this table represents a VPL."
    INDEX { ifIndex, atmVplVpi }
    ::= { atmVplStatTable 1 }

AtmVplStatEntry ::= SEQUENCE {
    atmVplStatTotalCellIns Counter32,
    atmVplStatClp0CellIns Counter32,
    atmVplStatTotalDiscards Counter32,
    atmVplStatClp0Discards Counter32,
    atmVplStatTotalCellOuts Counter32,
    atmVplStatClp0CellOuts Counter32,
    atmVplStatTaggedOuts Counter32
    }

atmVplStatTotalCellIns OBJECT-TYPE
    SYNTAX Counter32
    ACCESS read-only
    STATUS mandatory
    DESCRIPTION
        "The total number of valid ATM cells received by
        this VPL including both CLP=0 and CLP=1 cells.
        The cells are counted prior to the application of
        the traffic policing."
    ::= { atmVplStatEntry 1 }

atmVplStatClp0CellIns OBJECT-TYPE
    SYNTAX Counter32
    ACCESS read-only
    STATUS mandatory
    DESCRIPTION
        "The number of valid ATM cells received by this
        VPL with CLP=0.  The cells are counted prior to
        the application of the traffic policing."
    ::= { atmVplStatEntry 2 }

atmVplStatTotalDiscards OBJECT-TYPE
    SYNTAX Counter32
    ACCESS read-only
    STATUS mandatory
    DESCRIPTION
        "The total number of valid ATM cells discarded by
        the traffic policing entity. This includes cells
        orginally received with CLP=0 and CLP=1."
    ::= { atmVplStatEntry 3 }

atmVplStatClp0Discards OBJECT-TYPE
    SYNTAX Counter32
    ACCESS read-only
    STATUS mandatory
    DESCRIPTION
        "The total number of valid ATM cells received with
        CLP=0 an  discarded by the traffic policing
        entity."
    ::= { atmVplStatEntry 4 }

atmVplStatTotalCellOuts OBJECT-TYPE
    SYNTAX Counter32
    ACCESS read-only
    STATUS mandatory
    DESCRIPTION
        "The total number of valid ATM cells transmitted
        by this VPL.  This includes both CLP=0 and CLP=1
        cells."
    ::= { atmVplStatEntry 5 }

atmVplStatClp0CellOuts OBJECT-TYPE
    SYNTAX Counter32
    ACCESS read-only
    STATUS mandatory
    DESCRIPTION
        "The total number of valid ATM cells transmitted
        with CLP=0 by this VPL."
    ::= { atmVplStatEntry 6 }

atmVplStatTaggedOuts OBJECT-TYPE
    SYNTAX Counter32
    ACCESS read-only
    STATUS mandatory
    DESCRIPTION
        "The total number of valid ATM cells tagged by the
        traffic policing entity from CLP=0 to CLP=1 and
        transmitted by this VPL."
    ::= { atmVplStatEntry 7 }

atmVplLogicalPortTable OBJECT-TYPE
    SYNTAX SEQUENCE OF AtmVplLogicalPortEntry
    ACCESS not-accessible
    STATUS mandatory
    DESCRIPTION
        "Indicates whether the VPL is an ATM Logical Port
        interface (ifType=80)."
    ::= { atm2MIBObjects 10 }

atmVplLogicalPortEntry OBJECT-TYPE
    SYNTAX AtmVplLogicalPortEntry
    ACCESS not-accessible
    STATUS mandatory
    DESCRIPTION
        "An entry with information about the ATM Logical
        Port interface."
    INDEX { ifIndex, atmVplVpi }
-- Augments atmVplEntry FROM ATM-MIB
    ::= { atmVplLogicalPortTable 1 }

AtmVplLogicalPortEntry ::= SEQUENCE {
    atmVplLogicalPortDef INTEGER,
    atmVplLogicalPortIndex InterfaceIndex
    }

atmVplLogicalPortDef OBJECT-TYPE
    SYNTAX INTEGER {
        notLogicalIf(1),
        isLogicalIf(2)
        }
    ACCESS read-write
    STATUS mandatory
    DESCRIPTION
        "Indicates whether the VPC at this VPL interface
        is an ATM Logical Port interface."
    DEFVAL { notLogicalIf }
    ::= { atmVplLogicalPortEntry 1 }

atmVplLogicalPortIndex OBJECT-TYPE
    SYNTAX InterfaceIndex
--    Rsyntax Integer32
    ACCESS read-only
    STATUS mandatory
    DESCRIPTION
        "The ifTable index of the ATM logical port
        interface associated with this VPL. Only valid if
        the value of atmVplLogicalPortDef is isLogicalIf,
        and the VPL row is active."
    ::= { atmVplLogicalPortEntry 2 }

atmVclStatTable OBJECT-TYPE
    SYNTAX SEQUENCE OF AtmVclStatEntry
    ACCESS not-accessible
    STATUS mandatory
    DESCRIPTION
        "This table contains all statistic counters per
        VCL.  It is used to monitor the usage of the VCL
        in terms of incoming cells and outgoing cells."
    ::= { atm2MIBObjects 11 }

atmVclStatEntry OBJECT-TYPE
    SYNTAX AtmVclStatEntry
    ACCESS not-accessible
    STATUS mandatory
    DESCRIPTION
        "Each entry in this table represents a VCL."
    INDEX { ifIndex, atmVclVpi, atmVclVci }
    ::= { atmVclStatTable 1 }

AtmVclStatEntry ::= SEQUENCE {
    atmVclStatTotalCellIns Counter32,
    atmVclStatClp0CellIns Counter32,
    atmVclStatTotalDiscards Counter32,
    atmVclStatClp0Discards Counter32,
    atmVclStatTotalCellOuts Counter32,
    atmVclStatClp0CellOuts Counter32,
    atmVclStatTaggedOuts Counter32
    }

atmVclStatTotalCellIns OBJECT-TYPE
    SYNTAX Counter32
    ACCESS read-only
    STATUS mandatory
    DESCRIPTION
        "The total number of valid ATM cells received by
        this VCL including both CLP=0 and CLP=1 cells.
        The cells are counted prior to the application of
        the traffic policing."
    ::= { atmVclStatEntry 1 }

atmVclStatClp0CellIns OBJECT-TYPE
    SYNTAX Counter32
    ACCESS read-only
    STATUS mandatory
    DESCRIPTION
        "The number of valid ATM cells received by this
        VCL with CLP=0.  The cells are counted prior to
        the application of the traffic policing."
    ::= { atmVclStatEntry 2 }

atmVclStatTotalDiscards OBJECT-TYPE
    SYNTAX Counter32
    ACCESS read-only
    STATUS mandatory
    DESCRIPTION
        "The total number of valid ATM cells discarded by
        the traffic policing entity. This includes cells
        orginally received with CLP=0 and CLP=1."
    ::= { atmVclStatEntry 3 }

atmVclStatClp0Discards OBJECT-TYPE
    SYNTAX Counter32
    ACCESS read-only
    STATUS mandatory
    DESCRIPTION
        "The total number of valid ATM cells received with
        CLP=0 an  discarded by the traffic policing
        entity."
    ::= { atmVclStatEntry 4 }

atmVclStatTotalCellOuts OBJECT-TYPE
    SYNTAX Counter32
    ACCESS read-only
    STATUS mandatory
    DESCRIPTION
        "The total number of valid ATM cells transmitted
        by this VCL.  This includes both CLP=0 and CLP=1
        cells."
    ::= { atmVclStatEntry 5 }

atmVclStatClp0CellOuts OBJECT-TYPE
    SYNTAX Counter32
    ACCESS read-only
    STATUS mandatory
    DESCRIPTION
        "The total number of valid ATM cells transmitted
        with CLP=0 by this VCL."
    ::= { atmVclStatEntry 6 }

atmVclStatTaggedOuts OBJECT-TYPE
    SYNTAX Counter32
    ACCESS read-only
    STATUS mandatory
    DESCRIPTION
        "The total number of valid ATM cells tagged by the
        traffic policing entity from CLP=0 to CLP=1 and
        transmitted by this VCL."
    ::= { atmVclStatEntry 7 }

atmAal5VclStatTable OBJECT-TYPE
    SYNTAX SEQUENCE OF AtmAal5VclStatEntry
    ACCESS not-accessible
    STATUS mandatory
    DESCRIPTION
        "This table provides a collection of objects
        providing AAL5 configuration and performance
        statistics of a VCL."
    ::= { atm2MIBObjects 12 }

atmAal5VclStatEntry OBJECT-TYPE
    SYNTAX AtmAal5VclStatEntry
    ACCESS not-accessible
    STATUS mandatory
    DESCRIPTION
        "Each entry in this table represents a VCL."
    INDEX { ifIndex, atmVclVpi, atmVclVci }
    ::= { atmAal5VclStatTable 1 }

AtmAal5VclStatEntry ::= SEQUENCE {
    atmAal5VclInPkts Counter32,
    atmAal5VclOutPkts Counter32,
    atmAal5VclInOctets Counter32,
    atmAal5VclOutOctets Counter32
    }

atmAal5VclInPkts OBJECT-TYPE
    SYNTAX Counter32
    ACCESS read-only
    STATUS mandatory
    DESCRIPTION
        "The number of AAL5 CPCS PDUs received on the AAL5
        VCC at the interface identified by the ifIndex."
    ::= { atmAal5VclStatEntry 1 }

atmAal5VclOutPkts OBJECT-TYPE
    SYNTAX Counter32
    ACCESS read-only
    STATUS mandatory
    DESCRIPTION
        "The number of AAL5 CPCS PDUs transmitted on the
        AAL5 VCC at the interface identified by the
        ifIndex."
    ::= { atmAal5VclStatEntry 2 }

atmAal5VclInOctets OBJECT-TYPE
    SYNTAX Counter32
    ACCESS read-only
    STATUS mandatory
    DESCRIPTION
        "The number of octets contained in AAL5 CPCS PDUs
        received on the AAL5 VCC at the interface
        identified by the ifIndex."
    ::= { atmAal5VclStatEntry 3 }

atmAal5VclOutOctets OBJECT-TYPE
    SYNTAX Counter32
    ACCESS read-only
    STATUS mandatory
    DESCRIPTION
        "The number of octets contained in AAL5 CPCS PDUs
        transmitted on the AAL5 VCC at the interface
        identified by the ifIndex."
    ::= { atmAal5VclStatEntry 4 }

atmVclGenTable OBJECT-TYPE
    SYNTAX SEQUENCE OF AtmVclGenEntry
    ACCESS not-accessible
    STATUS mandatory
    DESCRIPTION
        "General Information for each VC."
    ::= { atm2MIBObjects 13 }

atmVclGenEntry OBJECT-TYPE
    SYNTAX AtmVclGenEntry
    ACCESS not-accessible
    STATUS mandatory
    DESCRIPTION
        "An entry with general information
        about the ATM VC."
    INDEX { ifIndex, atmVclVpi, atmVclVci }
-- Augments atmVclEntry FROM ATM-MIB
    ::= { atmVclGenTable 1 }

AtmVclGenEntry ::= SEQUENCE {
    atmVclGenSigDescrIndex AtmSigDescrParamIndex
    }

atmVclGenSigDescrIndex OBJECT-TYPE
    SYNTAX AtmSigDescrParamIndex
--    Rsyntax INTEGER(0..2147483647)
    ACCESS read-write
    STATUS mandatory
    DESCRIPTION
        "The value of this object identifies the
        row in the ATM Signalling Descriptor
        Parameter Table which applies to this
        VCL."
    ::= { atmVclGenEntry 1 }

atmInterfaceExtTable OBJECT-TYPE
    SYNTAX SEQUENCE OF AtmInterfaceExtEntry
    ACCESS not-accessible
    STATUS mandatory
    DESCRIPTION
        "This table contains ATM interface
        configuration and monitoring information not
        defined in the atmInterfaceConfTable from the
        ATM-MIB [1].  This includes the type of
        connection setup procedures, ILMI information,
        and information on the VPI/VCI range."
    ::= { atm2MIBObjects 14 }

atmInterfaceExtEntry OBJECT-TYPE
    SYNTAX AtmInterfaceExtEntry
    ACCESS not-accessible
    STATUS mandatory
    DESCRIPTION
        "An entry extends the
        atmInterfaceConfEntry defined in [1].  Each
        entry corresponds to an ATM
        interface."
    INDEX { ifIndex }
-- Augments atmInterfaceConfEntry FROM ATM-MIB
    ::= { atmInterfaceExtTable 1 }

AtmInterfaceExtEntry ::= SEQUENCE {
    atmIntfConfigType AtmInterfaceType,
    atmIntfActualType AtmInterfaceType,
    atmIntfConfigSide INTEGER,
    atmIntfActualSide INTEGER,
    atmIntfIlmiFsmState INTEGER,
    atmIntfIlmiEstablishConPollIntvl Integer32,
    atmIntfIlmiCheckConPollIntvl Integer32,
    atmIntfIlmiConPollInactFactor Integer32,
    atmIntfIlmiPublicPrivateIndctr INTEGER,
    atmInterfaceConfMaxSvpcVpi INTEGER,
    atmInterfaceCurrentMaxSvpcVpi INTEGER,
    atmInterfaceConfMaxSvccVpi INTEGER,
    atmInterfaceCurrentMaxSvccVpi INTEGER,
    atmInterfaceConfMinSvccVci INTEGER,
    atmInterfaceCurrentMinSvccVci INTEGER,
    atmIntfSigVccRxTrafficDescrIndex AtmTrafficDescrParamIndex,
    atmIntfSigVccTxTrafficDescrIndex AtmTrafficDescrParamIndex,
    atmIntfPvcFailures Counter32,
    atmIntfCurrentlyFailingPVpls Gauge32,
    atmIntfCurrentlyFailingPVcls Gauge32,
    atmIntfPvcFailuresTrapEnable TruthValue,
    atmIntfPvcNotificationInterval INTEGER
    }

atmIntfConfigType OBJECT-TYPE
    SYNTAX AtmInterfaceType
--    Rsyntax INTEGER {
--        other(1),
--        autoConfig(2),
--        ituDss2(3),
--        atmfUni3Dot0(4),
--        atmfUni3Dot1(5),
--        atmfUni4Dot0(6),
--        atmfIispUni3Dot0(7),
--        atmfIispUni3Dot1(8),
--        atmfIispUni4Dot0(9),
--        atmfPnni1Dot0(10),
--        atmfBici2Dot0(11),
--        atmfUniPvcOnly(12),
--        atmfNniPvcOnly(13)
--        }
    ACCESS read-write
    STATUS mandatory
    DESCRIPTION
        "The type of connection setup procedures
        configured for the ATM interface.  Setting this
        variable to a value of 'other' is not allowed."
    DEFVAL { autoConfig }
    ::= { atmInterfaceExtEntry 1 }

atmIntfActualType OBJECT-TYPE
    SYNTAX AtmInterfaceType
--    Rsyntax INTEGER {
--        other(1),
--        autoConfig(2),
--        ituDss2(3),
--        atmfUni3Dot0(4),
--        atmfUni3Dot1(5),
--        atmfUni4Dot0(6),
--        atmfIispUni3Dot0(7),
--        atmfIispUni3Dot1(8),
--        atmfIispUni4Dot0(9),
--        atmfPnni1Dot0(10),
--        atmfBici2Dot0(11),
--        atmfUniPvcOnly(12),
--        atmfNniPvcOnly(13)
--        }
    ACCESS read-only
    STATUS mandatory
    DESCRIPTION
        "The type of connection setup procedures
        currently being used on the interface.  This may
        reflect a manually configured value for the
        interface type, or may be determined by other
        means such as auto-configuration.  A value of
        `autoConfig' indicates that auto-configuration
        was requested but has not yet been completed."
    ::= { atmInterfaceExtEntry 2 }

atmIntfConfigSide OBJECT-TYPE
    SYNTAX INTEGER {
        other(1),
        user(2),
        network(3)
        }
    ACCESS read-write
    STATUS mandatory
    DESCRIPTION
        "The configured role of the managed entity as one
        side of the ATM interface.  This value does not
        apply when the object atmIntfConfigType is set to
        `autoConfig', `atmfPnni1Dot0', or
        `atmfBici2Dot0'."
    ::= { atmInterfaceExtEntry 3 }

atmIntfActualSide OBJECT-TYPE
    SYNTAX INTEGER {
        other(1),
        user(2),
        network(3),
        symmetric(4)
        }
    ACCESS read-only
    STATUS mandatory
    DESCRIPTION
        "The current role used by the managed entity to
        represent one side of the ATM interface."
    ::= { atmInterfaceExtEntry 4 }

atmIntfIlmiFsmState OBJECT-TYPE
    SYNTAX INTEGER {
        stopped(1),
        linkFailing(2),
        establishing(3),
        configuring(4),
        retrievingNetworkPrefixes(5),
        registeringNetworkPrefixes(6),
        retrievingAddresses(7),
        registeringAddresses(8),
        verifying(9)
        }
    ACCESS read-only
    STATUS mandatory
    DESCRIPTION
        "Indicates the state of the ILMI Finite State Machine
        associated with this interface."
    REFERENCE
        "ATM Forum ILMI 4.0 Specification, Appendix 1"
    ::= { atmInterfaceExtEntry 7 }

atmIntfIlmiEstablishConPollIntvl OBJECT-TYPE
    SYNTAX Integer32
--  SYNTAX Integer32(1..65535)
--  Units
--    seconds
    ACCESS read-write
    STATUS mandatory
    DESCRIPTION
        "The amount of time S between successive transmissions
        of ILMI messages on this interface for the purpose of
        detecting establishment of ILMI connectivity."
    REFERENCE
        "ATM Forum ILMI 4.0 Section 8.3.1"
    DEFVAL { 1 }
    ::= { atmInterfaceExtEntry 8 }

atmIntfIlmiCheckConPollIntvl OBJECT-TYPE
    SYNTAX Integer32
--  SYNTAX Integer32(0..65535)
--  Units
--    seconds
    ACCESS read-write
    STATUS mandatory
    DESCRIPTION
        "The amount of time T between successive transmissions
        of ILMI messages on this interface for the purpose of
        detecting loss of ILMI connectivity.  The distinguished
        value zero disables ILMI connectivity procedures on
        this interface."
    REFERENCE
        "ATM Forum ILMI 4.0 Section 8.3.1"
    DEFVAL { 5 }
    ::= { atmInterfaceExtEntry 9 }

atmIntfIlmiConPollInactFactor OBJECT-TYPE
    SYNTAX Integer32
--  SYNTAX Integer32(0..65535)
    ACCESS read-write
    STATUS mandatory
    DESCRIPTION
        "The number K of consecutive polls on this interface
        for which no ILMI response message is received before
        ILMI connectivity is declared lost."
    REFERENCE
        "ATM Forum ILMI 4.0 Section 8.3.1"
    DEFVAL { 4 }
    ::= { atmInterfaceExtEntry 10 }

atmIntfIlmiPublicPrivateIndctr OBJECT-TYPE
    SYNTAX INTEGER {
        other(1),
        public(2),
        private(3)
        }
    ACCESS read-write
    STATUS mandatory
    DESCRIPTION
        "Specifies whether this end of the interface is
        advertised in ILMI as a device of the `public' or
        `private' type."
    DEFVAL { private }
    ::= { atmInterfaceExtEntry 11 }

atmInterfaceConfMaxSvpcVpi OBJECT-TYPE
    SYNTAX INTEGER(0..4095)
    ACCESS read-write
    STATUS mandatory
    DESCRIPTION
        "The maximum VPI that the signalling stack on the ATM
        interface is configured to support for allocation to
        switched virtual path connections."
    ::= { atmInterfaceExtEntry 12 }

atmInterfaceCurrentMaxSvpcVpi OBJECT-TYPE
    SYNTAX INTEGER(0..4095)
    ACCESS read-only
    STATUS mandatory
    DESCRIPTION
        "The maximum VPI that the signalling stack on the ATM
        interface may currently allocate to switched virtual
        path connections.  This value is the minimum of
        atmInterfaceConfMaxSvpcVpi, and the
        atmInterfaceMaxSvpcVpi of the interface's UNI/NNI peer.
        
        If the interface does not negotiate with its peer to
        determine the maximum VPI that can be allocated to
        SVPCs on the interface, then the value of this object
        must equal atmInterfaceConfMaxSvpcVpi. "
    ::= { atmInterfaceExtEntry 13 }

atmInterfaceConfMaxSvccVpi OBJECT-TYPE
    SYNTAX INTEGER(0..4095)
    ACCESS read-write
    STATUS mandatory
    DESCRIPTION
        "The maximum VPI that the signalling stack on the ATM
        interface is configured to support for allocation to
        switched virtual channel connections."
    ::= { atmInterfaceExtEntry 14 }

atmInterfaceCurrentMaxSvccVpi OBJECT-TYPE
    SYNTAX INTEGER(0..4095)
    ACCESS read-only
    STATUS mandatory
    DESCRIPTION
        "The maximum VPI that the signalling stack on the ATM
        interface may currently allocate to switched virtual
        channel connections.  This value is the minimum of
        atmInterfaceConfMaxSvccVpi, and the
        atmInterfaceConfMaxSvccVpi of the interface's UNI/NNI
        peer.
        
        If the interface does not negotiate with its peer to
        determine the maximum VPI that can be allocated to
        SVCCs on the interface, then the value of this object
        must equal atmInterfaceConfMaxSvccVpi."
    ::= { atmInterfaceExtEntry 15 }

atmInterfaceConfMinSvccVci OBJECT-TYPE
    SYNTAX INTEGER(0..65535)
    ACCESS read-write
    STATUS mandatory
    DESCRIPTION
        "The minimum VCI that the signalling stack on the ATM
        interface is configured to support for allocation to
        switched virtual channel connections."
    ::= { atmInterfaceExtEntry 16 }

atmInterfaceCurrentMinSvccVci OBJECT-TYPE
    SYNTAX INTEGER(0..65535)
    ACCESS read-only
    STATUS mandatory
    DESCRIPTION
        "The minimum VCI that the signalling stack on the ATM
        interface may currently allocate to switched virtual
        channel connections.  This value is the maximum of
        atmInterfaceConfMinSvccVci, and the
        atmInterfaceConfMinSvccVci of the interface's UNI/NNI
        peer.
        
        If the interface does not negotiate with its peer to
        determine the minimum VCI that can be allocated to
        SVCCs on the interface, then the value of this object
        must equal atmInterfaceConfMinSvccVci."
    ::= { atmInterfaceExtEntry 17 }

atmIntfSigVccRxTrafficDescrIndex OBJECT-TYPE
    SYNTAX AtmTrafficDescrParamIndex
--    Rsyntax INTEGER(0..2147483647)
    ACCESS read-write
    STATUS mandatory
    DESCRIPTION
        "This object identifies the row in the
        atmTrafficDescrParamTable used during ILMI
        auto-configuration to specify the advertised
        signalling VCC traffic parameters for the
        receive direction.
        
        The traffic descriptor resulting from ILMI auto-
        configuration of the signalling VCC is indicated
        in the atmVclTable."
    ::= { atmInterfaceExtEntry 18 }

atmIntfSigVccTxTrafficDescrIndex OBJECT-TYPE
    SYNTAX AtmTrafficDescrParamIndex
--    Rsyntax INTEGER(0..2147483647)
    ACCESS read-write
    STATUS mandatory
    DESCRIPTION
        "This object identifies the row in the
        atmTrafficDescrParamTable used during ILMI
        auto-configuration to specify the advertised
        signalling VCC traffic parameters for the
        transmit direction.
        
        The traffic descriptor resulting from ILMI auto-
        configuration of the signalling VCC is indicated
        in the atmVclTable."
    ::= { atmInterfaceExtEntry 19 }

atmIntfPvcFailures OBJECT-TYPE
    SYNTAX Counter32
    ACCESS read-only
    STATUS mandatory
    DESCRIPTION
        "The number of times the operational status of a PVPL
        or PVCL on this interface has gone down."
    ::= { atmInterfaceExtEntry 20 }

atmIntfCurrentlyFailingPVpls OBJECT-TYPE
    SYNTAX Gauge32
    ACCESS read-only
    STATUS mandatory
    DESCRIPTION
        "The current number of VPLs on this interface for which
        there is an active row in the atmVplTable having an
        atmVplConnKind value of `pvc' and an atmVplOperStatus
        with a value other than `up'."
    ::= { atmInterfaceExtEntry 21 }

atmIntfCurrentlyFailingPVcls OBJECT-TYPE
    SYNTAX Gauge32
    ACCESS read-only
    STATUS mandatory
    DESCRIPTION
        "The current number of VCLs on this interface for which
        there is an active row in the atmVclTable having an
        atmVclConnKind value of `pvc' and an atmVclOperStatus
        with a value other than `up'."
    ::= { atmInterfaceExtEntry 22 }

atmIntfPvcFailuresTrapEnable OBJECT-TYPE
    SYNTAX TruthValue
--    Rsyntax INTEGER {
--        true(1),
--        false(2)
--        }
    ACCESS read-write
    STATUS mandatory
    DESCRIPTION
        "Allows the generation of traps in response to PVCL or
        PVPL failures on this interface."
    DEFVAL { false }
    ::= { atmInterfaceExtEntry 23 }

atmIntfPvcNotificationInterval OBJECT-TYPE
    SYNTAX INTEGER(1..3600)
--  Units
--    seconds
    ACCESS read-write
    STATUS mandatory
    DESCRIPTION
        "The minimum interval between the sending of
        atmIntfPvcFailuresTrap notifications for this
        interface."
    DEFVAL { 30 }
    ::= { atmInterfaceExtEntry 24 }

atmIlmiSrvcRegTable OBJECT-TYPE
    SYNTAX SEQUENCE OF AtmIlmiSrvcRegEntry
    ACCESS not-accessible
    STATUS mandatory
    DESCRIPTION
        "This table contains a list of all the ATM network
        services known by this device.
        
        The characteristics of these services are made
        available through the ILMI, using the ILMI general-
        purpose service registry MIB.
        
        These services may be made available to all ATM
        interfaces (atmIlmiSrvcRegIndex = 0) or to some
        specific ATM interfaces only (atmIlmiSrvcRegIndex = ATM
        interface index)."
    ::= { atm2MIBObjects 15 }

atmIlmiSrvcRegEntry OBJECT-TYPE
    SYNTAX AtmIlmiSrvcRegEntry
    ACCESS not-accessible
    STATUS mandatory
    DESCRIPTION
        "Information about a single service provider that is
        available to the user-side of an adjacent device
        through the ILMI."
    INDEX { atmIlmiSrvcRegIndex, atmIlmiSrvcRegServiceID, atmIlmiSrvcRegAddressIndex }
    ::= { atmIlmiSrvcRegTable 1 }

AtmIlmiSrvcRegEntry ::= SEQUENCE {
    atmIlmiSrvcRegIndex InterfaceIndex,
    atmIlmiSrvcRegServiceID OBJECT IDENTIFIER,
    atmIlmiSrvcRegAddressIndex INTEGER,
    atmIlmiSrvcRegATMAddress AtmAddr,
    atmIlmiSrvcRegParm1 OCTET STRING,
    atmIlmiSrvcRegRowStatus RowStatus
    }

atmIlmiSrvcRegIndex OBJECT-TYPE
    SYNTAX InterfaceIndex
--    Rsyntax Integer32
    ACCESS not-accessible
    STATUS mandatory
    DESCRIPTION
        "The ATM interface where the service defined in this
        entry can be made available to an ATM device attached
        to this interface.
        
        The value of 0 has a special meaning: when an ATM
        service is defined in an entry whose
        atmIlmiSrvcRegIndex is zero, the ATM service is
        available to ATM devices connected to any ATM
        interface.  (default value(s)).
        
        When the user-side of an adjacent device queries the
        content of the ILMI service registry MIB (using the
        ILMI protocol), the local network-side responds with
        the ATM services defined in atmIlmiSrvcRegTable
        entries, provided that these entries are indexed by:
                    - the corresponding interface number (atmIlmiSrvcRegIndex equal
                      to the number of the interface that the adjacent device is
                      connected to)
                    - zero (atmIlmiSrvcRegIndex=0)."
    ::= { atmIlmiSrvcRegEntry 1 }

atmIlmiSrvcRegServiceID OBJECT-TYPE
    SYNTAX OBJECT IDENTIFIER
    ACCESS not-accessible
    STATUS mandatory
    DESCRIPTION
        "This is the service identifier which uniquely
        identifies the type of service at the address provided
        in the table.  The object identifiers for the LAN
        Emulation Configuration Server (LECS) and the ATM Name
        Server (ANS) are defined in the ATM Forum ILMI Service
        Registry MIB."
    ::= { atmIlmiSrvcRegEntry 2 }

atmIlmiSrvcRegAddressIndex OBJECT-TYPE
    SYNTAX INTEGER(1..2147483647)
    ACCESS not-accessible
    STATUS mandatory
    DESCRIPTION
        "An arbitrary integer to differentiate multiple rows
        containing different ATM addresses for the same service
        on the same interface.  This number needs NOT to be the
        same as the corresponding ILMI atmfSrvcRegAddressIndex
        MIB object."
    ::= { atmIlmiSrvcRegEntry 3 }

atmIlmiSrvcRegATMAddress OBJECT-TYPE
    SYNTAX AtmAddr
--    Rsyntax OCTET STRING(SIZE(0 | 8 | 20))
    ACCESS read-write
    STATUS mandatory
    DESCRIPTION
        "This is the full address of the service. The user-side of the
        adjacent device may use this address to establish a connection
        with the service."
    ::= { atmIlmiSrvcRegEntry 4 }

atmIlmiSrvcRegParm1 OBJECT-TYPE
    SYNTAX OCTET STRING(SIZE(1..255))
    ACCESS read-write
    STATUS mandatory
    DESCRIPTION
        "An octet string used according to the value of
        atmIlmiSrvcRegServiceID."
    ::= { atmIlmiSrvcRegEntry 5 }

atmIlmiSrvcRegRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or destroy an entry from
        this table."
    ::= { atmIlmiSrvcRegEntry 6 }

atmIlmiNetworkPrefixTable OBJECT-TYPE
    SYNTAX SEQUENCE OF AtmIlmiNetworkPrefixEntry
    ACCESS not-accessible
    STATUS mandatory
    DESCRIPTION
        "A table specifying per interface network prefix(es)
        supplied by the network side of the UNI during ILMI
        address registration.  When no network prefixes are
        specified for a particular interface, one or more
        network prefixes based on the switch address(es) may be
        used for ILMI address registration."
    ::= { atm2MIBObjects 16 }

atmIlmiNetworkPrefixEntry OBJECT-TYPE
    SYNTAX AtmIlmiNetworkPrefixEntry
    ACCESS not-accessible
    STATUS mandatory
    DESCRIPTION
        "Information about a single network prefix supplied by
        the network side of the UNI during ILMI address
        registration.  Note that the index variable
        atmIlmiNetPrefixPrefix is a variable-length string, and
        as such the rule for variable-length strings in section
        7.7 of RFC 1902 applies."
    INDEX { ifIndex, atmIlmiNetPrefixPrefix }
    ::= { atmIlmiNetworkPrefixTable 1 }

AtmIlmiNetworkPrefixEntry ::= SEQUENCE {
    atmIlmiNetPrefixPrefix AtmIlmiNetworkPrefix,
    atmIlmiNetPrefixRowStatus RowStatus
    }

atmIlmiNetPrefixPrefix OBJECT-TYPE
    SYNTAX AtmIlmiNetworkPrefix
--    Rsyntax OCTET STRING(SIZE(8 | 13))
    ACCESS not-accessible
    STATUS mandatory
    DESCRIPTION
        "The network prefix specified for use in ILMI address
        registration."
    ::= { atmIlmiNetworkPrefixEntry 1 }

atmIlmiNetPrefixRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Used to create, delete, activate and de-activate
        network prefixes used in ILMI address registration."
    ::= { atmIlmiNetworkPrefixEntry 2 }

atmSwitchAddressTable OBJECT-TYPE
    SYNTAX SEQUENCE OF AtmSwitchAddressEntry
    ACCESS not-accessible
    STATUS mandatory
    DESCRIPTION
        "This table contains one or more ATM endsystem
        addresses on a per switch basis.  These addresses are
        used to identify the switch.  When no ILMI network
        prefixes are configured for certain interfaces, network
        prefixes based on the switch address(es) may be used
        for ILMI address registration."
    ::= { atm2MIBObjects 17 }

atmSwitchAddressEntry OBJECT-TYPE
    SYNTAX AtmSwitchAddressEntry
    ACCESS not-accessible
    STATUS mandatory
    DESCRIPTION
        "An entry in the ATM Switch Address table."
    INDEX { atmSwitchAddressIndex }
    ::= { atmSwitchAddressTable 1 }

AtmSwitchAddressEntry ::= SEQUENCE {
    atmSwitchAddressIndex Integer32,
    atmSwitchAddressAddress OCTET STRING,
    atmSwitchAddressRowStatus RowStatus
    }

atmSwitchAddressIndex OBJECT-TYPE
    SYNTAX Integer32
--  SYNTAX Integer32(1..65535)
    ACCESS not-accessible
    STATUS mandatory
    DESCRIPTION
        "An arbitrary index used to enumerate the ATM endsystem
        addresses for this switch."
    ::= { atmSwitchAddressEntry 1 }

atmSwitchAddressAddress OBJECT-TYPE
    SYNTAX OCTET STRING(SIZE(13 .. 20))
--  SYNTAX OCTET STRING(SIZE(13 | 20))
    ACCESS read-write
    STATUS mandatory
    DESCRIPTION
        "An ATM endsystem address or address prefix used to
        identify this switch.  When no ESI or SEL field is
        specified, the switch may generate the ESI and SEL
        fields automatically to obtain a complete 20-byte ATM
        endsystem address."
    ::= { atmSwitchAddressEntry 2 }

atmSwitchAddressRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Used to create, delete, activate, and de-
        activate
        addresses used to identify this switch."
    ::= { atmSwitchAddressEntry 3 }

atmVpCrossConnectXTable OBJECT-TYPE
    SYNTAX SEQUENCE OF AtmVpCrossConnectXEntry
    ACCESS not-accessible
    STATUS mandatory
    DESCRIPTION
        "This table contains one row per VP Cross Connect
        represented in the atmVpCrossConnectTable."
    ::= { atm2MIBObjects 18 }

atmVpCrossConnectXEntry OBJECT-TYPE
    SYNTAX AtmVpCrossConnectXEntry
    ACCESS not-accessible
    STATUS mandatory
    DESCRIPTION
        "Information about a particular ATM VP Cross Connect.
        
        Each entry provides an two objects that name the Cross
        Connect.  One is assigned by the Service User and the
        other by the Service Provider."
    INDEX { atmVpCrossConnectIndex, atmVpCrossConnectLowIfIndex, atmVpCrossConnectLowVpi, atmVpCrossConnectHighIfIndex, atmVpCrossConnectHighVpi }
-- Augments atmVpCrossConnectEntry FROM ATM-MIB
    ::= { atmVpCrossConnectXTable 1 }

AtmVpCrossConnectXEntry ::= SEQUENCE {
    atmVpCrossConnectUserName DisplayString,
    atmVpCrossConnectProviderName DisplayString 
    }

atmVpCrossConnectUserName OBJECT-TYPE
    SYNTAX DisplayString
--  Rsyntax OCTET STRING(0..255)
    ACCESS read-write
    STATUS mandatory
    DESCRIPTION
        "This is a service user assigned textual representation
        of a VPC PVC."
    ::= { atmVpCrossConnectXEntry 1 }

atmVpCrossConnectProviderName OBJECT-TYPE
    SYNTAX DisplayString
--  Rsyntax OCTET STRING(0..255)
    ACCESS read-only
    STATUS mandatory
    DESCRIPTION
        "This is a system supplied textual representation of
        VPC PVC.  It is assigned by the service provider."
    ::= { atmVpCrossConnectXEntry 2 }

atmVcCrossConnectXTable OBJECT-TYPE
    SYNTAX SEQUENCE OF AtmVcCrossConnectXEntry
    ACCESS not-accessible
    STATUS mandatory
    DESCRIPTION
        "This table contains one row per VC Cross Connect
        represented in the atmVcCrossConnectTable."
    ::= { atm2MIBObjects 19 }

atmVcCrossConnectXEntry OBJECT-TYPE
    SYNTAX AtmVcCrossConnectXEntry
    ACCESS not-accessible
    STATUS mandatory
    DESCRIPTION
        "Information about a particular ATM VC Cross Connect.
        
        Each entry provides an two objects that name the Cross
        Connect.  One is assigned by the Service User and the
        other by the Service Provider."
    INDEX { atmVcCrossConnectIndex, atmVcCrossConnectLowIfIndex, atmVcCrossConnectLowVpi, atmVcCrossConnectLowVci, atmVcCrossConnectHighIfIndex, atmVcCrossConnectHighVpi, atmVcCrossConnectHighVci }
-- Augments atmVcCrossConnectEntry FROM ATM-MIB
    ::= { atmVcCrossConnectXTable 1 }

AtmVcCrossConnectXEntry ::= SEQUENCE {
    atmVcCrossConnectUserName DisplayString,
    atmVcCrossConnectProviderName DisplayString
    }

atmVcCrossConnectUserName OBJECT-TYPE
    SYNTAX DisplayString
--  Rsyntax OCTET STRING(0..255) 
    ACCESS read-write
    STATUS mandatory
    DESCRIPTION
        "This is a service user assigned textual representation
        of a VCC PVC."
    ::= { atmVcCrossConnectXEntry 1 }

atmVcCrossConnectProviderName OBJECT-TYPE
    SYNTAX DisplayString
--  Rsyntax OCTET STRING(0..255)
    ACCESS read-only
    STATUS mandatory
    DESCRIPTION
        "This is a system supplied textual representation of
        VCC PVC.  It is assigned by the service provider."
    ::= { atmVcCrossConnectXEntry 2 }

atmCurrentlyFailingPVplTable OBJECT-TYPE
    SYNTAX SEQUENCE OF AtmCurrentlyFailingPVplEntry
    ACCESS not-accessible
    STATUS mandatory
    DESCRIPTION
        "A table indicating all VPLs for which there is an
        active row in the atmVplTable having an atmVplConnKind
        value of `pvc' and an atmVplOperStatus with a value
        other than `up'."
    ::= { atm2MIBObjects 20 }

atmCurrentlyFailingPVplEntry OBJECT-TYPE
    SYNTAX AtmCurrentlyFailingPVplEntry
    ACCESS not-accessible
    STATUS mandatory
    DESCRIPTION
        "Each entry in this table represents a VPL for which
        the atmVplRowStatus is `active', the atmVplConnKind is
        `pvc', and the atmVplOperStatus is other than `up'."
    INDEX { ifIndex, atmVplVpi }
    ::= { atmCurrentlyFailingPVplTable 1 }

AtmCurrentlyFailingPVplEntry ::= SEQUENCE {
    atmCurrentlyFailingPVplTimeStamp TimeStamp
    }

atmCurrentlyFailingPVplTimeStamp OBJECT-TYPE
    SYNTAX TimeStamp
--    Rsyntax TimeTicks
    ACCESS read-only
    STATUS mandatory
    DESCRIPTION
        "The time at which this PVPL began to fail."
    ::= { atmCurrentlyFailingPVplEntry 1 }

atmCurrentlyFailingPVclTable OBJECT-TYPE
    SYNTAX SEQUENCE OF AtmCurrentlyFailingPVclEntry
    ACCESS not-accessible
    STATUS mandatory
    DESCRIPTION
        "A table indicating all VCLs for which there is an
        active row in the atmVclTable having an atmVclConnKind
        value of `pvc' and an atmVclOperStatus with a value
        other than `up'."
    ::= { atm2MIBObjects 21 }

atmCurrentlyFailingPVclEntry OBJECT-TYPE
    SYNTAX AtmCurrentlyFailingPVclEntry
    ACCESS not-accessible
    STATUS mandatory
    DESCRIPTION
        "Each entry in this table represents a VCL for which
        the atmVclRowStatus is `active', the atmVclConnKind is
        `pvc', and the atmVclOperStatus is other than `up'."
    INDEX { ifIndex, atmVclVpi, atmVclVci }
    ::= { atmCurrentlyFailingPVclTable 1 }

AtmCurrentlyFailingPVclEntry ::= SEQUENCE {
    atmCurrentlyFailingPVclTimeStamp TimeStamp
    }

atmCurrentlyFailingPVclTimeStamp OBJECT-TYPE
    SYNTAX TimeStamp
--    Rsyntax TimeTicks
    ACCESS read-only
    STATUS mandatory
    DESCRIPTION
        "The time at which this PVCL began to fail."
    ::= { atmCurrentlyFailingPVclEntry 1 }

atmIntfPvcFailuresTrap TRAP-TYPE
-- Reverse mappable trap
    ENTERPRISE atmPvcTraps
    VARIABLES {
        ifIndex, atmIntfPvcFailures, atmIntfCurrentlyFailingPVpls, 
        atmIntfCurrentlyFailingPVcls }
--  Status
--    mandatory
    DESCRIPTION
        "A notification indicating that one or more PVPLs or
        PVCLs on this interface has failed since the last
        atmPvcFailuresTrap was sent.  If this trap has not been
        sent for the last atmIntfPvcNotificationInterval, then
        it will be sent on the next increment of
        atmIntfPvcFailures."
    ::= 1

atmSwitchServcHostGroup OBJECT IDENTIFIER ::= { atm2MIBGroups 1 }
-- OBJECT-GROUP
--  Status
--    mandatory
--  Descr
--    A collection of objects providing information
--     for a Switch/Service/Host that implements
--     ATM interfaces.
--  objects
--    atmSigSSCOPConEvents, atmSigSSCOPErrdPdus, 
--    atmSigDetectSetupAttempts, atmSigEmitSetupAttempts, 
--    atmSigDetectUnavailRoutes, atmSigEmitUnavailRoutes, 
--    atmSigDetectUnavailResrcs, atmSigEmitUnavailResrcs, 
--    atmSigDetectCldPtyEvents, atmSigEmitCldPtyEvents, 
--    atmSigDetectMsgErrors, atmSigEmitMsgErrors, 
--    atmSigDetectClgPtyEvents, atmSigEmitClgPtyEvents, 
--    atmSigDetectTimerExpireds, atmSigEmitTimerExpireds, 
--    atmSigDetectRestarts, atmSigEmitRestarts, atmSigInEstabls, 
--    atmSigOutEstabls, atmVclStatTotalCellIns, 
--    atmVclStatClp0CellIns, atmVclStatTotalDiscards, 
--    atmVclStatClp0Discards, atmVclStatTotalCellOuts, 
--    atmVclStatClp0CellOuts, atmVclStatTaggedOuts, 
--    atmVplStatTotalCellIns, atmVplStatClp0CellIns, 
--    atmVplStatTotalDiscards, atmVplStatClp0Discards, 
--    atmVplStatTotalCellOuts, atmVplStatClp0CellOuts, 
--    atmVplStatTaggedOuts, atmVplLogicalPortDef, 
--    atmVplLogicalPortIndex, atmInterfaceConfMaxSvpcVpi, 
--    atmInterfaceCurrentMaxSvpcVpi, atmInterfaceConfMaxSvccVpi, 
--    atmInterfaceCurrentMaxSvccVpi, atmInterfaceConfMinSvccVci, 
--    atmInterfaceCurrentMinSvccVci, 
--    atmIntfSigVccRxTrafficDescrIndex, 
--    atmIntfSigVccTxTrafficDescrIndex, atmIntfPvcFailures, 
--    atmIntfCurrentlyFailingPVpls, atmIntfCurrentlyFailingPVcls, 
--    atmIntfPvcNotificationInterval, atmIntfPvcFailuresTrapEnable, 
--    atmIntfConfigType, atmIntfActualType, atmIntfConfigSide, 
--    atmIntfActualSide, atmIntfIlmiFsmState, 
--    atmIntfIlmiEstablishConPollIntvl, 
--    atmIntfIlmiCheckConPollIntvl, atmIntfIlmiConPollInactFactor, 
--    atmIntfIlmiPublicPrivateIndctr

atmSwitchServcGroup OBJECT IDENTIFIER ::= { atm2MIBGroups 2 }
-- OBJECT-GROUP
--  Status
--    mandatory
--  Descr
--    A collection of objects providing information
--     for a Switch/Service that implements ATM interfaces.
--  objects
--    atmIlmiSrvcRegATMAddress, atmIlmiSrvcRegParm1, 
--    atmIlmiSrvcRegRowStatus, atmIlmiNetPrefixRowStatus, 
--    atmSigSupportClgPtyNumDel, atmSigSupportClgPtySubAddr, 
--    atmSigSupportCldPtySubAddr, atmSigSupportHiLyrInfo, 
--    atmSigSupportLoLyrInfo, atmSigSupportBlliRepeatInd, 
--    atmSigSupportAALInfo, atmSigSupportPrefCarrier, 
--    atmSvcVpCrossConnectCreationTime, 
--    atmSvcVpCrossConnectRowStatus, 
--    atmSvcVcCrossConnectCreationTime, 
--    atmSvcVcCrossConnectRowStatus, atmIfRegAddrAddressSource, 
--    atmIfRegAddrOrgScope, atmIfRegAddrRowStatus

atmServcGroup OBJECT IDENTIFIER ::= { atm2MIBGroups 4 }
-- OBJECT-GROUP
--  Status
--    mandatory
--  Descr
--    A collection of objects providing information
--     for an ATM Network Service.
--  objects
--    atmVpCrossConnectUserName, atmVpCrossConnectProviderName, 
--    atmVcCrossConnectUserName, atmVcCrossConnectProviderName

atmHostGroup OBJECT IDENTIFIER ::= { atm2MIBGroups 5 }
-- OBJECT-GROUP
--  Status
--    mandatory
--  Descr
--    A collection of objects providing information
--     for a Host that implements ATM interfaces.
--  objects
--    atmAal5VclInPkts, atmAal5VclOutPkts, atmAal5VclInOctets, 
--    atmAal5VclOutOctets, atmVclAddrType, atmVclAddrRowStatus, 
--    atmAddrVclAddrType, atmVclGenSigDescrIndex, 
--    atmSigDescrParamAalType, atmSigDescrParamAalSscsType, 
--    atmSigDescrParamBhliType, atmSigDescrParamBhliInfo, 
--    atmSigDescrParamBbcConnConf, atmSigDescrParamBlliLayer2, 
--    atmSigDescrParamBlliLayer3, atmSigDescrParamBlliPktSize, 
--    atmSigDescrParamBlliSnapId, atmSigDescrParamBlliOuiPid, 
--    atmSigDescrParamRowStatus

atm2MIBCompliance OBJECT IDENTIFIER ::= { atm2MIBCompliances 1 }
-- MODULE-COMPLIANCE
--  Status
--    mandatory
--  Descr
--    The compliance statement for SNMP entities which
--    represent ATM interfaces.  The compliance statements
--    are used to determine if a particular group or object
--    applies to hosts, networks/switches, or both.
--  Module
--    >>current<<
--   MandGroup
--    atmSwitchServcHostGroup
--   ObjVar
--    atmVclStatTotalCellIns
--   ObjVar
--    atmVclStatClp0CellIns
--   ObjVar
--    atmVclStatTotalDiscards
--   ObjVar
--    atmVclStatClp0Discards
--   ObjVar
--    atmVclStatTotalCellOuts
--   ObjVar
--    atmVclStatClp0CellOuts
--   ObjVar
--    atmVclStatTaggedOuts
--   ObjVar
--    atmVplStatTotalCellIns
--   ObjVar
--    atmVplStatClp0CellIns
--   ObjVar
--    atmVplStatTotalDiscards
--   ObjVar
--    atmVplStatClp0Discards
--   ObjVar
--    atmVplStatTotalCellOuts
--   ObjVar
--    atmVplStatClp0CellOuts
--   ObjVar
--    atmVplStatTaggedOuts
--   ObjVar
--    atmVplLogicalPortDef
--   ObjVar
--    atmIntfSigVccRxTrafficDescrIndex
--   ObjVar
--    atmIntfSigVccTxTrafficDescrIndex
--   OptGroup
--    atmSwitchServcGroup
--   ObjVar
--    atmIfRegAddrRowStatus
--   ObjVar
--    atmSigSupportClgPtyNumDel
--   ObjVar
--    atmSigSupportClgPtySubAddr
--   ObjVar
--    atmSigSupportCldPtySubAddr
--   ObjVar
--    atmSigSupportHiLyrInfo
--   ObjVar
--    atmSigSupportLoLyrInfo
--   ObjVar
--    atmSigSupportBlliRepeatInd
--   ObjVar
--    atmSigSupportAALInfo
--   ObjVar
--    atmSigSupportPrefCarrier
--   ObjVar
--    atmSvcVpCrossConnectRowStatus
--   ObjVar
--    atmSvcVcCrossConnectRowStatus
--   OptGroup
--    atmServcGroup
--   OptGroup
--    atmHostGroup
--   ObjVar
--    atmVclAddrType
--   ObjVar
--    atmVclAddrRowStatus
--   ObjVar
--    atmVclGenSigDescrIndex
--   ObjVar
--    atmSigDescrParamAalType
--   ObjVar
--    atmSigDescrParamAalSscsType
--   ObjVar
--    atmSigDescrParamBhliType
--   ObjVar
--    atmSigDescrParamBhliInfo
--   ObjVar
--    atmSigDescrParamBbcConnConf
--   ObjVar
--    atmSigDescrParamBlliLayer2
--   ObjVar
--    atmSigDescrParamBlliLayer3
--   ObjVar
--    atmSigDescrParamBlliPktSize
--   ObjVar
--    atmSigDescrParamBlliSnapId
--   ObjVar
--    atmSigDescrParamBlliOuiPid
--   ObjVar
--    atmSigDescrParamRowStatus


END
-- MIB created 6/25/98 14:39:52, by
--   SMIC (the next generation) version 1.6.31, December 11, 1994.

LAN-EMULATION-CLIENT-MIB DEFINITIONS ::= BEGIN

-- From file: "aflec201.mi2"
-- Compile options "G P A"

IMPORTS
    enterprises
	    FROM RFC1155-SMI
    Counter32, Integer32
            FROM SNMPv2-SMI-v1
    OBJECT-TYPE
            FROM RFC-1212
    MacAddress, RowStatus, TruthValue, DisplayString
            FROM SNMPv2-TC-v1
    InterfaceIndex
            FROM IF-MIB
    ifIndex
            FROM RFC1213-MIB
    OwnerString
            FROM RMON-MIB;

-- leClientMIB OBJECT IDENTIFIER ::= { atmfLanEmulation 1 }
-- MODULE-IDENTITY
--  LastUpdated
--    9802230000Z
--  OrgName
--    ATM Forum LAN Emulation Sub-Working Group
--  ContactInfo
--    
--      The ATM Forum
--      2570 West El Camino Real, Suite 304
--      Mountain View, CA  94040-1313
--      Tel: +1-650-949-6700
--      Fax: +1-650-949-6705
--      E-mail: info@atmforum.com
--      Web: http://www.atmforum.com/
--                                         
--  Descr
--    This module defines a portion of the management 
--     information base (MIB) for managing ATM LAN Emulation
--     Client nodes.  It is meant to be used in connection with
--     the AToM MIB and MIB-II / RFC 1573 'ifTable' entries
--     for each LEC / emulated 802.x network interface.
--  RevDate
--    9505100000Z
--  RevDescr
--    The LAST-UPDATED date of the MIB in the Version 1.0 LAN
--     Emulation Client management specification.
--  RevDate
--    9802230000Z
--  RevDescr
--    This MIB module now provides extensive support for LAN
--     Emulation Version 2.0 clients, and the optional ability
--     to query a proxy client (say, one attached to a bridge)
--     to find out how it would respond to a LE_ARP request.

atmForum        OBJECT IDENTIFIER ::= { enterprises 353 }
atmForumNetworkManagement OBJECT IDENTIFIER ::= { atmForum 5 }
atmfLanEmulation OBJECT IDENTIFIER ::= { atmForumNetworkManagement 3 }
leClientMIB OBJECT IDENTIFIER ::= { atmfLanEmulation 1 }
leClientMIBObjects OBJECT IDENTIFIER ::= { leClientMIB 1 }
lecQueryObjects OBJECT IDENTIFIER ::= { leClientMIBObjects 12 }
lecMacQueryObjects OBJECT IDENTIFIER ::= { lecQueryObjects 1 }
lecRDQueryObjects OBJECT IDENTIFIER ::= { lecQueryObjects 2 }
leClientMIBConformance OBJECT IDENTIFIER ::= { leClientMIB 2 }
leClientMIBGroups OBJECT IDENTIFIER ::= { leClientMIBConformance 1 }
leClientMIBCompliances OBJECT IDENTIFIER ::= { leClientMIBConformance 2 }

AtmLaneAddress ::= OCTET STRING(SIZE(0..20))
-- AtmLaneAddress ::= OCTET STRING(SIZE(0 | 20))
-- TEXTUAL-CONVENTION
--  Status
--    mandatory
--  Descr
--    A twenty-octet binary string, containing a standard
--     ATM Forum address == or the zero-length string,
--     indicating the absence of an address.
--    
--     For LAN Emulation purposes, the eight-octet address
--     format is not used.

VpiInteger ::= INTEGER(0..4095)
-- TEXTUAL-CONVENTION
--  Status
--    mandatory
--  Descr
--    An integer large enough to hold a VPI.  Objects that
--     use this textual convention should contain either
--    
--       -  A value which conforms to the AtmVpIdentifier
--          convention in the proposed ATM-TC-MIB, or
--    
--       -  Zero (if there is no circuit/path data).
--    
--     AtmVpIdentifier is currently defined as
--    
--          The VPI value for a VPL or VCL.  The value VPI=0
--          is only allowed for a VCL.  For ATM UNIs supporting
--          VPCs the VPI value ranges from 1 to 255.  For ATM
--          UNIs supporting VCCs the VPI value ranges from 0
--          to 255.  For ATM NNIs the VPI value ranges from 0
--          to 4095.  The maximum VPI value cannot exceed the
--          value allowable by atmInterfaceMaxVpiBits defined
--          in ATM-MIB.
--    
--     To align the textual conventions, VpiInteger now ranges
--     between 0 and 4095, instead of between 0 and 255.

VciInteger ::= INTEGER(0..65535)
-- TEXTUAL-CONVENTION
--  Status
--    mandatory
--  Descr
--    An integer large enough to hold a VCI.  Objects that
--     use this textual convention should contain either
--    
--        -  A value which conforms to the AtmVcIdentifier
--           convention in the proposed ATM-TC-MIB, or
--    
--        -  Zero (if there is no circuit data).
--    
--     AtmVcIdentifier is currently defined as
--    
--          The VCI value for a VCL.  The maximum VCI value
--          cannot exceed the value allowable by
--          atmInterfaceMaxVciBits defined in ATM-MIB.

LeConnectionInterface ::= INTEGER(0..2147483647)
-- TEXTUAL-CONVENTION
--  Status
--    mandatory
--  Descr
--    A combination flag and ifTable index, indicating
--     whether a LAN Emulation circuit exists - and, if
--     so, which interface is associated with it at the
--     point where it connects to a LE Client.
--    
--     Objects of this type are always defined as part of
--     a set that includes
--    
--             fooInterface   LeConnectionInterface
--             fooVpi         VpiInteger
--             fooVci         VciInteger
--    
--     The interpretation of these objects is as follows.
--    
--     1.  If no connection exists, 'fooInterface' has a
--         value of 0.  Because Interfaces table entries
--         always have 'ifIndex' values larger than 0,
--         'fooInterface' reliably serves as a 'connection
--         exists' flag.
--    
--         In this case, 'fooVpi' and 'fooVci' are
--         meaningless, and have the value 0.
--    
--     2.  If a PVC or SVC exists, 'fooInterface' is defined
--         to have the value of the MIB-II/RFC 1573 'ifIndex'
--         of the 'atm' interface associated with the VCC.
--         'fooVpi' and 'fooVci' will contain its VPI/VCI.
--         Therefore, ('fooInterface', 'fooVpi', 'fooVci')
--         give you an index into the AToM MIB which allows
--         you to examine and play with the circuit further.
--    
--      3. If a proprietary connection (such as an internal
--         data path between co-located components) exists,
--         this specification does not mandate how it should
--         be managed.  One option is to set 'fooInterface'
--         to the value of the MIB-II/RFC 1573 'ifIndex' for
--         the LAN Emulation Client.  This indicates that a
--         connection exists, but is not being managed in the
--         same fashion as an ATM VCC.

LecState ::= INTEGER {
        initialState(1),
        lecsConnect(2),
        configure(3),
        join(4),
        initialRegistration(5),
        busConnect(6),
        operational(7)
        }
-- TEXTUAL-CONVENTION
--  Status
--    mandatory
--  Descr
--    An official protocol state of a LAN Emulation Client.
--  Refer
--    ATM Forum LAN Emulation Over ATM Specification, V1.0,
--     Section 2.3.1

LecDataFrameFormat ::= INTEGER {
        unspecified(1),
        aflane8023(2),
        aflane8025(3)
        }
-- TEXTUAL-CONVENTION
--  Status
--    mandatory
--  Descr
--    A 'LAN Type' value.
--    
--     C2  LAN Type.  The type of LAN that the LE Client is,
--         or wishes to become, a member of.  This MUST be one
--         of Ethernet/IEEE 802.3, IEEE 802.5, or Unspecified.
--  Refer
--    ATM Forum LAN Emulation Over ATM Specification, V1.0,
--     Section 5.1.1

LecDataFrameSize ::= INTEGER {
        unspecified(1),
        max1516(2),
        max4544(3),
        max9234(4),
        max18190(5),
        max1580(6)
        }
-- TEXTUAL-CONVENTION
--  Status
--    mandatory
--  Descr
--    A 'Maximum Data Frame Size' value.
--    
--     C3  Maximum Data Frame Size.  The maximum AAL-5 SDU size
--         of a data frame that the LE Client wishes to send on
--         any Multicast Send VCC, or to receive on any
--         Multicast Send VCC or Multicast Forward VCC.
--    
--         This parameter also specifies the maximum AAL-5 SDU
--         on all of a LE Client's non-multiplexed Data Direct
--         VCCs, and the maximum AAL-5 SDU - 12 (for overhead)
--         on all of a LE Client's LLC-multiplexed Data Direct
--         VCCs.
--    
--         This setting MUST be either 1516, 1580, 4544, 9234,
--         or 18190 octets, or Unspecified.  The 1580 value is
--         only available to 'V2 Capable' clients.
--  Refer
--    ATM Forum LAN Emulation V1 and V2 LUNI specifications,
--     Section 5.1.1

LeArpTableEntryType ::= INTEGER {
        other(1),
        learnedViaControl(2),
        learnedViaData(3),
        staticVolatile(4),
        staticNonVolatile(5)
        }
-- TEXTUAL-CONVENTION
--  Status
--    mandatory
--  Descr
--    Indicates how a LE_ARP table entry was created and
--     whether it is subject to aging.
--    
--         other(1)
--             The LE_ARP entry does not fall into one of
--             the categories defined below.
--    
--         learnedViaControl(2)
--             This LE_ARP entry was learned by using the
--             LE_ARP_REQUEST / LE_ARP_RESPONSE protocol,
--             or by otherwise observing relevant traffic
--             on Control VCCs.
--    
--             Entries of this type are aged.
--    
--         learnedViaData(3)
--             This LE_ARP entry was learned by observing
--             incoming traffic on Data VCCs.
--    
--             Entries of this type are aged.
--    
--         staticVolatile(4)
--             This LE_ARP entry was created by management.
--             It will not be aged.  On the other hand, it
--             will not survive a restart of the client.
--    
--             If an agent permits LE_ARP entries of this
--             type to be created, it may require that the
--             LAN Emulation Client be in the 'operational'
--             state at the time.
--    
--         staticNonVolatile(5)
--             This LE_ARP entry was created by management.
--             It will not be aged, and it will survive a
--             restart of the client.
--    
--     The values 'learnedViaData' and 'learnedViaControl'
--     can be read, but may not be written.

lecConfigTable OBJECT-TYPE
    SYNTAX SEQUENCE OF LecConfigEntry
    ACCESS not-accessible
    STATUS mandatory
    DESCRIPTION
        "A table describing all of the LAN Emulation Clients
         implemented by this host.  Each LE Client has a row
         in the MIB-II/RFC 1573 Interfaces table (describing
         the emulated packet interface it presents to higher
         layers).  Each LE Client also has a row in this and
         other LEC MIB tables (describing its interface with
         other LAN Emulation components).
        
         This table contains configuration variables.  Three
         extension tables contain client status, performance
         statistics, and information about control/multicast
         VCCs.
        
         Unlike hardware ports, LE Clients can be created by
         management.  However, the RFC 1573 Interfaces table
         does not directly support row creation.  Therefore,
         creating or deleting a row in the lecConfigTable is
         defined to have the side effect of creating or
         deleting corresponding rows in
        
             -  the MIB-II / RFC 1573 Interfaces table,
             -  the 'lecMappingTable',
             -  the 'lecStatusTable',
             -  the 'lecServerVccTable',
             -  the 'lecStatisticsTable', and
             -  any other dependent tables
        
         New Interfaces table rows for LAN Emulation Clients
         always have 'ifAdminStatus' set to 'down'.
        
         A Note On Indexing:
         -------------------
         Most of the tables in this MIB are indexed in whole
         or in part by 'lecIndex' - not by 'ifIndex'.
        
         Why is there a separate index?
        
         Traditionally, ifIndex values are chosen by agents,
         and are permitted to change across restarts.  Using
         ifIndex to index lecConfigTable could complicate
         row creation and/or cause interoperability problems
         (if each agent had special restrictions on ifIndex).
         Having a separate index avoids these problems.      "
    ::= { leClientMIBObjects 1 }

lecConfigEntry OBJECT-TYPE
    SYNTAX LecConfigEntry
    ACCESS not-accessible
    STATUS mandatory
    DESCRIPTION
        "Each table entry contains configuration information
         for one LAN Emulation Client.
        
         Most of the objects are derived from Initial State
         Parameters in the LAN Emulation specification."
    INDEX { lecIndex }
    ::= { lecConfigTable 1 }

LecConfigEntry ::= SEQUENCE {
    lecIndex INTEGER,
    lecRowStatus RowStatus,
    lecOwner OwnerString,
    lecConfigMode INTEGER,
    lecConfigLanType LecDataFrameFormat,
    lecConfigMaxDataFrameSize LecDataFrameSize,
    lecConfigLanName DisplayString,
    lecConfigLesAtmAddress AtmLaneAddress,
    lecControlTimeout INTEGER,
    lecMaxUnknownFrameCount INTEGER,
    lecMaxUnknownFrameTime INTEGER,
    lecVccTimeoutPeriod Integer32,
    lecMaxRetryCount INTEGER,
    lecAgingTime INTEGER,
    lecForwardDelayTime INTEGER,
    lecExpectedArpResponseTime INTEGER,
    lecFlushTimeOut INTEGER,
    lecPathSwitchingDelay INTEGER,
    lecLocalSegmentID INTEGER,
    lecMulticastSendType INTEGER,
    lecMulticastSendAvgRate Integer32,
    lecMulticastSendPeakRate Integer32,
    lecConnectionCompleteTimer INTEGER,
    lecConfigLecsAtmAddress AtmLaneAddress,
    lecInitialControlTimeout INTEGER,
    lecControlTimeoutMultiplier INTEGER,
    lecV2MaxUnknownFrameCount INTEGER,
    lecConfigLocalSegmentID INTEGER,
    lecConfigV2Capable TruthValue,
    lecConfigSelectiveMulticast TruthValue,
    lecForwardDisconnectTimeout INTEGER,
    lecConfigLLCMultiplexCapable TruthValue,
    lecMinReconfigureDelay INTEGER,
    lecMaxReconfigureDelay INTEGER,
    lecMaxBusConnectRetries INTEGER,
    lecTokenRingExplorerExclude TruthValue
    }

lecIndex OBJECT-TYPE
    SYNTAX INTEGER(1..2147483647)
    ACCESS not-accessible
    STATUS mandatory
    DESCRIPTION
        "A value which uniquely identifies this conceptual
         row in the lecConfigTable.
        
         If the conceptual row identified by this value of
         lecIndex is recreated following an agent restart,
         the same value of lecIndex must be used to identify
         the recreated row.  (However, the Interfaces table
         index associated with the client may change.)"
    ::= { lecConfigEntry 1 }

lecRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object lets network managers create and delete
         LAN Emulation Clients, on systems that support this
         optional capability.
        
         It does not control Joins and Terminations; they are
         controlled by 'ifAdminStatus'.  However, taking rows
         out of service will have the side effect of changing
         their 'ifAdminStatus' values to 'down', thus causing
         any active emulated LAN connections to be terminated.
        
         Within each conceptual lecConfigTable row, objects
         which are writable may be modified regardless of the
         value of lecRowStatus.  It is not necessary to set a
         row's status to 'notInService' first.
        
         When creating a LAN Emulation Client, it is up to the
         management station to determine a suitable 'lecIndex'.
         To facilitate interoperability, agents should not put
         any restrictions on the 'lecIndex' beyond the obvious
         ones that it be valid and unused.
        
         If you create a LAN Emulation Client via this object,
         it will initially have
        
             'ifAdminStatus' = 'down'
             'ifOperStatus' = 'down'
             'lecInterfaceState' = 'initialState'            "
    ::= { lecConfigEntry 2 }

lecOwner OBJECT-TYPE
    SYNTAX OwnerString(SIZE(0..127))
--    Rsyntax OCTET STRING(SIZE(0..127))
    ACCESS read-write
    STATUS mandatory
    DESCRIPTION
        "The entity that configured this entry and is therefore
         using the resources assigned to it."
    ::= { lecConfigEntry 3 }

lecConfigMode OBJECT-TYPE
    SYNTAX INTEGER {
        automatic(1),
        manual(2)
        }
    ACCESS read-write
    STATUS mandatory
    DESCRIPTION
        "Indicates whether this LAN Emulation Client should
         auto-configure the next time it is (re)started.
        
         In automatic(1) mode, a client uses a LAN Emulation
         Configuration Server to learn the ATM address of its
         LAN Emulation Server, and to obtain other parameters.
        
         lecConfig{ LanType, MaxDataFrameSize, LanName } are
         used in the Configure request.  lecConfigLesAtmAddress
         is ignored.
        
         In manual(2) mode, management tells the client the
         ATM address of its LAN Emulation Server and the
         values of other parameters.
        
         lecConfig{ LanType, MaxDataFrameSize, LanName } are
         used in the Join request.  lecConfigLesAtmAddress
         tells the client which LES to call."
    REFERENCE
        "ATM Forum LAN Emulation Over ATM Specification, V1.0,
         Sections 3.4.1.1 and 5.3"
    DEFVAL { automatic }
    ::= { lecConfigEntry 4 }

lecConfigLanType OBJECT-TYPE
    SYNTAX LecDataFrameFormat
--    Rsyntax INTEGER {
--        unspecified(1),
--        aflane8023(2),
--        aflane8025(3)
--        }
    ACCESS read-write
    STATUS mandatory
    DESCRIPTION
        "C2c  LAN Type (configured).
        
         The data frame format which this client will use the
         next time it returns to the Initial State.
        
         Auto-configuring clients use this parameter in their
         Configure requests.  Manually-configured clients use
         it in their Join requests.
        
         This MIB object will not be overwritten with the new
         value from a LE_{JOIN,CONFIGURE}_RESPONSE.  Instead,
         lecActualLanType will be."
    REFERENCE
        "ATM Forum LAN Emulation Over ATM Specification, V1.0
         and V2.0, Section 5.1.1"
    DEFVAL { unspecified }
    ::= { lecConfigEntry 5 }

lecConfigMaxDataFrameSize OBJECT-TYPE
    SYNTAX LecDataFrameSize
--    Rsyntax INTEGER {
--        unspecified(1),
--        max1516(2),
--        max4544(3),
--        max9234(4),
--        max18190(5),
--        max1580(6)
--        }
    ACCESS read-write
    STATUS mandatory
    DESCRIPTION
        "C3c  Maximum Data Frame Size (configured).
        
         The maximum data frame size which this client will
         use the next time it returns to the Initial State.
        
         Auto-configuring clients use this parameter in their
         Configure requests.  Manually-configured clients use
         it in their Join requests.
        
         This MIB object will not be overwritten with the new
         value from a LE_{JOIN,CONFIGURE}_RESPONSE.  Instead,
         lecActualMaxDataFrameSize will be."
    REFERENCE
        "ATM Forum LAN Emulation Over ATM Specification, V1.0
         and V2.0, Section 5.1.1"
    DEFVAL { unspecified }
    ::= { lecConfigEntry 6 }

lecConfigLanName OBJECT-TYPE
    SYNTAX DisplayString(SIZE(0..32))
--    Rsyntax OCTET STRING(SIZE(0..32))
    ACCESS read-write
    STATUS mandatory
    DESCRIPTION
        "C5c  ELAN Name (configured).
        
         The ELAN Name this client will use the next time it
         returns to the Initial State.
        
         Auto-configuring clients use this parameter in their
         Configure requests.  Manually-configured clients use
         it in their Join requests.
        
         This MIB object will not be overwritten with the new
         value from a LE_{JOIN,CONFIGURE}_RESPONSE.  Instead,
         lecActualLanName will be."
    REFERENCE
        "ATM Forum LAN Emulation Over ATM Specification, V1.0
         and V2.0, Section 5.1.1"
    ::= { lecConfigEntry 7 }

lecConfigLesAtmAddress OBJECT-TYPE
    SYNTAX AtmLaneAddress
--    Rsyntax OCTET STRING(SIZE(0 | 20))
    ACCESS read-write
    STATUS mandatory
    DESCRIPTION
        "C9  LE Server ATM Address.
        
         The LAN Emulation Server which this client will use
         the next time it is started in manual configuration
         mode.
        
         When lecConfigMode is 'automatic', there is no need
         to set this address, and no advantage to doing so.
         The client will use the LECS to find a LES, putting
         the auto-configured address in lecActualLesAtmAddress
         while leaving lecConfigLesAtmAddress alone."
    REFERENCE
        "ATM Forum LAN Emulation Over ATM Specification, V1.0
         and V2.0, Section 5.1.1"
    ::= { lecConfigEntry 8 }

lecControlTimeout OBJECT-TYPE
    SYNTAX INTEGER(10..300)
--  Units
--    seconds
    ACCESS read-write
    STATUS mandatory
    DESCRIPTION
        "C7  Control Time-out.  Time out period used for
             timing out most request/response control frame
             interactions, as specified elsewhere [in the
             LAN Emulation specification].
        
             In LANE V2.0, this value specifies the maximum
             cumulative timeout for an exponential backoff
             algorithm.
        
         This time value is expressed in seconds."
    REFERENCE
        "ATM Forum LAN Emulation Over ATM Specification, V1.0
         and V2.0, Section 5.1.1"
    DEFVAL { 30 }
    ::= { lecConfigEntry 9 }

lecMaxUnknownFrameCount OBJECT-TYPE
    SYNTAX INTEGER(1..10)
--  Units
--    frames
    ACCESS read-write
    STATUS deprecated
    DESCRIPTION
        "This is the LANE V1.0 version of 'C10 Maximum Unknown
         Frame Count'.  It should not be implemented except as
         required for backwards compatibility.
        
         It has been deprecated because LANE V2.0 permits this
         parameter to take values up to 20 -- a revision which
         doesn't seem to be allowed under rules in RFC 1902."
    REFERENCE
        "ATM Forum LAN Emulation Over ATM Specification, V1.0,
         Section 5.1.1"
    DEFVAL { 1 }
    ::= { lecConfigEntry 10 }

lecMaxUnknownFrameTime OBJECT-TYPE
    SYNTAX INTEGER(1..60)
--  Units
--    seconds
    ACCESS read-write
    STATUS mandatory
    DESCRIPTION
        "C11 Maximum Unknown Frame Time.  Within the period of
             time defined by the Maximum Unknown Frame Time, a
             LE Client will send no more than Maximum Unknown
             Frame Count frames to the BUS for a given unicast
             LAN Destination, and it must also initiate the
             address resolution protocol to resolve that LAN
             Destination.
        
             LANE V2.0 changes this to 'will send no more than
             Maximum Unknown Frame Count frames to the BUS ...
             without initiating the [LE_ARP]', implying that a
             LANE V2.0 client is not always required to send a
             LE_ARP_REQUEST along with the unknown frames.
        
         This time value is expressed in seconds."
    REFERENCE
        "ATM Forum LAN Emulation Over ATM Specification, V1.0
         and V2.0, Section 5.1.1"
    DEFVAL { 1 }
    ::= { lecConfigEntry 11 }

lecVccTimeoutPeriod OBJECT-TYPE
    SYNTAX Integer32
--  Units
--    seconds
    ACCESS read-write
    STATUS mandatory
    DESCRIPTION
        "C12 VCC Time-out Period.  A LE Client SHOULD release
             any Data Direct VCC that it has not used to
             transmit or receive any data frames for the
             length of the VCC Time-out Period.  This parameter
             is only meaningful for SVC Data Direct VCCs
             signalled with the Ethernet/IEEE 802.3 LE Data
             Direct VCC B-LLI value or the IEEE 802.5 LE Data
             Direct VCC B-LLI value.  It should not be used for
             any SVC signalled with the LLC-Multiplexed B-LLI
             value.
        
         This time value is expressed in seconds.  The default
         value is 20 minutes.  A value of 0 seconds means that
         the timeout period is infinite.  Negative values will
         be rejected by the agent."
    REFERENCE
        "ATM Forum LAN Emulation Over ATM Specification, V1.0
         and V2.0, Section 5.1.1"
    DEFVAL { 1200 }
    ::= { lecConfigEntry 12 }

lecMaxRetryCount OBJECT-TYPE
    SYNTAX INTEGER(0..2)
    ACCESS read-write
    STATUS mandatory
    DESCRIPTION
        "C13 Maximum Retry Count.  A LE CLient MUST not retry
             a LE_ARP_REQUEST for a given frame's LAN
             destination more than Maximum Retry Count times,
             after the first LE_ARP_REQUEST for that same
             frame's LAN destination."
    REFERENCE
        "ATM Forum LAN Emulation Over ATM Specification, V1.0
         and V2.0, Section 5.1.1"
    DEFVAL { 1 }
    ::= { lecConfigEntry 13 }

lecAgingTime OBJECT-TYPE
    SYNTAX INTEGER(10..300)
--  Units
--    seconds
    ACCESS read-write
    STATUS mandatory
    DESCRIPTION
        "C17 Aging Time.  The maximum time that a LE Client
             will maintain an entry for a unicast LAN
             Destination in its LE_ARP cache in the absence
             of a verification of that relationship.
        
         This time value is expressed in seconds."
    REFERENCE
        "ATM Forum LAN Emulation Over ATM Specification, V1.0
         and V2.0, Section 5.1.1"
    DEFVAL { 300 }
    ::= { lecConfigEntry 14 }

lecForwardDelayTime OBJECT-TYPE
    SYNTAX INTEGER(4..30)
--  Units
--    seconds
    ACCESS read-write
    STATUS mandatory
    DESCRIPTION
        "C18 Forward Delay Time.  The maximum time that a LE
             Client will maintain an entry for a non-local MAC
             address in its LE_ARP cache in the absence of a
             verification of that relationship, as long as the
             Topology Change flag C19 is true.
        
         lecForwardDelayTime SHOULD BE less than lecAgingTime.
         When it is not, lecAgingTime governs LE_ARP aging.
        
         This time value is expressed in seconds."
    REFERENCE
        "ATM Forum LAN Emulation Over ATM Specification, V1.0
         and V2.0, Section 5.1.1"
    DEFVAL { 15 }
    ::= { lecConfigEntry 15 }

lecExpectedArpResponseTime OBJECT-TYPE
    SYNTAX INTEGER(1..30)
--  Units
--    seconds
    ACCESS read-write
    STATUS mandatory
    DESCRIPTION
        "C20 Expected LE_ARP Reponse Time.  The maximum time
             that the LEC expects an LE_ARP_REQUEST/
             LE_ARP_RESPONSE cycle to take.  Used for retries
             and verifies.
        
         This time value is expressed in seconds."
    REFERENCE
        "ATM Forum LAN Emulation Over ATM Specification, V1.0
         and V2.0, Section 5.1.1"
    DEFVAL { 1 }
    ::= { lecConfigEntry 16 }

lecFlushTimeOut OBJECT-TYPE
    SYNTAX INTEGER(1..4)
--  Units
--    seconds
    ACCESS read-write
    STATUS mandatory
    DESCRIPTION
        "C21 Flush Time-out.  Time limit to wait to receive a
             LE_FLUSH_RESPONSE after the LE_FLUSH_REQUEST has
             been sent before taking recovery action.
        
         This time value is expressed in seconds."
    REFERENCE
        "ATM Forum LAN Emulation Over ATM Specification, V1.0
         and V2.0, Section 5.1.1"
    DEFVAL { 4 }
    ::= { lecConfigEntry 17 }

lecPathSwitchingDelay OBJECT-TYPE
    SYNTAX INTEGER(1..8)
--  Units
--    seconds
    ACCESS read-write
    STATUS mandatory
    DESCRIPTION
        "C22 Path Switching Delay.  The time since sending a
             frame to the BUS after which the LE Client may
             assume that the frame has been either discarded
             or delivered to the recipient.  May be used to
             bypass the Flush protocol.
        
         This time value is expressed in seconds."
    REFERENCE
        "ATM Forum LAN Emulation Over ATM Specification, V1.0
         and V2.0, Section 5.1.1"
    DEFVAL { 6 }
    ::= { lecConfigEntry 18 }

lecLocalSegmentID OBJECT-TYPE
    SYNTAX INTEGER(0..4095)
    ACCESS read-write
    STATUS deprecated
    DESCRIPTION
        "C23 Local Segment ID.  The segment ID of the emulated
             LAN.  This is only required for IEEE 802.5 clients
             that are Source Routing bridges.
        
         This object has been deprecated and replaced by a pair
         of Config/Actual objects.  It shouldn't be implemented
         except as required for backwards compatibility."
    REFERENCE
        "ATM Forum LAN Emulation Over ATM Specification, V1.0,
         Section 5.1.1"
    ::= { lecConfigEntry 19 }

lecMulticastSendType OBJECT-TYPE
    SYNTAX INTEGER {
        bestEffort(1),
        variableBitRate(2),
        constantBitRate(3)
        }
    ACCESS read-write
    STATUS mandatory
    DESCRIPTION
        "C24 Multicast Send VCC Type.  Signalling parameter
             that SHOULD be used by the LE Client when
             establishing the Multicast Send VCC.
        
             This is the method to be used by the LE Client
             when specifying traffic parameters when it sets
             up the Multicast Send VCC for this emulated LAN."
    REFERENCE
        "ATM Forum LAN Emulation Over ATM Specification, V1.0
         and V2.0, Section 5.1.1"
    ::= { lecConfigEntry 20 }

lecMulticastSendAvgRate OBJECT-TYPE
    SYNTAX Integer32
--  Units
--    cells per second
    ACCESS read-write
    STATUS mandatory
    DESCRIPTION
        "C25 Multicast Send VCC AvgRate.  Signalling parameter
             that SHOULD be used by the LE Client when
             establishing the Multicast Send VCC.
        
             Forward and Backward Sustained Cell Rate to be
             requested by LE Client when setting up Multicast
             Send VCC, if using Variable bit rate codings."
    REFERENCE
        "ATM Forum LAN Emulation Over ATM Specification, V1.0
         and V2.0, Section 5.1.1"
    ::= { lecConfigEntry 21 }

lecMulticastSendPeakRate OBJECT-TYPE
    SYNTAX Integer32
--  Units
--    cells per second
    ACCESS read-write
    STATUS mandatory
    DESCRIPTION
        "C26 Multicast Send VCC PeakRate.  Signalling parameter
             that SHOULD be used by the LE Client when
             establishing the Multicast Send VCC.
        
             Forward and Backward Peak Cell Rate to be
             requested by LE Client when setting up the
             Multicast Send VCC when using either Variable or
             Constant bit rate codings."
    REFERENCE
        "ATM Forum LAN Emulation Over ATM Specification, V1.0
         and V2.0, Section 5.1.1"
    ::= { lecConfigEntry 22 }

lecConnectionCompleteTimer OBJECT-TYPE
    SYNTAX INTEGER(1..10)
--  Units
--    seconds
    ACCESS read-write
    STATUS mandatory
    DESCRIPTION
        "C28 Connection Complete Timer.  Optional.  In
             Connection Establishment this is the time period
             in which data or a READY_IND message is expected
             from a Calling Party.
        
         This time value is expressed in seconds."
    REFERENCE
        "ATM Forum LAN Emulation Over ATM Specification, V1.0
         and V2.0, Section 5.1.1"
    DEFVAL { 4 }
    ::= { lecConfigEntry 23 }

lecConfigLecsAtmAddress OBJECT-TYPE
    SYNTAX AtmLaneAddress
--    Rsyntax OCTET STRING(SIZE(0 | 20))
    ACCESS read-write
    STATUS mandatory
    DESCRIPTION
        "LE Configuration Server ATM address.
        
         A manually-configured LECS address that this client
         may use in its attempts at auto-configuration."
    REFERENCE
        "LANE 1.0 addendum"
    ::= { lecConfigEntry 24 }

lecInitialControlTimeout OBJECT-TYPE
    SYNTAX INTEGER(1..10)
--  Units
--    seconds
    ACCESS read-write
    STATUS mandatory
    DESCRIPTION
        "C7i  Initial Control Time-out.
        
         In LANE V2.0, control time-out consists of an initial
         time-out of C7i seconds, a retry multiplier (or
         logarithmic back-off base) of C7x, and a cumulative
         maximum time-out of C7 seconds."
    REFERENCE
        "ATM Forum LAN Emulation V2.0 LUNI specification,
         Section 5.1.1"
    DEFVAL { 5 }
    ::= { lecConfigEntry 25 }

lecControlTimeoutMultiplier OBJECT-TYPE
    SYNTAX INTEGER(2..5)
--  Units
--    seconds
    ACCESS read-write
    STATUS mandatory
    DESCRIPTION
        "C7x  Control Time-out Multiplier.
        
         In LANE V2.0, control time-out consists of an initial
         time-out of C7i seconds, a retry multiplier (or
         logarithmic back-off base) of C7x, and a cumulative
         maximum time-out of C7 seconds."
    REFERENCE
        "ATM Forum LAN Emulation V2.0 LUNI specification,
         Section 5.1.1"
    DEFVAL { 2 }
    ::= { lecConfigEntry 26 }

lecV2MaxUnknownFrameCount OBJECT-TYPE
    SYNTAX INTEGER(1..20)
--  Units
--    frames
    ACCESS read-write
    STATUS mandatory
    DESCRIPTION
        "C10 Maximum Unknown Frame Count.  See the description
             of lecMaxUnknownFrameTime above.
        
         This object may be used with both LANE V1.0 clients &
         LANE V2.0 clients.  For LANE V1.0 clients, this value
         should be in the range 1..10, with a default of 1."
    REFERENCE
        "ATM Forum LAN Emulation V2.0 LUNI specification,
         Section 5.1.1"
    DEFVAL { 10 }
    ::= { lecConfigEntry 27 }

lecConfigLocalSegmentID OBJECT-TYPE
    SYNTAX INTEGER(0..4095)
    ACCESS read-write
    STATUS mandatory
    DESCRIPTION
        "C23c Local Segment ID (configured).  The segment ID of
              the emulated LAN.  This is only required for IEEE
              802.5 clients that are Source Routing bridges.
        
         A setting which this client will use the next time it
         returns to the Initial State.
        
         This MIB object will not be overwritten with the new
         value from a LE_{JOIN,CONFIGURE}_RESPONSE.  Instead,
         lecActualLocalSegmentID will be."
    REFERENCE
        "ATM Forum LAN Emulation V2.0 LUNI specification,
         Section 5.1.1"
    ::= { lecConfigEntry 28 }

lecConfigV2Capable OBJECT-TYPE
    SYNTAX TruthValue
--    Rsyntax INTEGER {
--        true(1),
--        false(2)
--        }
    ACCESS read-write
    STATUS mandatory
    DESCRIPTION
        "C29c  V2 Capable (configured).
        
         A setting which this client will use the next time it
         returns to the Initial State.
        
         Indicates whether this client is set up to behave as
         a LANE V2 client.
        
         This MIB object will not be overwritten with the new
         value from a LE_{JOIN,CONFIGURE}_RESPONSE.  Instead,
         lecActualV2Capable will be."
    REFERENCE
        "ATM Forum LAN Emulation V2.0 LUNI specification,
         Section 5.1.1"
    ::= { lecConfigEntry 29 }

lecConfigSelectiveMulticast OBJECT-TYPE
    SYNTAX TruthValue
--    Rsyntax INTEGER {
--        true(1),
--        false(2)
--        }
    ACCESS read-write
    STATUS mandatory
    DESCRIPTION
        "C32c  Selective Multicast (configured).
        
         A setting which this client will use the next time it
         returns to the Initial State.
        
         Indicates if this client is configured to register to
         receive specific multicast destination MAC addresses.
         Must not be 'true' if lecConfigV2Capable is 'false'.
        
         This MIB object will not be overwritten with the new
         value from a LE_{JOIN,CONFIGURE}_RESPONSE.  Instead,
         lecActualSelectiveMulticast will be."
    REFERENCE
        "ATM Forum LAN Emulation V2.0 LUNI specification,
         Section 5.1.1"
    ::= { lecConfigEntry 30 }

lecForwardDisconnectTimeout OBJECT-TYPE
    SYNTAX INTEGER(10..300)
--  Units
--    seconds
    ACCESS read-write
    STATUS mandatory
    DESCRIPTION
        "C33  Forward Disconnect Time-out
        
         If the LE Client detects that the BUS has had no
         Multicast Forward VCCs to the LE Client for time
         Forward Disconnect Time-out, the LE Client MUST
         disconnect from the BUS and try to re-establish
         a new connection."
    REFERENCE
        "ATM Forum LAN Emulation V2.0 LUNI specification,
         Section 5.1.1"
    DEFVAL { 60 }
    ::= { lecConfigEntry 31 }

lecConfigLLCMultiplexCapable OBJECT-TYPE
    SYNTAX TruthValue
--    Rsyntax INTEGER {
--        true(1),
--        false(2)
--        }
    ACCESS read-write
    STATUS mandatory
    DESCRIPTION
        "C34c  LLC Multiplex Capable (configured).
        
         A setting which this client will use the next time it
         returns to the Initial State.
        
         Gives a network manager an optional method to disable
         LLC multiplexing on a LANE V2 client that supports it.
         Cannot be used to enable LLC multiplexing on products
         that do not support it.
        
         This MIB object will not be overwritten with the new
         value from a LE_{JOIN,CONFIGURE}_RESPONSE.  Instead,
         lecActualLLCMultiplexCapable will be."
    REFERENCE
        "ATM Forum LAN Emulation V2.0 LUNI specification,
         Section 5.1.1"
    ::= { lecConfigEntry 32 }

lecMinReconfigureDelay OBJECT-TYPE
    SYNTAX INTEGER(1..10000)
--  Units
--    milliseconds
    ACCESS read-write
    STATUS mandatory
    DESCRIPTION
        "C37  Minimum Reconfigure Delay.
        
         The minimum time that a LE client must wait before
         retrying reconfiguration.  This setting must be
         less than or equal to lecMaxReconfigureDelay."
    REFERENCE
        "ATM Forum LAN Emulation V2.0 LUNI specification,
         Section 5.1.1"
    DEFVAL { 1 }
    ::= { lecConfigEntry 33 }

lecMaxReconfigureDelay OBJECT-TYPE
    SYNTAX INTEGER(1..10000)
--  Units
--    milliseconds
    ACCESS read-write
    STATUS mandatory
    DESCRIPTION
        "C38  Maximum Reconfigure Delay.
        
         The maximum time that a LE client must wait before
         retrying reconfiguration.  This setting must be
         greater than or equal to lecMinReconfigureDelay."
    REFERENCE
        "ATM Forum LAN Emulation V2.0 LUNI specification,
         Section 5.1.1"
    DEFVAL { 5000 }
    ::= { lecConfigEntry 34 }

lecMaxBusConnectRetries OBJECT-TYPE
    SYNTAX INTEGER(0..2)
    ACCESS read-write
    STATUS mandatory
    DESCRIPTION
        "C39  Maximum BUS Connect Retries.
        
         The maximum number of times that a LE Client can try
         to establish the Default Multicast Send VCC before
         returning to the configuration procedure."
    REFERENCE
        "ATM Forum LAN Emulation V2.0 LUNI specification,
         Section 5.1.1"
    DEFVAL { 1 }
    ::= { lecConfigEntry 35 }

lecTokenRingExplorerExclude OBJECT-TYPE
    SYNTAX TruthValue
--    Rsyntax INTEGER {
--        true(1),
--        false(2)
--        }
    ACCESS read-write
    STATUS mandatory
    DESCRIPTION
        "C40  Token Ring Explorer Frame Exclude.
        
         This indicates whether or not the LE Client wishes to
         receive Token Ring explorer frames other than those
         directed to one of its registered MAC addresses.
         Normally, only bridges need to receive such explorer
         frames.  This parameter only applies to token-ring
         ELANs.  This parameter MUST NOT change without
         restarting the Configure phase."
    REFERENCE
        "ATM Forum LAN Emulation V2.0 LUNI specification,
         Section 5.1.1"
    ::= { lecConfigEntry 36 }

lecStatusTable OBJECT-TYPE
    SYNTAX SEQUENCE OF LecStatusEntry
    ACCESS not-accessible
    STATUS mandatory
    DESCRIPTION
        "A read-only table containing identification, status,
         and operational information about the LAN Emulation
         Clients this agent manages."
    ::= { leClientMIBObjects 2 }

lecStatusEntry OBJECT-TYPE
    SYNTAX LecStatusEntry
    ACCESS not-accessible
    STATUS mandatory
    DESCRIPTION
        "Each table entry contains information about one LAN
         Emulation Client."
    INDEX { lecIndex }
-- Augments lecConfigEntry
    ::= { lecStatusTable 1 }

LecStatusEntry ::= SEQUENCE {
    lecIfIndex InterfaceIndex,
    lecPrimaryAtmAddress AtmLaneAddress,
    lecID INTEGER,
    lecInterfaceState LecState,
    lecLastFailureRespCode INTEGER,
    lecLastFailureState LecState,
    lecProtocol INTEGER,
    lecVersion INTEGER,
    lecTopologyChange TruthValue,
    lecConfigServerAtmAddress AtmLaneAddress,
    lecConfigSource INTEGER,
    lecActualLanType LecDataFrameFormat,
    lecActualMaxDataFrameSize LecDataFrameSize,
    lecActualLanName DisplayString,
    lecActualLesAtmAddress AtmLaneAddress,
    lecProxyClient TruthValue,
    lecActualLocalSegmentID INTEGER,
    lecActualV2Capable TruthValue,
    lecElanID Integer32,
    lecActualSelectiveMulticast TruthValue,
    lecActualLLCMultiplexCapable TruthValue,
    lecPreferredLesAddress AtmLaneAddress,
    lecStoresServiceCategories TruthValue
    }

lecIfIndex OBJECT-TYPE
    SYNTAX InterfaceIndex
--    Rsyntax Integer32
    ACCESS read-only
    STATUS mandatory
    DESCRIPTION
        "This object identifies the logical interface number
         ('ifIndex') assigned to this client, and is used to
         identify corresponding rows in the Interfaces MIB.
        
         Note that re-initialization of the management agent
         may cause a client's 'lecIfIndex' to change."
    ::= { lecStatusEntry 1 }

lecPrimaryAtmAddress OBJECT-TYPE
    SYNTAX AtmLaneAddress
--    Rsyntax OCTET STRING(SIZE(0 | 20))
    ACCESS read-only
    STATUS mandatory
    DESCRIPTION
        "C1  LE Client's ATM Addresses.
        
         The primary ATM address of this LAN Emulation Client.
         This address is used to establish the Control Direct
         and Multicast Send VCCs, and may also be used to set
         up Data Direct VCCs.
        
         A client may have additional ATM addresses for use
         with Data Direct VCCs.  These addresses are readable
         via the lecAtmAddressTable."
    REFERENCE
        "ATM Forum LAN Emulation Over ATM Specification, V1.0
         and V2.0, Section 5.1.1"
    ::= { lecStatusEntry 2 }

lecID OBJECT-TYPE
    SYNTAX INTEGER(0..65279)
    ACCESS read-only
    STATUS mandatory
    DESCRIPTION
        "C14 LE Client Identifier.  Each LE Client requires a
             LE Client Identifier (LECID) assigned by the LE
             Server during the Join phase.  The LECID is placed
             in control requests by the LE Client and MAY be
             used for echo suppression on multicast data frames
             sent by that LE Client.  This value MUST NOT
             change without terminating the LE Client and
             returning to the Initial state.  A valid LECID
             MUST be in the range X'0001' through X'FEFF'.
        
         The value of this object is only meaningful for a LEC
         that is connected to a LES.  For a LEC which does not
         belong to an emulated LAN, the value of this object
         is defined to be 0."
    REFERENCE
        "ATM Forum LAN Emulation Over ATM Specification, V1.0
         and V2.0, Section 5.1.1"
    ::= { lecStatusEntry 3 }

lecInterfaceState OBJECT-TYPE
    SYNTAX LecState
--    Rsyntax INTEGER {
--        initialState(1),
--        lecsConnect(2),
--        configure(3),
--        join(4),
--        initialRegistration(5),
--        busConnect(6),
--        operational(7)
--        }
    ACCESS read-only
    STATUS mandatory
    DESCRIPTION
        "The current state of the LAN Emulation Client.
        
         Note that 'ifOperStatus' is defined to be 'up' when,
         and only when, 'lecInterfaceState' is 'operational'."
    REFERENCE
        "ATM Forum LAN Emulation Over ATM Specification, V1.0,
         Section 2.3.1"
    ::= { lecStatusEntry 4 }

lecLastFailureRespCode OBJECT-TYPE
    SYNTAX INTEGER {
        none(1),
        timeout(2),
        undefinedError(3),
        versionNotSupported(4),
        invalidRequestParameters(5),
        duplicateLanDestination(6),
        duplicateAtmAddress(7),
        insufficientResources(8),
        accessDenied(9),
        invalidRequesterId(10),
        invalidLanDestination(11),
        invalidAtmAddress(12),
        noConfiguration(13),
        leConfigureError(14),
        insufficientInformation(15),
        tlvNotFound(16)
        }
    ACCESS read-only
    STATUS mandatory
    DESCRIPTION
        "Status code from the last failed Configure response
         or Join response.  Failed responses are those for
         which the LE_CONFIGURE_RESPONSE / LE_JOIN_RESPONSE
         frame contains a non-zero code, or fails to arrive
         within a timeout period.
        
         If none of this client's requests have failed, this
         object has the value 'none'.
        
         If the failed response contained a STATUS code that
         is not defined in the LAN Emulation specification,
         this object has the value 'undefinedError'.
        
         The value 'timeout' is self-explanatory.
        
         Other failure codes correspond to those defined in
         the specification, although they may have different
         numeric values."
    REFERENCE
        "ATM Forum LAN Emulation Over ATM Specification, V1.0
         and V2.0, Section 4.2, Table 13"
    ::= { lecStatusEntry 5 }

lecLastFailureState OBJECT-TYPE
    SYNTAX LecState
--    Rsyntax INTEGER {
--        initialState(1),
--        lecsConnect(2),
--        configure(3),
--        join(4),
--        initialRegistration(5),
--        busConnect(6),
--        operational(7)
--        }
    ACCESS read-only
    STATUS mandatory
    DESCRIPTION
        "The state this client was in when it updated the
         'lecLastFailureRespCode'.
        
         If 'lecLastFailureRespCode' is 'none', this object
         has the value initialState(1)."
    REFERENCE
        "ATM Forum LAN Emulation Over ATM Specification, V1.0,
         Section 2.3.1"
    ::= { lecStatusEntry 6 }

lecProtocol OBJECT-TYPE
    SYNTAX INTEGER(1..255)
    ACCESS read-only
    STATUS mandatory
    DESCRIPTION
        "The LAN Emulation protocol which this client supports,
         and specifies in its LE_JOIN_REQUESTs."
    REFERENCE
        "ATM Forum LAN Emulation Over ATM Specification, V1.0,
         Section 4.2"
    ::= { lecStatusEntry 7 }

lecVersion OBJECT-TYPE
    SYNTAX INTEGER(1..255)
    ACCESS read-only
    STATUS mandatory
    DESCRIPTION
        "The LAN Emulation protocol version which this client
         supports, and specifies in its LE_JOIN_REQUESTs."
    REFERENCE
        "ATM Forum LAN Emulation Over ATM Specification, V1.0,
         Section 4.2"
    ::= { lecStatusEntry 8 }

lecTopologyChange OBJECT-TYPE
    SYNTAX TruthValue
--    Rsyntax INTEGER {
--        true(1),
--        false(2)
--        }
    ACCESS read-only
    STATUS mandatory
    DESCRIPTION
        "C19 Topology Change.  Boolean indication that the LE
             Client is using the Forward Delay Time C18,
             instead of the Aging Time C17, to age non-local
             entries in its LE_ARP cache C16.
        
         For a client which is not connected to the LES, this
         object is defined to have the value 'false'."
    REFERENCE
        "ATM Forum LAN Emulation Over ATM Specification, V1.0
         and V2.0, Section 5.1.1"
    ::= { lecStatusEntry 9 }

lecConfigServerAtmAddress OBJECT-TYPE
    SYNTAX AtmLaneAddress
--    Rsyntax OCTET STRING(SIZE(0 | 20))
    ACCESS read-only
    STATUS mandatory
    DESCRIPTION
        "The ATM address of the LAN Emulation Configuration
         Server (if known) or the empty string (otherwise)."
    ::= { lecStatusEntry 10 }

lecConfigSource OBJECT-TYPE
    SYNTAX INTEGER {
        gotAddressViaIlmi(1),
        usedWellKnownAddress(2),
        usedLecsPvc(3),
        didNotUseLecs(4),
        usedConfiguredAddress(5),
        configInProgress(6)
        }
    ACCESS read-only
    STATUS mandatory
    DESCRIPTION
        "Indicates whether this LAN Emulation Client used the
         LAN Emulation Configuration Server, and, if so, what
         method it used to establish the Configuration Direct
         VCC.
        
         The value 'configInProgress' indicates configuration
         is in progress, and may be used to troubleshoot LECs
         that get stuck in the configuration phase."
    REFERENCE
        "ATM Forum LAN Emulation Over ATM Specification, V1.0,
         Section 5.2; LANE 1.0 and LEC MIB 1.0 addendums"
    ::= { lecStatusEntry 11 }

lecActualLanType OBJECT-TYPE
    SYNTAX LecDataFrameFormat
--    Rsyntax INTEGER {
--        unspecified(1),
--        aflane8023(2),
--        aflane8025(3)
--        }
    ACCESS read-only
    STATUS mandatory
    DESCRIPTION
        "C2  LAN Type.
        
         The data frame format that this LAN Emulation Client
         is using right now.  This may come from
        
             *  lecConfigLanType,
             *  the LAN Emulation Configuration Server, or
             *  the LAN Emulation Server
        
         This value is related to 'ifMtu' and 'ifType'.  See
         the LEC management specification for more details."
    REFERENCE
        "ATM Forum LAN Emulation Over ATM Specification, V1.0
         and V2.0, Section 5.1.1"
    ::= { lecStatusEntry 12 }

lecActualMaxDataFrameSize OBJECT-TYPE
    SYNTAX LecDataFrameSize
--    Rsyntax INTEGER {
--        unspecified(1),
--        max1516(2),
--        max4544(3),
--        max9234(4),
--        max18190(5),
--        max1580(6)
--        }
    ACCESS read-only
    STATUS mandatory
    DESCRIPTION
        "C3  Maximum Data Frame Size.
        
         The maximum data frame size that this LAN Emulation
         client is using right now.  This may come from
        
             *  lecConfigMaxDataFrameSize,
             *  the LAN Emulation Configuration Server, or
             *  the LAN Emulation Server                     "
    REFERENCE
        "ATM Forum LAN Emulation Over ATM Specification, V1.0
         and V2.0, Section 5.1.1"
    ::= { lecStatusEntry 13 }

lecActualLanName OBJECT-TYPE
    SYNTAX DisplayString(SIZE(0..32))
--    Rsyntax OCTET STRING(SIZE(0..32))
    ACCESS read-only
    STATUS mandatory
    DESCRIPTION
        "C5  ELAN Name.
        
         The identity of the emulated LAN which this client
         last joined, or wishes to join.  This may come from
        
             *  lecConfigLanName,
             *  the LAN Emulation Configuration Server, or
             *  the LAN Emulation Server                     "
    REFERENCE
        "ATM Forum LAN Emulation Over ATM Specification, V1.0
         and V2.0, Section 5.1.1"
    ::= { lecStatusEntry 14 }

lecActualLesAtmAddress OBJECT-TYPE
    SYNTAX AtmLaneAddress
--    Rsyntax OCTET STRING(SIZE(0 | 20))
    ACCESS read-only
    STATUS mandatory
    DESCRIPTION
        "C9  LE Server ATM Address.
        
         The LAN Emulation Server address currently in use or
         most recently attempted.
        
         If no LAN Emulation Server attachment has been tried,
         this object's value is the zero-length string."
    REFERENCE
        "ATM Forum LAN Emulation Over ATM Specification, V1.0
         and V2.0, Section 5.1.1"
    ::= { lecStatusEntry 15 }

lecProxyClient OBJECT-TYPE
    SYNTAX TruthValue
--    Rsyntax INTEGER {
--        true(1),
--        false(2)
--        }
    ACCESS read-only
    STATUS mandatory
    DESCRIPTION
        "C4  Proxy.
        
         Indicates whether this client is acting as a proxy.
        
         Proxy clients are allowed to represent unregistered
         MAC addresses and route descriptors, and receive
         copies of LE_ARP_REQUEST frames for such LAN
         Destinations."
    REFERENCE
        "ATM Forum LAN Emulation Over ATM Specification, V1.0
         and V2.0, Section 5.1.1"
    ::= { lecStatusEntry 16 }

lecActualLocalSegmentID OBJECT-TYPE
    SYNTAX INTEGER(0..4095)
    ACCESS read-only
    STATUS mandatory
    DESCRIPTION
        "C23 Local Segment ID.  The segment ID of the emulated
             LAN.  This is only required for IEEE 802.5 clients
             that are Source Routing bridges."
    REFERENCE
        "ATM Forum LAN Emulation V2.0 LUNI specification,
         Section 5.1.1"
    ::= { lecStatusEntry 17 }

lecActualV2Capable OBJECT-TYPE
    SYNTAX TruthValue
--    Rsyntax INTEGER {
--        true(1),
--        false(2)
--        }
    ACCESS read-only
    STATUS mandatory
    DESCRIPTION
        "C29  V2 Capable.
        
         If set, the LE Client must exhibit LANE v2 behavior
         where it differs in its requirements from LANE v1
         behavior.  If clear, the LE Client must exhibit LANE
         v1 behavior in those cases.  This variable is set or
         cleared according to the presence or absence of the
         V2 Required FLAGS bit in the LE_JOIN_RESPONSE."
    REFERENCE
        "ATM Forum LAN Emulation V2.0 LUNI specification,
         Section 5.1.1"
    ::= { lecStatusEntry 18 }

lecElanID OBJECT-TYPE
    SYNTAX Integer32
    ACCESS read-only
    STATUS mandatory
    DESCRIPTION
        "C31  ELAN-ID.
        
         The ELAN-ID to be used in all LANE LLC-multiplexed
         data frames sent or received by this client.  This
         object takes the value 0 if the LES is a LANE V1.0
         LES.  The initial value of this object is 0."
    REFERENCE
        "ATM Forum LAN Emulation V2.0 LUNI specification,
         Section 5.1.1"
    ::= { lecStatusEntry 19 }

lecActualSelectiveMulticast OBJECT-TYPE
    SYNTAX TruthValue
--    Rsyntax INTEGER {
--        true(1),
--        false(2)
--        }
    ACCESS read-only
    STATUS mandatory
    DESCRIPTION
        "C32  Selective Multicast.
        
         This indicates whether or not the LE Client will
         register to receive specific multicast destination
         MAC addresses.  If this flag is set, the LE Client
         MUST issue a LE_REGISTER_REQUEST for all of the
         multicast or group MAC adddresses in C15, except
         for the broadcast MAC address.  If this variable is
         clear, the LE Client MUST NOT issue a
         LE_REGISTER_REQUEST for any multicast MAC address,
         and can expect to receive all multicast frames from
         the BUS."
    REFERENCE
        "ATM Forum LAN Emulation V2.0 LUNI specification,
         Section 5.1.1"
    ::= { lecStatusEntry 20 }

lecActualLLCMultiplexCapable OBJECT-TYPE
    SYNTAX TruthValue
--    Rsyntax INTEGER {
--        true(1),
--        false(2)
--        }
    ACCESS read-only
    STATUS mandatory
    DESCRIPTION
        "C34  LLC Multiplex Capable.
        
         If set, this variable indicates that the LE Client
         can accept and process LLC-multiplexed Data Direct
         VCCs.  If clear, it indicates that the LE Client
         will refuse to accept LLC-multiplexed Data Direct
         VCCs.  This variable MUST be clear if the LE Client
         is connected to a LANE v1 LES."
    REFERENCE
        "ATM Forum LAN Emulation V2.0 LUNI specification,
         Section 5.1.1"
    ::= { lecStatusEntry 21 }

lecPreferredLesAddress OBJECT-TYPE
    SYNTAX AtmLaneAddress
--    Rsyntax OCTET STRING(SIZE(0 | 20))
    ACCESS read-only
    STATUS mandatory
    DESCRIPTION
        "C35  Preferred LES Address.
        
         The ATM address of the preferred LE Server.  This
         variable is set during the Configuration phase by
         copying the contents of the Preferred LES TLV
         received in the LE_CONFIGURE_RESPONSE."
    REFERENCE
        "ATM Forum LAN Emulation V2.0 LUNI specification,
         Section 5.1.1"
    ::= { lecStatusEntry 22 }

lecStoresServiceCategories OBJECT-TYPE
    SYNTAX TruthValue
--    Rsyntax INTEGER {
--        true(1),
--        false(2)
--        }
    ACCESS read-only
    STATUS mandatory
    DESCRIPTION
        "Indicates whether or not the client saves Service
         Category TLV data from LE_ARP_RESPONSEs and makes
         it available through leArpTable and leRDArpTable."
    REFERENCE
        "LAN Emulation Over ATM Version 2 - LUNI Specification,
         Annex A (LAN Emulation Control Frame TLVs)"
    ::= { lecStatusEntry 23 }

lecMappingTable OBJECT-TYPE
    SYNTAX SEQUENCE OF LecMappingEntry
    ACCESS not-accessible
    STATUS mandatory
    DESCRIPTION
        "A table mapping the 'ifIndex' values of 'aflane8023'
         and 'aflane8025' interfaces to the 'lecIndex' values
         of the corresponding LAN Emulation Clients."
    ::= { leClientMIBObjects 3 }

lecMappingEntry OBJECT-TYPE
    SYNTAX LecMappingEntry
    ACCESS not-accessible
    STATUS mandatory
    DESCRIPTION
        "Each row describes one ifIndex --> lecIndex mapping."
    INDEX { ifIndex }
    ::= { lecMappingTable 1 }

LecMappingEntry ::= SEQUENCE {
    lecMappingIndex INTEGER
    }

lecMappingIndex OBJECT-TYPE
    SYNTAX INTEGER(1..2147483647)
    ACCESS read-only
    STATUS mandatory
    DESCRIPTION
        "The 'lecIndex' of the client which implements the
         specified interface."
    ::= { lecMappingEntry 1 }

lecStatisticsTable OBJECT-TYPE
    SYNTAX SEQUENCE OF LecStatisticsEntry
    ACCESS not-accessible
    STATUS mandatory
    DESCRIPTION
        "An extension table containing traffic statistics for
         all the LAN Emulation Clients this host implements."
    ::= { leClientMIBObjects 4 }

lecStatisticsEntry OBJECT-TYPE
    SYNTAX LecStatisticsEntry
    ACCESS not-accessible
    STATUS mandatory
    DESCRIPTION
        "Each row in this table contains traffic statistics
         for one LAN Emulation client."
    INDEX { lecIndex }
-- Augments lecConfigEntry
    ::= { lecStatisticsTable 1 }

LecStatisticsEntry ::= SEQUENCE {
    lecArpRequestsOut Counter32,
    lecArpRequestsIn Counter32,
    lecArpRepliesOut Counter32,
    lecArpRepliesIn Counter32,
    lecControlFramesOut Counter32,
    lecControlFramesIn Counter32,
    lecSvcFailures Counter32,
    lecFlowFailures Counter32,
    lecEchoDiscards Counter32,
    lecFilteredMulticasts Counter32
    }

lecArpRequestsOut OBJECT-TYPE
    SYNTAX Counter32
    ACCESS read-only
    STATUS mandatory
    DESCRIPTION
        "The number of LE_ARP_REQUESTs sent over the LUNI by
         this LAN Emulation Client."
    ::= { lecStatisticsEntry 1 }

lecArpRequestsIn OBJECT-TYPE
    SYNTAX Counter32
    ACCESS read-only
    STATUS mandatory
    DESCRIPTION
        "The number of LE_ARP_REQUESTs received over the LUNI
         by this LAN Emulation Client.
        
         Requests may arrive on the Control Direct VCC or on
         the Control Distribute VCC, depending upon how the
         LES is implemented and the chances it has had for
         learning.  This counter covers both VCCs."
    ::= { lecStatisticsEntry 2 }

lecArpRepliesOut OBJECT-TYPE
    SYNTAX Counter32
    ACCESS read-only
    STATUS mandatory
    DESCRIPTION
        "The number of LE_ARP_RESPONSEs sent over the LUNI by
         this LAN Emulation Client."
    ::= { lecStatisticsEntry 3 }

lecArpRepliesIn OBJECT-TYPE
    SYNTAX Counter32
    ACCESS read-only
    STATUS mandatory
    DESCRIPTION
        "The number of LE_ARP_RESPONSEs received over the LUNI
         by this LAN Emulation Client.  This count includes
         all such replies, whether solicited or not.
        
         Replies may arrive on the Control Direct VCC or on
         the Control Distribute VCC, depending upon how the
         LES is implemented.  This counter covers both VCCs."
    ::= { lecStatisticsEntry 4 }

lecControlFramesOut OBJECT-TYPE
    SYNTAX Counter32
    ACCESS read-only
    STATUS mandatory
    DESCRIPTION
        "The total number of control packets sent by this
         LAN Emulation Client over the LUNI."
    ::= { lecStatisticsEntry 5 }

lecControlFramesIn OBJECT-TYPE
    SYNTAX Counter32
    ACCESS read-only
    STATUS mandatory
    DESCRIPTION
        "The total number of control packets received by this
         LAN Emulation Client over the LUNI."
    ::= { lecStatisticsEntry 6 }

lecSvcFailures OBJECT-TYPE
    SYNTAX Counter32
    ACCESS read-only
    STATUS mandatory
    DESCRIPTION
        "The total number of
        
             *  outgoing LAN Emulation SVCs which this client
                tried, but failed, to open;
        
             *  incoming LAN Emulation SVCs which this client
                tried, but failed to establish; and
        
             *  incoming LAN Emulation SVCs which this client
                rejected for protocol or security reasons.
        
         It does not include SVC failures for LLC-multiplexed
         connections."
    ::= { lecStatisticsEntry 7 }

lecFlowFailures OBJECT-TYPE
    SYNTAX Counter32
    ACCESS read-only
    STATUS mandatory
    DESCRIPTION
        "The total number of
        
             *  outgoing LLC-multiplexed LAN Emulation flows
                which this client tried, but failed, to open;
        
             *  incoming LLC-multiplexed LAN Emulation flows
                which this client did not accept / establish.
        
         Only failures of which the LEC is aware and which are
         clearly LANE-related need to be counted."
    ::= { lecStatisticsEntry 8 }

lecEchoDiscards OBJECT-TYPE
    SYNTAX Counter32
    ACCESS read-only
    STATUS mandatory
    DESCRIPTION
        "The number of incoming data frames which were thrown
         away because they were echo frames (e. g., copies of
         this client's own outgoing traffic).
        
         Such discards are a normal part of LAN Emulation and
         not a cause for alarm.  So this counter is mainly of
         interest for helping to estimate average frame size.
        
         Frames that are included in this count should not be
         included in ifInDiscards, so as to avoid setting off
         false alarms."
    ::= { lecStatisticsEntry 9 }

lecFilteredMulticasts OBJECT-TYPE
    SYNTAX Counter32
    ACCESS read-only
    STATUS mandatory
    DESCRIPTION
        "The number of incoming data frames which were thrown
         away by the client because they were for a multicast
         (or group) address upper-layer software didn't want.
        
         If this counter indicates that a LEC is being loaded
         down with an excessive number of unwanted multicasts,
         one possible solution is to install LECs and LES/BUS
         pairs with better support for selective multicasting.
        
         Frames that are included in this count should not be
         included in ifInDiscards, so as to avoid setting off
         false alarms."
    ::= { lecStatisticsEntry 10 }

lecServerVccTable OBJECT-TYPE
    SYNTAX SEQUENCE OF LecServerVccEntry
    ACCESS not-accessible
    STATUS mandatory
    DESCRIPTION
        "A table identifying the Control VCCs and Multicast
         VCCs for each LAN Emulation Client which this host
         implements.
        
         For LANE 2.0 clients, the table identifies Control
         VCCs and Default Multicast Send VCCs."
    ::= { leClientMIBObjects 5 }

lecServerVccEntry OBJECT-TYPE
    SYNTAX LecServerVccEntry
    ACCESS not-accessible
    STATUS mandatory
    DESCRIPTION
        "Each row in this table describes the Control VCCs
         and Multicast VCCs for one LEC."
    INDEX { lecIndex }
-- Augments lecConfigEntry
    ::= { lecServerVccTable 1 }

LecServerVccEntry ::= SEQUENCE {
    lecConfigDirectInterface LeConnectionInterface,
    lecConfigDirectVpi VpiInteger,
    lecConfigDirectVci VciInteger,
    lecControlDirectInterface LeConnectionInterface,
    lecControlDirectVpi VpiInteger,
    lecControlDirectVci VciInteger,
    lecControlDistributeInterface LeConnectionInterface,
    lecControlDistributeVpi VpiInteger,
    lecControlDistributeVci VciInteger,
    lecMulticastSendInterface LeConnectionInterface,
    lecMulticastSendVpi VpiInteger,
    lecMulticastSendVci VciInteger,
    lecMulticastForwardInterface LeConnectionInterface,
    lecMulticastForwardVpi VpiInteger,
    lecMulticastForwardVci VciInteger
    }

lecConfigDirectInterface OBJECT-TYPE
    SYNTAX LeConnectionInterface
--    Rsyntax INTEGER(0..2147483647)
    ACCESS read-only
    STATUS mandatory
    DESCRIPTION
        "The interface associated with the Configuration
         Direct VCC.  If no Configuration Direct VCC exists,
         this object has the value 0.  Otherwise, the objects
        
             ( lecConfigDirectInterface,
               lecConfigDirectVpi, lecConfigDirectVci )
        
         identify the circuit."
    REFERENCE
        "ATM Forum LAN Emulation Over ATM Specification, V1.0,
         Section 2.2.2.1.1"
    ::= { lecServerVccEntry 1 }

lecConfigDirectVpi OBJECT-TYPE
    SYNTAX VpiInteger
--    Rsyntax INTEGER(0..4095)
    ACCESS read-only
    STATUS mandatory
    DESCRIPTION
        "If the Configuration Direct VCC exists, this object
         contains the VPI which identifies that VCC at
         the point where it connects to this LE client.
        
         Otherwise, this object has the value 0."
    REFERENCE
        "ATM Forum LAN Emulation Over ATM Specification, V1.0,
         Section 2.2.2.1.1"
    ::= { lecServerVccEntry 2 }

lecConfigDirectVci OBJECT-TYPE
    SYNTAX VciInteger
--    Rsyntax INTEGER(0..65535)
    ACCESS read-only
    STATUS mandatory
    DESCRIPTION
        "If the Configuration Direct VCC exists, this object
         contains the VCI which identifies that VCC at
         the point where it connects to this LE client.
        
         Otherwise, this object has the value 0."
    REFERENCE
        "ATM Forum LAN Emulation Over ATM Specification, V1.0,
         Section 2.2.2.1.1"
    ::= { lecServerVccEntry 3 }

lecControlDirectInterface OBJECT-TYPE
    SYNTAX LeConnectionInterface
--    Rsyntax INTEGER(0..2147483647)
    ACCESS read-only
    STATUS mandatory
    DESCRIPTION
        "The interface associated with the Control Direct VCC.
         If no Control Direct VCC exists, this object has the
         value 0.  Otherwise, the objects
        
             ( lecControlDirectInterface,
               lecControlDirectVpi, lecControlDirectVci )
        
         identify the circuit."
    REFERENCE
        "ATM Forum LAN Emulation Over ATM Specification, V1.0,
         Section 2.2.2.1.2"
    ::= { lecServerVccEntry 4 }

lecControlDirectVpi OBJECT-TYPE
    SYNTAX VpiInteger
--    Rsyntax INTEGER(0..4095)
    ACCESS read-only
    STATUS mandatory
    DESCRIPTION
        "If the Control Direct VCC exists, this object
         contains the VPI which identifies that VCC at
         the point where it connects to this LE client.
        
         Otherwise, this object has the value 0."
    REFERENCE
        "ATM Forum LAN Emulation Over ATM Specification, V1.0,
         Section 2.2.2.1.2"
    ::= { lecServerVccEntry 5 }

lecControlDirectVci OBJECT-TYPE
    SYNTAX VciInteger
--    Rsyntax INTEGER(0..65535)
    ACCESS read-only
    STATUS mandatory
    DESCRIPTION
        "If the Control Direct VCC exists, this object
         contains the VCI which identifies that VCC at
         the point where it connects to this LE client.
        
         Otherwise, this object has the value 0."
    REFERENCE
        "ATM Forum LAN Emulation Over ATM Specification, V1.0,
         Section 2.2.2.1.2"
    ::= { lecServerVccEntry 6 }

lecControlDistributeInterface OBJECT-TYPE
    SYNTAX LeConnectionInterface
--    Rsyntax INTEGER(0..2147483647)
    ACCESS read-only
    STATUS mandatory
    DESCRIPTION
        "The interface associated with the Control Distribute
         VCC.  If no Control Distribute VCC has been set up to
         this client, this object has the value 0.  Otherwise,
         the objects
        
             ( lecControlDistributeInterface,
               lecControlDistributeVpi,
               lecControlDistributeVci )
        
         identify the circuit."
    REFERENCE
        "ATM Forum LAN Emulation Over ATM Specification, V1.0,
         Section 2.2.2.1.3"
    ::= { lecServerVccEntry 7 }

lecControlDistributeVpi OBJECT-TYPE
    SYNTAX VpiInteger
--    Rsyntax INTEGER(0..4095)
    ACCESS read-only
    STATUS mandatory
    DESCRIPTION
        "If the Control Distribute VCC exists, this object
         contains the VPI which identifies that VCC at the
         point where it connects to this LE client.
        
         Otherwise, this object has the value 0."
    REFERENCE
        "ATM Forum LAN Emulation Over ATM Specification, V1.0,
         Section 2.2.2.1.3"
    ::= { lecServerVccEntry 8 }

lecControlDistributeVci OBJECT-TYPE
    SYNTAX VciInteger
--    Rsyntax INTEGER(0..65535)
    ACCESS read-only
    STATUS mandatory
    DESCRIPTION
        "If the Control Distribute VCC exists, this object
         contains the VCI which identifies that VCC at the
         point where it connects to this LE client.
        
         Otherwise, this object contains the value 0."
    REFERENCE
        "ATM Forum LAN Emulation Over ATM Specification, V1.0,
         Section 2.2.2.1.3"
    ::= { lecServerVccEntry 9 }

lecMulticastSendInterface OBJECT-TYPE
    SYNTAX LeConnectionInterface
--    Rsyntax INTEGER(0..2147483647)
    ACCESS read-only
    STATUS mandatory
    DESCRIPTION
        "The interface associated with the Multicast Send
         VCC.  If no Multicast Send VCC exists, this object
         has the value 0.  Otherwise, the objects
        
             ( lecMulticastSendInterface,
               lecMulticastSendVpi, lecMulticastSendVci )
        
         identify the circuit."
    REFERENCE
        "ATM Forum LAN Emulation Over ATM Specification, V1.0,
         Section 2.2.2.2.2"
    ::= { lecServerVccEntry 10 }

lecMulticastSendVpi OBJECT-TYPE
    SYNTAX VpiInteger
--    Rsyntax INTEGER(0..4095)
    ACCESS read-only
    STATUS mandatory
    DESCRIPTION
        "If the Multicast Send VCC exists, this object
         contains the VPI which identifies that VCC at
         the point where it connects to this LE client.
        
         Otherwise, this object has the value 0."
    REFERENCE
        "ATM Forum LAN Emulation Over ATM Specification, V1.0,
         Section 2.2.2.2.2"
    ::= { lecServerVccEntry 11 }

lecMulticastSendVci OBJECT-TYPE
    SYNTAX VciInteger
--    Rsyntax INTEGER(0..65535)
    ACCESS read-only
    STATUS mandatory
    DESCRIPTION
        "If the Multicast Send VCC exists, this object
         contains the VCI which identifies that VCC at
         the point where it connects to this LE client.
        
         Otherwise, this object has the value 0."
    REFERENCE
        "ATM Forum LAN Emulation Over ATM Specification, V1.0,
         Section 2.2.2.2.2"
    ::= { lecServerVccEntry 12 }

lecMulticastForwardInterface OBJECT-TYPE
    SYNTAX LeConnectionInterface
--    Rsyntax INTEGER(0..2147483647)
    ACCESS read-only
    STATUS mandatory
    DESCRIPTION
        "For a LANE V1.0 client:
         -----------------------
         The interface associated with the Multicast Forward
         VCC.  If no Multicast Forward VCC has been set up to
         this client, this object has the value 0.  Otherwise,
         the objects
        
             ( lecMulticastForwardInterface,
               lecMulticastForwardVpi,
               lecMulticastForwardVci )
        
         identify the circuit.
        
         For a LANE V2.0 client in LANE 2.0 mode:
         ----------------------------------------
         The value 0.  There may not be a single VCC that can
         be identified as the 'default'."
    REFERENCE
        "ATM Forum LAN Emulation Over ATM Specification, V1.0,
         Section 2.2.2.2.3"
    ::= { lecServerVccEntry 13 }

lecMulticastForwardVpi OBJECT-TYPE
    SYNTAX VpiInteger
--    Rsyntax INTEGER(0..4095)
    ACCESS read-only
    STATUS mandatory
    DESCRIPTION
        "For a LANE V1.0 client:
         -----------------------
         If the Multicast Forward VCC exists, this object
         contains the VPI which identifies that VCC at the
         point where it connects to this LE client.
        
         Otherwise, this object has the value 0.
        
         For a LANE V2.0 client in LANE 2.0 mode:
         ----------------------------------------
         The value 0."
    REFERENCE
        "ATM Forum LAN Emulation Over ATM Specification, V1.0,
         Section 2.2.2.2.3"
    ::= { lecServerVccEntry 14 }

lecMulticastForwardVci OBJECT-TYPE
    SYNTAX VciInteger
--    Rsyntax INTEGER(0..65535)
    ACCESS read-only
    STATUS mandatory
    DESCRIPTION
        "For a LANE V1.0 client:
         -----------------------
         If the Multicast Forward VCC exists, this object
         contains the VCI which identifies that VCC at the
         point where it connects to this LE client.
        
         Otherwise, this object has the value 0.
        
         For a LANE V2.0 client in LANE 2.0 mode:
         ----------------------------------------
         The value 0."
    REFERENCE
        "ATM Forum LAN Emulation Over ATM Specification, V1.0,
         Section 2.2.2.2.3"
    ::= { lecServerVccEntry 15 }

lecAtmAddressTable OBJECT-TYPE
    SYNTAX SEQUENCE OF LecAtmAddressEntry
    ACCESS not-accessible
    STATUS mandatory
    DESCRIPTION
        "A table listing all of the ATM addresses belonging
         to this host's LAN Emulation Clients."
    ::= { leClientMIBObjects 6 }

lecAtmAddressEntry OBJECT-TYPE
    SYNTAX LecAtmAddressEntry
    ACCESS not-accessible
    STATUS mandatory
    DESCRIPTION
        "Each row in this table describes one of a client's
         ATM addresses."
    INDEX { lecIndex, lecAtmAddress }
    ::= { lecAtmAddressTable 1 }

LecAtmAddressEntry ::= SEQUENCE {
    lecAtmAddress AtmLaneAddress,
    lecAtmAddressStatus RowStatus,
    lecAtmAddressMuxed INTEGER
    }

lecAtmAddress OBJECT-TYPE
    SYNTAX AtmLaneAddress
--    Rsyntax OCTET STRING(SIZE(0 | 20))
    ACCESS not-accessible
    STATUS mandatory
    DESCRIPTION
        "The ATM address this row describes.  This could be
         either a primary address or a secondary address."
    ::= { lecAtmAddressEntry 1 }

lecAtmAddressStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Used to create and delete rows in this table.
        
         A management station may not change the status of a
         primary ATM address to 'notInService' or 'destroy'
         unless the client's ifAdminStatus is 'down', and the
         client's lecInterfaceState is 'initialState'.
        
         Secondary ATM addresses may be destroyed at any time
         permitted by the agent."
    ::= { lecAtmAddressEntry 2 }

lecAtmAddressMuxed OBJECT-TYPE
    SYNTAX INTEGER {
        muxed(1),
        notMuxed(2),
        both(3),
        none(4)
        }
    ACCESS read-write
    STATUS mandatory
    DESCRIPTION
        "Indicates what type(s) of connections the LEC is
         willing to establish at this ATM address."
    ::= { lecAtmAddressEntry 3 }

lecMacAddressTable OBJECT-TYPE
    SYNTAX SEQUENCE OF LecMacAddressEntry
    ACCESS not-accessible
    STATUS mandatory
    DESCRIPTION
        "This table contains entries for all of the registered
         MAC addresses belonging to this agent's LE clients.
        
         For all LANE clients, this includes
        
         C6  Local Unicast MAC Address(es).  Each LE Client has
             zero or more local unicast MAC addresses.  In an
             operational LE Client, every address in this
             variable MUST have been registered with the LE
             Server.  Two LE CLients joined to the same
             emulated LAN MUST NOT have the same local unicast
             MAC address.  A LE Client's MAC addresses may
             change during normal operations.  When answering
             a LE_ARP_REQUEST for any address in this list, the
             'Remote Address' bit in the FLAGS field of the
             LE_ARP_RESPONSE MUST be clear.
        
        For a LANE V2.0 client, this also includes <registered>
        multicast MAC addresses in C15."
    REFERENCE
        "ATM Forum LAN Emulation Over ATM Specification, V1.0
         and V2.0, Section 5.1.1"
    ::= { leClientMIBObjects 7 }

lecMacAddressEntry OBJECT-TYPE
    SYNTAX LecMacAddressEntry
    ACCESS not-accessible
    STATUS mandatory
    DESCRIPTION
        "Each table row describes a (MAC address, ATM address)
         pair registered for a particular client."
    INDEX { lecIndex, lecMacAddress }
    ::= { lecMacAddressTable 1 }

LecMacAddressEntry ::= SEQUENCE {
    lecMacAddress MacAddress,
    lecMacAddressAtmBinding AtmLaneAddress,
    lecMacAddressMuxedAtmBinding AtmLaneAddress,
    lecMacAddressServiceCategory INTEGER
    }

lecMacAddress OBJECT-TYPE
    SYNTAX MacAddress
--    Rsyntax OCTET STRING(SIZE(6))
    ACCESS not-accessible
    STATUS mandatory
    DESCRIPTION
        "A unicast or multicast MAC address that this LEC has
         registered with its LES.
        
         Note that the LANE V1.0 specification does not allow
         V1.0 clients to register multicast addresses."
    ::= { lecMacAddressEntry 1 }

lecMacAddressAtmBinding OBJECT-TYPE
    SYNTAX AtmLaneAddress
--    Rsyntax OCTET STRING(SIZE(0 | 20))
    ACCESS read-only
    STATUS mandatory
    DESCRIPTION
        "The non-multiplexed ATM address, if any, registered
         for 'lecMacAddress'."
    ::= { lecMacAddressEntry 2 }

lecMacAddressMuxedAtmBinding OBJECT-TYPE
    SYNTAX AtmLaneAddress
--    Rsyntax OCTET STRING(SIZE(0 | 20))
    ACCESS read-only
    STATUS mandatory
    DESCRIPTION
        "The LLC-multiplexed ATM address, if any, registered
         for 'lecMacAddress'."
    ::= { lecMacAddressEntry 3 }

lecMacAddressServiceCategory OBJECT-TYPE
    SYNTAX INTEGER(0..2147483647)
    ACCESS read-only
    STATUS mandatory
    DESCRIPTION
        "A bitmap describing the service categories which the
         LEC supports for this MAC address.
        
         The bitmap is larger than the LANE 2.0 specification
         requires, in case room is ever needed for expansion."
    REFERENCE
        "LAN Emulation Over ATM Version 2 - LUNI Specification,
         Annex A (LAN Emulation Control Frame TLVs)"
    ::= { lecMacAddressEntry 4 }

lecRouteDescrTable OBJECT-TYPE
    SYNTAX SEQUENCE OF LecRouteDescrEntry
    ACCESS not-accessible
    STATUS mandatory
    DESCRIPTION
        "This table lists all of the Local Route Descriptors
         which are registered by this host's LAN Emulation
         Clients.
        
         C8  Local Route Descriptor(s).  Local Route
             Descriptors exist only for source-routed IEEE
             802.5 LE Clients that are Source-Route Bridges.
             All Local Route Descriptors in any given emulated
             LAN MUST be unique.  A LE Client MAY have zero or
             more Local Route Descriptors and these Local Route
             Descriptors MAY change during normal operation.
             In an operational LE Client, every Local Route
             Descriptor in C8 MUST have been registered with
             the LE Server.  When answering a LE_ARP_REQUEST
             for any address in this list, the 'Remote Address'
             bit in the FLAGS field of the LE_ARP_RESPONSE MUST
             be clear."
    REFERENCE
        "ATM Forum LAN Emulation Over ATM Specification, V1.0
         and V2.0, Section 5.1.1"
    ::= { leClientMIBObjects 8 }

lecRouteDescrEntry OBJECT-TYPE
    SYNTAX LecRouteDescrEntry
    ACCESS not-accessible
    STATUS mandatory
    DESCRIPTION
        "Each table row describes a (Route Descriptor, ATM
         address) pair registered for a particular client."
    INDEX { lecIndex, lecRouteDescrSegmentID, lecRouteDescrBridgeNumber }
    ::= { lecRouteDescrTable 1 }

LecRouteDescrEntry ::= SEQUENCE {
    lecRouteDescrSegmentID INTEGER,
    lecRouteDescrBridgeNumber INTEGER,
    lecRouteDescrAtmBinding AtmLaneAddress,
    lecRouteDescrMuxedAtmBinding AtmLaneAddress,
    lecRouteDescrServiceCategory INTEGER
    }

lecRouteDescrSegmentID OBJECT-TYPE
    SYNTAX INTEGER(0..4095)
    ACCESS not-accessible
    STATUS mandatory
    DESCRIPTION
        "The LAN ID portion of the IEEE 802.5 route descriptor
         associated with this conceptual row."
    ::= { lecRouteDescrEntry 1 }

lecRouteDescrBridgeNumber OBJECT-TYPE
    SYNTAX INTEGER(0..15)
    ACCESS not-accessible
    STATUS mandatory
    DESCRIPTION
        "The Bridge Number portion of the IEEE 802.5 route
         descriptor associated with this conceptual row."
    ::= { lecRouteDescrEntry 2 }

lecRouteDescrAtmBinding OBJECT-TYPE
    SYNTAX AtmLaneAddress
--    Rsyntax OCTET STRING(SIZE(0 | 20))
    ACCESS read-only
    STATUS mandatory
    DESCRIPTION
        "The non-multiplexed ATM address, if any, registered
         for the IEEE 802.5 route descriptor
         ('lecRouteDescrSegmentID',
          'lecRouteDescrBridgeNumber')."
    ::= { lecRouteDescrEntry 3 }

lecRouteDescrMuxedAtmBinding OBJECT-TYPE
    SYNTAX AtmLaneAddress
--    Rsyntax OCTET STRING(SIZE(0 | 20))
    ACCESS read-only
    STATUS mandatory
    DESCRIPTION
        "The LLC-multiplexed ATM address, if any, registered
         for the IEEE 802.5 route descriptor
         ('lecRouteDescrSegmentID',
          'lecRouteDescrBridgeNumber')."
    ::= { lecRouteDescrEntry 4 }

lecRouteDescrServiceCategory OBJECT-TYPE
    SYNTAX INTEGER(0..2147483647)
    ACCESS read-only
    STATUS mandatory
    DESCRIPTION
        "A bitmap describing the service categories which the
         LEC supports for this route descriptor.
        
         The bitmap is larger than the LANE 2.0 specification
         requires, in case room is ever needed for expansion."
    REFERENCE
        "LAN Emulation Over ATM Version 2 - LUNI Specification,
         Annex A (LAN Emulation Control Frame TLVs)"
    ::= { lecRouteDescrEntry 5 }

leArpTable OBJECT-TYPE
    SYNTAX SEQUENCE OF LeArpEntry
    ACCESS not-accessible
    STATUS mandatory
    DESCRIPTION
        "This table provides access to an ATM LAN Emulation
         Client's MAC-to-ATM ARP cache.  It contains entries
         for unicast addresses and for the broadcast address.
        
         For LANE V2.0 clients whose C32 Selective Multicast
         flag is set, this table will also contain multicast
         address entries.
        
         C16 LE_ARP Cache.  A table of entries, each of which
             establishes a relationship between a LAN
             Destination external to the LE Client and the
             ATM address to which data frames for that LAN
             Destination will be sent."
    REFERENCE
        "ATM Forum LAN Emulation Over ATM Specification,
         Section 5.1.1"
    ::= { leClientMIBObjects 9 }

leArpEntry OBJECT-TYPE
    SYNTAX LeArpEntry
    ACCESS not-accessible
    STATUS mandatory
    DESCRIPTION
        "An ATM LAN Emulation ARP cache entry containing
         information about the binding of one MAC address
         to one ATM address."
    INDEX { lecIndex, leArpMacAddress }
    ::= { leArpTable 1 }

LeArpEntry ::= SEQUENCE {
    leArpMacAddress MacAddress,
    leArpAtmAddress AtmLaneAddress,
    leArpIsRemoteAddress TruthValue,
    leArpEntryType LeArpTableEntryType,
    leArpRowStatus RowStatus,
    leArpMuxedAtmAddress AtmLaneAddress,
    leArpServiceCategory INTEGER
    }

leArpMacAddress OBJECT-TYPE
    SYNTAX MacAddress
--    Rsyntax OCTET STRING(SIZE(6))
    ACCESS not-accessible
    STATUS mandatory
    DESCRIPTION
        "The MAC address for which this cache entry provides
         a translation.  Since ATM LAN Emulation uses an ARP
         protocol to locate the Broadcast and Unknown Server,
         the value of this object could be the broadcast MAC
         address.  Starting with LANE Version 2.0, the value
         could also be a multicast or group MAC address.
        
         Unicast MAC addresses should be unique within any
         given ATM Emulated LAN.  However, there's no
         requirement that they be unique across disjoint
         emulated LANs."
    ::= { leArpEntry 1 }

leArpAtmAddress OBJECT-TYPE
    SYNTAX AtmLaneAddress
--    Rsyntax OCTET STRING(SIZE(0 | 20))
    ACCESS read-write
    STATUS mandatory
    DESCRIPTION
        "The non-multiplexed LE Client or Broadcast/Multicast
         Service ATM address corresponding to the MAC address
         'leArpMacAddress'.
        
         This value may be determined through the use of the
         LE_ARP procedure, through source address learning,
         or through other mechanisms.
        
         Some agents may provide write access to this object,
         as part of their support for 'static' LE_ARP entries.
         The effect of attempting to write an ATM address to
         a 'learned' row is explicitly undefined.  Agents may
         disallow the write, accept the write and change the
         row's type, or even accept the write as-is."
    ::= { leArpEntry 2 }

leArpIsRemoteAddress OBJECT-TYPE
    SYNTAX TruthValue
--    Rsyntax INTEGER {
--        true(1),
--        false(2)
--        }
    ACCESS read-only
    STATUS mandatory
    DESCRIPTION
        "Indicates whether this entry is for a local or remote
         MAC address.
        
         In this context, 'local' means 'a MAC address that is
         local to the remote client', as opposed to 'one of my
         addresses'.
        
             true(1)
                 The address is believed to be remote - or its
                 local/remote status is unknown.
        
                 For an entry created via the LE_ARP mechanism,
                 this corresponds to the 'Remote address' flag
                 being set in the LE_ARP_RESPONSE.
        
                 During Topology Change periods, remote LE_ARP
                 entries generally age out faster than others.
                 Specifically, they are subject to the Forward
                 Delay Time as well as to the Aging Time.
        
             false(2)
                 The address is believed to be local - that is
                 to say, registered with the LES by the client
                 whose ATM address is leArpAtmAddress (and/or
                 leArpMuxedAtmAddress).
        
                 For an entry created via the LE_ARP mechanism,
                 this corresponds to the 'Remote address' flag
                 being cleared in the LE_ARP_RESPONSE."
    ::= { leArpEntry 3 }

leArpEntryType OBJECT-TYPE
    SYNTAX LeArpTableEntryType
--    Rsyntax INTEGER {
--        other(1),
--        learnedViaControl(2),
--        learnedViaData(3),
--        staticVolatile(4),
--        staticNonVolatile(5)
--        }
    ACCESS read-write
    STATUS mandatory
    DESCRIPTION
        "Indicates how this LE_ARP table entry was created and
         whether it is aged."
    DEFVAL { staticVolatile }
    ::= { leArpEntry 4 }

leArpRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Lets users create and delete LE_ARP cache entries,
         on systems that support this capability.
        
         Normally clients will maintain their LE_ARP caches
         automatically.  However, managers may occasionally
         want to create 'static' LE_ARP cache entries.
        
         Rules
        
           1.  Before a new row can become 'active', values
               must be supplied for the columnar objects
               leArpAtmAddress and leArpEntryType.
        
               The value for leArpAtmAddress may be a zero-
               length address if there is an ATM address in
               the leArpMuxedAtmAddress, and the LE_ARP row
               belongs to a LEC running LANE 2.0 or higher.
        
           2.  It is not necessary to set leArpRowStatus to
               'notInService' in order to modify a writable
               object in the same conceptual row.
        
           3.  LE_ARP entries whose status is 'notReady' or
               'notInService' will not be used to translate
               LAN Destinations to ATM Addresses.  However,
               clients may overwrite such entries with data
               obtained from other sources.  For example, a
               client which needed to transmit a data frame
               to a given MAC address (or via a given Route
               Descriptor) might find that its LE_ARP entry
               for the LAN Destination is 'notInService' or
               'notReady'.  The client might then act as if
               the LAN Destination was unknown - generating
               a LE_ARP_REQUEST, flooding the data frame to
               the BUS, and creating a new, 'active' LE_ARP
               cache entry based on the LE_ARP_RESPONSE."
    ::= { leArpEntry 5 }

leArpMuxedAtmAddress OBJECT-TYPE
    SYNTAX AtmLaneAddress
--    Rsyntax OCTET STRING(SIZE(0 | 20))
    ACCESS read-write
    STATUS mandatory
    DESCRIPTION
        "The LLC-multiplexed LE Client or Broadcast/Multicast
         Service ATM address corresponding to the MAC address
         'leArpMacAddress'.
        
         This value may be determined through the use of the
         LE_ARP procedure, through source address learning,
         or through other mechanisms.
        
         Some agents may provide write access to this object,
         as part of their support for 'static' LE_ARP entries.
         The effect of attempting to write an ATM address to
         a 'learned' row is explicitly undefined.  Agents may
         disallow the write, accept the write and change the
         row's type, or even accept the write as-is."
    ::= { leArpEntry 6 }

leArpServiceCategory OBJECT-TYPE
    SYNTAX INTEGER(0..2147483647)
    ACCESS read-write
    STATUS mandatory
    DESCRIPTION
        "A bitmap describing the service categories which the
         LEC 'lecIndex' supports.
        
         This value normally comes from the optional 'Service-
         Category' TLV in LANE 2.0 LE_ARP_RESPONSEs.
        
         The bitmap is larger than the LANE 2.0 specification
         requires, in case room is ever needed for expansion.
        
         If service categories aren't applicable, aren't known,
         or the implementor does not want to provide memory to
         store them (e.g., because they would only be used for
         SNMP), this object should be set to the value 0.
        
         See also the object 'lecStoresServiceCategories'."
    REFERENCE
        "LAN Emulation Over ATM Version 2 - LUNI Specification,
         Annex A (LAN Emulation Control Frame TLVs)"
    ::= { leArpEntry 7 }

leRDArpTable OBJECT-TYPE
    SYNTAX SEQUENCE OF LeRDArpEntry
    ACCESS not-accessible
    STATUS mandatory
    DESCRIPTION
        "This table provides access to an ATM LAN Emulation
         Client's Route Descriptor-to-ATM ARP cache.
        
         Implementation of this table is optional for hosts
         that do not support emulated IEEE 802.5 Token Ring
         LANs, and mandatory for hosts which do.
        
         C16 LE_ARP Cache.  A table of entries, each of which
             establishes a relationship between a LAN
             Destination external to the LE Client and the
             ATM address to which data frames for that LAN
             Destination will be sent."
    REFERENCE
        "ATM Forum LAN Emulation Over ATM Specification,
         Section 5.1.1"
    ::= { leClientMIBObjects 10 }

leRDArpEntry OBJECT-TYPE
    SYNTAX LeRDArpEntry
    ACCESS not-accessible
    STATUS mandatory
    DESCRIPTION
        "An ATM LAN Emulation ARP cache entry containing
         information about the binding of one IEEE 802.5
         route descriptor to one ATM address."
    INDEX { lecIndex, leRDArpSegmentID, leRDArpBridgeNumber }
    ::= { leRDArpTable 1 }

LeRDArpEntry ::= SEQUENCE {
    leRDArpSegmentID INTEGER,
    leRDArpBridgeNumber INTEGER,
    leRDArpAtmAddress AtmLaneAddress,
    leRDArpEntryType LeArpTableEntryType,
    leRDArpRowStatus RowStatus,
    leRDArpMuxedAtmAddress AtmLaneAddress,
    leRDArpServiceCategory INTEGER,
    leRDArpIsRemoteDescriptor TruthValue
    }

leRDArpSegmentID OBJECT-TYPE
    SYNTAX INTEGER(0..4095)
    ACCESS not-accessible
    STATUS mandatory
    DESCRIPTION
        "The LAN ID portion of the IEEE 802.5 route descriptor
         associated with this ARP cache entry."
    ::= { leRDArpEntry 1 }

leRDArpBridgeNumber OBJECT-TYPE
    SYNTAX INTEGER(0..15)
    ACCESS not-accessible
    STATUS mandatory
    DESCRIPTION
        "The Bridge Number portion of the IEEE 802.5 route
         descriptor associated with this ARP cache entry."
    ::= { leRDArpEntry 2 }

leRDArpAtmAddress OBJECT-TYPE
    SYNTAX AtmLaneAddress
--    Rsyntax OCTET STRING(SIZE(0 | 20))
    ACCESS read-write
    STATUS mandatory
    DESCRIPTION
        "The non-multiplexed ATM address of the LAN Emulation
         Client which is associated with the route descriptor
         ('leRDArpSegmentID', 'leRDArpBridgeNumber').
        
         This value may be determined through the use of the
         LE_ARP procedure, through source address learning,
         or through other mechanisms.
        
         Some agents may provide write access to this object,
         as part of their support for 'static' LE_ARP entries.
         The effect of attempting to write an ATM address to
         a 'learned' row is explicitly undefined.  Agents may
         disallow the write, accept the write and change the
         row's type, or even accept the write as-is."
    ::= { leRDArpEntry 3 }

leRDArpEntryType OBJECT-TYPE
    SYNTAX LeArpTableEntryType
--    Rsyntax INTEGER {
--        other(1),
--        learnedViaControl(2),
--        learnedViaData(3),
--        staticVolatile(4),
--        staticNonVolatile(5)
--        }
    ACCESS read-write
    STATUS mandatory
    DESCRIPTION
        "Indicates how this LE_ARP table entry was created and
         whether it is aged."
    DEFVAL { staticVolatile }
    ::= { leRDArpEntry 4 }

leRDArpRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Lets users create and delete LE_ARP cache entries,
         on systems that support this capability.
        
         Normally clients will maintain their LE_ARP caches
         automatically.  However, managers may occasionally
         want to create 'static' LE_ARP cache entries.
        
         Rules
        
           1.  Before a new row can become 'active', values
               must be supplied for the columnar objects
               leRDArpAtmAddress and leRDArpEntryType.
        
           2.  It is not necessary to set leRDArpRowStatus to
               'notInService' in order to modify a writable
               object in the same conceptual row.
        
           3.  LE_ARP entries whose status is 'notReady' or
               'notInService' will not be used to translate
               LAN Destinations to ATM Addresses.  However,
               clients may overwrite such entries with data
               obtained from other sources.  For example, a
               client which needed to transmit a data frame
               to a given MAC address (or via a given Route
               Descriptor) might find that its LE_ARP entry
               for the LAN Destination is 'notInService' or
               'notReady'.  The client might then act as if
               the LAN Destination was unknown - generating
               a LE_ARP_REQUEST, flooding the data frame to
               the BUS, and creating a new, 'active' LE_ARP
               cache entry based on the LE_ARP_RESPONSE."
    ::= { leRDArpEntry 5 }

leRDArpMuxedAtmAddress OBJECT-TYPE
    SYNTAX AtmLaneAddress
--    Rsyntax OCTET STRING(SIZE(0 | 20))
    ACCESS read-write
    STATUS mandatory
    DESCRIPTION
        "The LLC-multiplexed ATM address of the LAN Emulation
         Client which is associated with the route descriptor
         ('leRDArpSegmentID', 'leRDArpBridgeNumber').
        
         This value may be determined through the use of the
         LE_ARP procedure, through source address learning,
         or through other mechanisms.
        
         Some agents may provide write access to this object,
         as part of their support for 'static' LE_ARP entries.
         The effect of attempting to write an ATM address to
         a 'learned' row is explicitly undefined.  Agents may
         disallow the write, accept the write and change the
         row's type, or even accept the write as-is."
    ::= { leRDArpEntry 6 }

leRDArpServiceCategory OBJECT-TYPE
    SYNTAX INTEGER(0..2147483647)
    ACCESS read-write
    STATUS mandatory
    DESCRIPTION
        "A bitmap describing the service categories which the
         LEC 'lecIndex'supports.
        
         This value normally comes from the optional 'Service-
         Category' TLV in LANE 2.0 LE_ARP_RESPONSEs.
        
         The bitmap is larger than the LANE 2.0 specification
         requires, in case room is ever needed for expansion.
        
         If service categories aren't applicable, aren't known,
         or the implementor does not want to provide memory to
         store them (e.g., because they would only be used for
         SNMP), this object should be set to the value 0.
        
         See also the object 'lecStoresServiceCategories'."
    REFERENCE
        "LAN Emulation Over ATM Version 2 - LUNI Specification,
         Annex A (LAN Emulation Control Frame TLVs)"
    ::= { leRDArpEntry 7 }

leRDArpIsRemoteDescriptor OBJECT-TYPE
    SYNTAX TruthValue
--    Rsyntax INTEGER {
--        true(1),
--        false(2)
--        }
    ACCESS read-only
    STATUS mandatory
    DESCRIPTION
        "Indicates whether this entry is for a local or remote
         route descriptor.
        
         In this context, 'local' means 'a route descriptor
         that is local to the remote client', as opposed to
         'one of my route descriptors'.
        
             true(1)
                 The route descriptor is believed to be remote
                 - or its local/remote status is unknown.
        
                 For an entry created via the LE_ARP mechanism,
                 this corresponds to the 'Remote address' flag
                 being set in the LE_ARP_RESPONSE.
        
             false(2)
                 The route descriptor is believed to be local
                 - that is to say, registered with the LES by
                 the client whose address is leRDArpAtmAddress
                 (and/or leRDArpMuxedATMAddress).
        
                 For an entry created via the LE_ARP mechanism,
                 this corresponds to the 'Remote address' flag
                 being cleared in the LE_ARP_RESPONSE."
    ::= { leRDArpEntry 8 }

lecMcForwardTable OBJECT-TYPE
    SYNTAX SEQUENCE OF LecMcForwardEntry
    ACCESS not-accessible
    STATUS mandatory
    DESCRIPTION
        "A table identifying Multicast Forward VCCs for LAN
         Emulation Version 2.0 clients."
    ::= { leClientMIBObjects 11 }

lecMcForwardEntry OBJECT-TYPE
    SYNTAX LecMcForwardEntry
    ACCESS not-accessible
    STATUS mandatory
    DESCRIPTION
        "Each row represents one Multicast Forward VCC."
    INDEX { lecIndex, lecMcForwardInterface, lecMcForwardVpi, lecMcForwardVci }
    ::= { lecMcForwardTable 1 }

LecMcForwardEntry ::= SEQUENCE {
    lecMcForwardInterface LeConnectionInterface,
    lecMcForwardVpi VpiInteger,
    lecMcForwardVci VciInteger,
    lecMcForwardVerification INTEGER
    }

lecMcForwardInterface OBJECT-TYPE
    SYNTAX LeConnectionInterface
--    Rsyntax INTEGER(0..2147483647)
    ACCESS not-accessible
    STATUS mandatory
    DESCRIPTION
        "The interface associated with the Multicast Forward
         VCC."
    ::= { lecMcForwardEntry 1 }

lecMcForwardVpi OBJECT-TYPE
    SYNTAX VpiInteger
--    Rsyntax INTEGER(0..4095)
    ACCESS not-accessible
    STATUS mandatory
    DESCRIPTION
        "The VPI which identifies the Multicast Forward VCC
         at the point where it connects to the LANE client."
    ::= { lecMcForwardEntry 2 }

lecMcForwardVci OBJECT-TYPE
    SYNTAX VciInteger
--    Rsyntax INTEGER(0..65535)
    ACCESS not-accessible
    STATUS mandatory
    DESCRIPTION
        "The VCI which identifies the Multicast Forward VCC
         at the point where it connects to the LANE client."
    ::= { lecMcForwardEntry 3 }

lecMcForwardVerification OBJECT-TYPE
    SYNTAX INTEGER {
        none(1),
        implicit(2),
        explicit(3)
        }
    ACCESS read-only
    STATUS mandatory
    DESCRIPTION
        "Indicates whether the calling address for this VCC
         has been verified.
        
             none      -  No verification
        
             implicit  -  Calling party address was same as
                          BUS address
        
             explicit  -  Client used LE_VERIFY protocol
        
         Also serves double-duty as a 'row exists' flag."
    ::= { lecMcForwardEntry 4 }

lecMacQueryLecIndex OBJECT-TYPE
    SYNTAX INTEGER(0..2147483647)
    ACCESS read-write
    STATUS mandatory
    DESCRIPTION
        "The 'lecIndex' of the LEC whose MAC address binding
         the network management station wants to look up.
        
         When written:  Triggers a new query.
        
         When read:  Identifies the last LEC queried.  (This
         value may be 0 if there have been no queries, or if
         a LEC has been deleted.)"
    ::= { lecMacQueryObjects 1 }

lecMacQueryAddress OBJECT-TYPE
    SYNTAX MacAddress
--    Rsyntax OCTET STRING(SIZE(6))
    ACCESS read-write
    STATUS mandatory
    DESCRIPTION
        "The MAC address whose binding the network management
         station wants to look up.
        
         When written:  Triggers a new query.  (Note that the
         SNMP agent is free to reject multicast and broadcast
         addresses with a 'badValue' error.)
        
         When read:  Returns the last MAC address queried, or
         all zeroes if lecMacQueryLecIndex is 0."
    ::= { lecMacQueryObjects 2 }

lecMacQueryStatus OBJECT-TYPE
    SYNTAX INTEGER {
        none(1),
        unsupported(2),
        local(3),
        remote(4),
        unknown(5)
        }
    ACCESS read-only
    STATUS mandatory
    DESCRIPTION
        "The status of the last query - one of the following:
        
             none(1)
                No queries have been made; therefore, other
                results values are invalid.
        
             unsupported(2)
                Queries are not supported for this LEC.
        
             local(3)
                The MAC address is one of the client's local
                MAC addresses.
        
             remote(4)
                The MAC address is one of the client's remote
                MAC addresses.
        
             unknown(5)
                The MAC address does not belong (is not known
                to belong) to the client."
    ::= { lecMacQueryObjects 3 }

lecMacQueryAtmAddress OBJECT-TYPE
    SYNTAX AtmLaneAddress
--    Rsyntax OCTET STRING(SIZE(0 | 20))
    ACCESS read-only
    STATUS mandatory
    DESCRIPTION
        "The non-multiplexed ATM address which this client --
         i.e., client 'lecMacQueryLecIndex' -- would use in a
         LE_ARP_RESPONSE for 'lecMacQueryAddress'.
        
         This object is only meaningful when lecMacQueryStatus
         is 'localMacAddress' or 'remoteMacAddress'."
    ::= { lecMacQueryObjects 4 }

lecMacQueryMuxedAtmAddress OBJECT-TYPE
    SYNTAX AtmLaneAddress
--    Rsyntax OCTET STRING(SIZE(0 | 20))
    ACCESS read-only
    STATUS mandatory
    DESCRIPTION
        "The LLC-multiplexed ATM address which this client --
         i.e., client 'lecMacQueryLecIndex' -- would use in a
         LE_ARP_RESPONSE for 'lecMacQueryAddress'.
        
         This object is only meaningful when lecMacQueryStatus
         is 'localMacAddress' or 'remoteMacAddress'."
    ::= { lecMacQueryObjects 5 }

lecMacQueryServiceCategory OBJECT-TYPE
    SYNTAX INTEGER(0..2147483647)
    ACCESS read-only
    STATUS mandatory
    DESCRIPTION
        "The Service Category TLV that this client would use
         in a LE_ARP_RESPONSE for 'lecMacQueryAddress'.
        
         If this client wouldn't return a Service Category TLV
         in the LE_ARP_RESPONSE, this object should be set to
         zero.
        
         The bitmap is larger than the LANE 2.0 specification
         requires, in case room is ever needed for expansion.
        
         This object is only meaningful when lecMacQueryStatus
         is 'localMacAddress' or 'remoteMacAddress'."
    REFERENCE
        "LAN Emulation Over ATM Version 2 - LUNI Specification,
         Annex A (LAN Emulation Control Frame TLVs)"
    ::= { lecMacQueryObjects 6 }

lecRDQueryLecIndex OBJECT-TYPE
    SYNTAX INTEGER(0..2147483647)
    ACCESS read-write
    STATUS mandatory
    DESCRIPTION
        "The 'lecIndex' of the LEC whose route descriptor to
         ATM address binding the network management station
         wants to look up.
        
         When written:  Triggers a new query.
        
         When read:  Identifies the last LEC queried.  (This
         value may be 0 if there have been no queries, or if
         a LEC has been deleted.)"
    ::= { lecRDQueryObjects 1 }

lecRDQuerySegmentID OBJECT-TYPE
    SYNTAX INTEGER(0..4095)
    ACCESS read-write
    STATUS mandatory
    DESCRIPTION
        "The LAN ID portion of the IEEE 802.5 route descriptor
         whose binding the network management station wants to
         look up.
        
         When written:  Triggers a new query.
        
         When read:  Returns the LAN ID portion of the last RD
         queried, or 0 if lecRDQueryLecIndex is 0."
    ::= { lecRDQueryObjects 2 }

lecRDQueryBridgeNumber OBJECT-TYPE
    SYNTAX INTEGER(0..15)
    ACCESS read-write
    STATUS mandatory
    DESCRIPTION
        "The bridge number portion of the IEEE 802.5 route
         descriptor whose binding the network management
         station wants to look up.
        
         When written:  Triggers a new query.
        
         When read:  Returns the bridge number portion of the
         last RD queried, or 0 if lecRDQueryLecIndex is 0."
    ::= { lecRDQueryObjects 3 }

lecRDQueryStatus OBJECT-TYPE
    SYNTAX INTEGER {
        none(1),
        unsupported(2),
        local(3),
        remote(4),
        unknown(5)
        }
    ACCESS read-only
    STATUS mandatory
    DESCRIPTION
        "The status of the last query - one of the following:
        
            none(1)
                No queries have been made; therefore, other
                results values are invalid.
        
            unsupported(2)
                Queries are not supported for this LEC.
        
            local(3)
                The route descriptor is one of the client's
                local route descriptors.
        
            remote(4)
                The route descriptor is one of the client's
                remote route descriptors.
        
            unknown(5)
                The route descriptor does not belong (is not
                known to belong) to the client."
    ::= { lecRDQueryObjects 4 }

lecRDQueryAtmAddress OBJECT-TYPE
    SYNTAX AtmLaneAddress
--    Rsyntax OCTET STRING(SIZE(0 | 20))
    ACCESS read-only
    STATUS mandatory
    DESCRIPTION
        "The non-multiplexed ATM address which this client --
         i.e., client 'lecRDQueryLecIndex' -- would use in a
         LE_ARP_RESPONSE for the route descriptor
         ('lecRDQuerySegmentID', 'lecRDQueryBridgeNumber').
        
         This object is only meaningful when lecRDQueryStatus
         is 'local' or 'remote'."
    ::= { lecRDQueryObjects 5 }

lecRDQueryMuxedAtmAddress OBJECT-TYPE
    SYNTAX AtmLaneAddress
--    Rsyntax OCTET STRING(SIZE(0 | 20))
    ACCESS read-only
    STATUS mandatory
    DESCRIPTION
        "The LLC-multiplexed ATM address which this client --
         i.e., client 'lecRDQueryLecIndex' -- would use in a
         LE_ARP_RESPONSE for the route descriptor
         ('lecRDQuerySegmentID', 'lecRDQueryBridgeNumber').
        
         This object is only meaningful when lecRDQueryStatus
         is 'local' or 'remote'."
    ::= { lecRDQueryObjects 6 }

lecRDQueryServiceCategory OBJECT-TYPE
    SYNTAX INTEGER(0..2147483647)
    ACCESS read-only
    STATUS mandatory
    DESCRIPTION
        "The Service Category TLV that this client would use
         in a LE_ARP_RESPONSE for the route descriptor
         ('lecRDQuerySegmentID', 'lecRDQueryBridgeNumber').
        
         If this client wouldn't return a Service Category TLV
         in the LE_ARP_RESPONSE, this object should be set to
         zero.
        
         The bitmap is larger than the LANE 2.0 specification
         requires, in case room is ever needed for expansion.
        
         This object is only meaningful when lecRDQueryStatus
         is 'local' or 'remote'."
    REFERENCE
        "LAN Emulation Over ATM Version 2 - LUNI Specification,
         Annex A (LAN Emulation Control Frame TLVs)"
    ::= { lecRDQueryObjects 7 }

lecTlvTable OBJECT-TYPE
    SYNTAX SEQUENCE OF LecTlvEntry
    ACCESS not-accessible
    STATUS mandatory
    DESCRIPTION
        "This table provides a place for an agent to store
         interesting TLVs associated with
        
             o  Registered LAN destinations
        
             o  LE_ARP entries
        
             o  Query results from the LE_ARP response group
        
             o  Initialization / configuration
        
         and any other categories the ATM Forum adds.
        
         Unless otherwise stated,
        
             o  Entries in this table are completely optional.
        
             o  An implementation may choose to keep only the
                TLVs which are 'interesting' to its designers,
                such as MPOA TLVs in LE_ARP_RESPONSEs.
        
             o  TLVs which already have their own MIB objects
                should not be duplicated here.
        
             o  Where write / create access is allowed, it is
                not mandatory.
        
         Implementors should document the specific lecTlvTable
         features of their agent."
    REFERENCE
        "LAN Emulation Over ATM Version 2 - LUNI Specification,
         Annex A (LAN Emulation Control Frame TLVs)"
    ::= { leClientMIBObjects 13 }

lecTlvEntry OBJECT-TYPE
    SYNTAX LecTlvEntry
    ACCESS not-accessible
    STATUS mandatory
    DESCRIPTION
        "Each table row describes one TLV of a related set."
    INDEX { lecIndex, lecTlvSetIndex, lecTlvLanDestination, lecTlvIndex }
    ::= { lecTlvTable 1 }

LecTlvEntry ::= SEQUENCE {
    lecTlvSetIndex INTEGER,
    lecTlvLanDestination OCTET STRING,
    lecTlvIndex INTEGER,
    lecTlvType OCTET STRING,
    lecTlvValue OCTET STRING,
    lecTlvRowStatus RowStatus
    }

lecTlvSetIndex OBJECT-TYPE
    SYNTAX INTEGER {
        layer3Tlvs(1),
        actualRegTlvs(2),
        configRegTlvs(3),
        leArpTlvs(4),
        queryTlvs(5)
        }
    ACCESS not-accessible
    STATUS mandatory
    DESCRIPTION
        "An index which helps to identify a set of TLVs, and to
         indicate their purpose.
        
         The value of this index defines the interpretation and
         use of corresponding table rows as follows:
        
             layer3Tlvs(1)
             -------------
                 This index provides access to Layer-3-Address
                 TLVs (Initial State variable C36) used during
                 the Initialization phase.
        
                 TLVs are stored in rows
        
                     ( lecIndex, 1,
                       LAN_Destination( all '00's ),
                       * )
        
                 These rows may be read / created / written /
                 deleted.
        
             actualRegTlvs(2)
             ----------------
                 This index provides access to TLVs which were
                 used to register LAN Destinations.
        
                 These TLVs are associated with entries in the
                 lecMacAddressTable and lecRouteDescrTable and
                 stored in rows
        
                     ( lecIndex, 2,
                       LAN_Destination( lecMacAddress ),
                       * )
        
                     ( lecIndex, 2,
                       LAN_Destination(
                           lecRouteDescrSegmentID,
                           lecRouteDescrBridgeNumber ),
                       * )
        
                 These rows may be read or deleted, but cannot
                 be created or modified.  Most implementations
                 are expected to make them read-only.
        
                 Note that TLVs that have their own objects in
                 the associated tables SHOULD NOT appear here.
                 LLC-Muxed-ATM-Address & Service-Category TLVs
                 are two examples.
        
             configRegTlvs(3)
             ----------------
                 This index provides a way to set registration
                 TLVs for unregistered LAN Destinations.
        
                 Hopefully this is not something that managers
                 will need to do a lot.
        
                 TLVs are stored in rows
        
                     ( lecIndex, 3,
                       LAN_Destination( the_LAN_destination ),
                       * )
        
                 Note that the agent might restrict the set of
                 LAN Destinations and TLVs that it allows; for
                 instance, to screen out the 'V2 Capable' TLV.
        
             leArpTlvs(4)
             ------------
                 This index provides access to TLVs associated
                 with the LE_ARP cache.
        
                 These TLVs are associated with leArpTable and
                 leRDArpTable, and stored in rows
        
                     ( lecIndex, 4,
                       LAN_Destination( leArpMacAddress ),
                       * )
        
                     ( lecIndex, 4,
                       LAN_Destination(
                               leRDArpSegmentID,
                               leRDArpBridgeNumber ),
                       * )
        
                 Agents may allow write/create access to TLVs
                 when the type of the associated LE_ARP entry
                 is 'staticVolatile', 'staticNonVolatile', or
                 'other'.
        
                 Note that TLVs that have their own objects in
                 the associated tables SHOULD NOT appear here.
                 LLC-Muxed-ATM-Address & Service-Category TLVs
                 are two examples.
        
             queryTlvs(5)
             ------------
                 This index provides access to TLVs associated
                 with the last MAC Address or Route Descriptor
                 query.
        
                 TLVs are associated with lecMacQueryObjects &
                 lecRDQueryObjects, and stored in rows
        
                     ( lecIndex, 5,
                       LAN_Destination( lecMacQueryAddress ),
                       * )
        
                     ( lecIndex, 5,
                       LAN_Destination(
                               lecRDQuerySegmentID,
                               lecRDQueryBridgeNumber ),
                       * )
        
                 Note that TLVs that have their own objects in
                 the associated tables SHOULD NOT appear here.
                 LLC-Muxed-ATM-Address & Service-Category TLVs
                 are two examples.
        
         Additional indices may be defined by the ATM Forum as
         needed."
    ::= { lecTlvEntry 1 }

lecTlvLanDestination OBJECT-TYPE
    SYNTAX OCTET STRING(SIZE(8))
    ACCESS not-accessible
    STATUS mandatory
    DESCRIPTION
        "The MAC address or route descriptor associated with
         the TLV (see the description of the lecTlvSetIndex),
         encoded in the fashion defined in the LANE 2.0 LUNI
         specification (Table 16).  To recap:
        
         The first two octets indicate the LAN Destination's
         type:  00, 01 for a MAC address; 00, 02 for a route
         descriptor; 00, 00 for 'no LAN Destination'.
        
         The next six octets contain either the MAC address,
         or four 00 octets followed by the route descriptor,
         or six nulls.
        
         Note:
         -----
         In the future, the ATM Forum may extend this field
         for use with other types of index values, provided
         that each new type of index value has a unique tag.
         Such extensions are NOT to be considered a 'change
         in semantics' that requires the deprecation of the
         index object and the table.
        
         Network management system implementors are advised
         to display values whose tags they do not recognize
         as (formatted) hexadecimal strings."
    ::= { lecTlvEntry 2 }

lecTlvIndex OBJECT-TYPE
    SYNTAX INTEGER(1..65535)
    ACCESS not-accessible
    STATUS mandatory
    DESCRIPTION
        "An arbitrary index which allows a set to contain
         multiple TLVs."
    ::= { lecTlvEntry 3 }

lecTlvType OBJECT-TYPE
    SYNTAX OCTET STRING(SIZE(4))
    ACCESS read-write
    STATUS mandatory
    DESCRIPTION
        "A four-octet string indicating this item's type.
         It consists of a three-octet OUI, followed by an
         octet identifying one of the organization's TLVs."
    ::= { lecTlvEntry 4 }

lecTlvValue OBJECT-TYPE
    SYNTAX OCTET STRING(SIZE(0..255))
    ACCESS read-write
    STATUS mandatory
    DESCRIPTION
        "The value - and, implicitly, the length - of the
         TLV."
    ::= { lecTlvEntry 5 }

lecTlvRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Provides a way for network managers to create and
         delete rows in the TLV table."
    ::= { lecTlvEntry 6 }

leClientConfigGroup OBJECT IDENTIFIER ::= { leClientMIBGroups 1 }
-- OBJECT-GROUP
--  Status
--    deprecated
--  Descr
--    A collection of objects used for creating and
--     configuring LAN Emulation Clients.
--    
--     This group is deprecated because some objects
--     in it have been replaced by newer ones.
--  objects
--    lecRowStatus, lecOwner, lecConfigMode, lecConfigLanType, 
--    lecConfigMaxDataFrameSize, lecConfigLanName, 
--    lecConfigLesAtmAddress, lecControlTimeout, 
--    lecMaxUnknownFrameCount, lecMaxUnknownFrameTime, 
--    lecVccTimeoutPeriod, lecMaxRetryCount, lecAgingTime, 
--    lecForwardDelayTime, lecExpectedArpResponseTime, 
--    lecFlushTimeOut, lecPathSwitchingDelay, lecLocalSegmentID, 
--    lecMulticastSendType, lecMulticastSendAvgRate, 
--    lecMulticastSendPeakRate, lecConnectionCompleteTimer

leClientStatusGroup OBJECT IDENTIFIER ::= { leClientMIBGroups 2 }
-- OBJECT-GROUP
--  Status
--    mandatory
--  Descr
--    A collection of objects describing the status
--     and operational parameters of the managed LAN
--     Emulation Clients.
--  objects
--    lecIfIndex, lecPrimaryAtmAddress, lecID, lecInterfaceState, 
--    lecLastFailureRespCode, lecLastFailureState, lecProtocol, 
--    lecVersion, lecTopologyChange, lecConfigServerAtmAddress, 
--    lecConfigSource, lecActualLanType, lecActualMaxDataFrameSize, 
--    lecActualLanName, lecActualLesAtmAddress, lecProxyClient

leClientMappingGroup OBJECT IDENTIFIER ::= { leClientMIBGroups 3 }
-- OBJECT-GROUP
--  Status
--    mandatory
--  Descr
--    A collection of objects which map a LAN Emulation
--     Client's 'ifIndex' to its 'lecIndex'.
--  objects
--    lecMappingIndex

leClientStatisticsGroup OBJECT IDENTIFIER ::= { leClientMIBGroups 4 }
-- OBJECT-GROUP
--  Status
--    mandatory
--  Descr
--    A collection of objects which act as an extension
--     to the lecConfigTable.
--    
--     These objects provide statistics on LAN Emulation
--     control traffic and SVC establishment.
--  objects
--    lecArpRequestsOut, lecArpRequestsIn, lecArpRepliesOut, 
--    lecArpRepliesIn, lecControlFramesOut, lecControlFramesIn, 
--    lecSvcFailures

leClientServerVccGroup OBJECT IDENTIFIER ::= { leClientMIBGroups 5 }
-- OBJECT-GROUP
--  Status
--    mandatory
--  Descr
--    A collection of objects which act as an extension
--     to the lecConfigTable.
--    
--     These objects identify Configuration Direct,
--     Control, and Multicast VCCs for each client,
--     making it easier to locate their entries in the
--     AToM MIB.
--  objects
--    lecConfigDirectInterface, lecConfigDirectVpi, 
--    lecConfigDirectVci, lecControlDirectInterface, 
--    lecControlDirectVpi, lecControlDirectVci, 
--    lecControlDistributeInterface, lecControlDistributeVpi, 
--    lecControlDistributeVci, lecMulticastSendInterface, 
--    lecMulticastSendVpi, lecMulticastSendVci, 
--    lecMulticastForwardInterface, lecMulticastForwardVpi, 
--    lecMulticastForwardVci

leClientAtmAddressesGroup OBJECT IDENTIFIER ::= { leClientMIBGroups 6 }
-- OBJECT-GROUP
--  Status
--    mandatory
--  Descr
--    A collection of objects which describe all of the
--     ATM addresses belonging to each client.
--  objects
--    lecAtmAddressStatus

leClientMacAddressesGroup OBJECT IDENTIFIER ::= { leClientMIBGroups 7 }
-- OBJECT-GROUP
--  Status
--    mandatory
--  Descr
--    A collection of objects which describe all of the
--     MAC addresses registered for each client.
--  objects
--    lecMacAddressAtmBinding

leClientRouteDescriptorsGroup OBJECT IDENTIFIER ::= { leClientMIBGroups 8 }
-- OBJECT-GROUP
--  Status
--    mandatory
--  Descr
--    A collection of objects which describe all of the
--     Route Descriptors registered for each client.
--  objects
--    lecRouteDescrAtmBinding

leClientArpGroup OBJECT IDENTIFIER ::= { leClientMIBGroups 9 }
-- OBJECT-GROUP
--  Status
--    mandatory
--  Descr
--    A collection of objects which describe the MAC-
--     to-ATM address mappings that this LAN Emulation
--     Client has learned.
--  objects
--    leArpAtmAddress, leArpIsRemoteAddress, leArpEntryType, 
--    leArpRowStatus

leClientRDArpGroup OBJECT IDENTIFIER ::= { leClientMIBGroups 10 }
-- OBJECT-GROUP
--  Status
--    mandatory
--  Descr
--    A collection of objects which describe the IEEE
--     802.5 Route Descriptor-to-ATM address mappings
--     that this LAN Emulation Client has learned.
--  objects
--    leRDArpAtmAddress, leRDArpEntryType, leRDArpRowStatus

leClientConfigGroupV1 OBJECT IDENTIFIER ::= { leClientMIBGroups 11 }
-- OBJECT-GROUP
--  Status
--    mandatory
--  Descr
--    A collection of objects used for creating and
--     configuring both V1 and V2 LE Clients.
--    
--     It is the same as leClientConfigGroup, except
--     that the deprecated objects lecLocalSegmentID
--     and lecMaxUnknownFrameCount have been removed
--     and replaced by lecV2MaxUnknownFrameCount and
--     lecConfigLocalSegmentID.
--    
--     Also, lecConfigLecsAtmAddress has been added.
--  objects
--    lecRowStatus, lecOwner, lecConfigMode, lecConfigLanType, 
--    lecConfigMaxDataFrameSize, lecConfigLanName, 
--    lecConfigLesAtmAddress, lecControlTimeout, 
--    lecMaxUnknownFrameTime, lecVccTimeoutPeriod, lecMaxRetryCount, 
--    lecAgingTime, lecForwardDelayTime, lecExpectedArpResponseTime, 
--    lecFlushTimeOut, lecPathSwitchingDelay, lecMulticastSendType, 
--    lecMulticastSendAvgRate, lecMulticastSendPeakRate, 
--    lecConnectionCompleteTimer, lecConfigLecsAtmAddress, 
--    lecV2MaxUnknownFrameCount, lecConfigLocalSegmentID

leClientConfigGroupV2 OBJECT IDENTIFIER ::= { leClientMIBGroups 12 }
-- OBJECT-GROUP
--  Status
--    mandatory
--  Descr
--    A collection of objects which extend the LEC
--     configuration table to deal with LANE V2.0.
--  objects
--    lecInitialControlTimeout, lecControlTimeoutMultiplier, 
--    lecConfigV2Capable, lecConfigSelectiveMulticast, 
--    lecForwardDisconnectTimeout, lecConfigLLCMultiplexCapable, 
--    lecMinReconfigureDelay, lecMaxReconfigureDelay, 
--    lecMaxBusConnectRetries, lecTokenRingExplorerExclude

leClientStatusGroupV2 OBJECT IDENTIFIER ::= { leClientMIBGroups 13 }
-- OBJECT-GROUP
--  Status
--    mandatory
--  Descr
--    A collection of objects which extend the LEC
--     status table to deal with LANE V2.0.
--  objects
--    lecActualLocalSegmentID, lecActualV2Capable, lecElanID, 
--    lecActualSelectiveMulticast, lecActualLLCMultiplexCapable, 
--    lecPreferredLesAddress, lecStoresServiceCategories

leClientStatisticsGroupV2 OBJECT IDENTIFIER ::= { leClientMIBGroups 14 }
-- OBJECT-GROUP
--  Status
--    mandatory
--  Descr
--    A collection of objects which provide statistics
--     on LLC-multiplexed flow establishment, and count
--     harmless discards separately from ifInDiscards.
--  objects
--    lecFlowFailures, lecEchoDiscards, lecFilteredMulticasts

leClientAtmAddressesGroupV2 OBJECT IDENTIFIER ::= { leClientMIBGroups 15 }
-- OBJECT-GROUP
--  Status
--    mandatory
--  Descr
--    An object which extends the lecAtmAddressTable to
--     provide information about LANE V2.0 multiplexing.
--  objects
--    lecAtmAddressMuxed

leClientMacAddressesGroupV2 OBJECT IDENTIFIER ::= { leClientMIBGroups 16 }
-- OBJECT-GROUP
--  Status
--    mandatory
--  Descr
--    Objects which extend the lecMacAddressTable to
--     provide information about LANE V2.0 multiplexing
--     and TLVs.
--  objects
--    lecMacAddressMuxedAtmBinding, lecMacAddressServiceCategory

leClientRouteDescriptorsGroupV2 OBJECT IDENTIFIER ::= { leClientMIBGroups 17 }
-- OBJECT-GROUP
--  Status
--    mandatory
--  Descr
--    An object which extends the lecRouteDescrTable to
--     provide information about LANE V2.0 multiplexing.
--  objects
--    lecRouteDescrMuxedAtmBinding, lecRouteDescrServiceCategory

leClientArpGroupV2 OBJECT IDENTIFIER ::= { leClientMIBGroups 18 }
-- OBJECT-GROUP
--  Status
--    mandatory
--  Descr
--    A collection of objects which provide additional
--     LE-ARP information for LANE Version 2.0.
--  objects
--    leArpMuxedAtmAddress, leArpServiceCategory

leClientRDArpGroupV2 OBJECT IDENTIFIER ::= { leClientMIBGroups 19 }
-- OBJECT-GROUP
--  Status
--    mandatory
--  Descr
--    A collection of objects which provide additional
--     LE-ARP information for LANE Version 2.0.
--  objects
--    leRDArpMuxedAtmAddress, leRDArpServiceCategory, 
--    leRDArpIsRemoteDescriptor

leClientMcForwardGroup OBJECT IDENTIFIER ::= { leClientMIBGroups 20 }
-- OBJECT-GROUP
--  Status
--    mandatory
--  Descr
--    A collection of objects that provide information
--     on Multicast Forward VCCs belonging to LANE V2.0
--     clients.
--  objects
--    lecMcForwardVerification

leClientMacQueryGroup OBJECT IDENTIFIER ::= { leClientMIBGroups 21 }
-- OBJECT-GROUP
--  Status
--    mandatory
--  Descr
--    A collection of objects that allow a network
--     manager to find out ATM bindings for a proxy
--     client's remote MAC address(es).
--  objects
--    lecMacQueryLecIndex, lecMacQueryAddress, lecMacQueryStatus, 
--    lecMacQueryAtmAddress, lecMacQueryMuxedAtmAddress, 
--    lecMacQueryServiceCategory

leClientRDQueryGroup OBJECT IDENTIFIER ::= { leClientMIBGroups 22 }
-- OBJECT-GROUP
--  Status
--    mandatory
--  Descr
--    A collection of objects that allow a network
--     manager to find out ATM bindings for a proxy
--     client's remote route descriptor(s).
--  objects
--    lecRDQueryLecIndex, lecRDQuerySegmentID, 
--    lecRDQueryBridgeNumber, lecRDQueryStatus, 
--    lecRDQueryAtmAddress, lecRDQueryMuxedAtmAddress, 
--    lecRDQueryServiceCategory

leClientTlvGroup OBJECT IDENTIFIER ::= { leClientMIBGroups 23 }
-- OBJECT-GROUP
--  Status
--    mandatory
--  Descr
--    A collection of objects that allow a network
--     manager to see 'interesting' TLV information.
--  objects
--    lecTlvType, lecTlvValue, lecTlvRowStatus

leClientMIBCompliance OBJECT IDENTIFIER ::= { leClientMIBCompliances 1 }
-- MODULE-COMPLIANCE
--  Status
--    deprecated
--  Descr
--    The original compliance statement for SNMP
--     entities which supported ATM LAN Emulation
--     Clients.
--    
--     See leClientMIBCompliance2 for the updated
--     statement.
--    
--    For a host to conform to this MIB, it must also implement
--    
--    - RFC 1213 - MIB II.
--    
--    - Interfaces table entries for each LE Client, as per the
--    LAN Emulation Client management specification.
--    
--    - The AToM MIB (RFC 1695 - Definitions of Managed Objects
--    for ATM Management), according to the conformance
--    statements defined in that RFC.
--    
--    Optionally, a host may implement
--    
--    - RFC 1573 - Evolution of the Interfaces Group of MIB-II.
--    
--    - The 'ifRcvAddressGroup' from RFC 1573, which provides a
--    way to represent and configure interfaces with multiple
--    addresses.
--    
--    See the LAN Emulation Client management specification for
--    interpretations of RFC 1573 / MIB-II as they apply to LAN
--    Emulation Clients.
--  Module
--    >>current<<
--   MandGroup
--    leClientConfigGroup
--   MandGroup
--    leClientStatusGroup
--   MandGroup
--    leClientMappingGroup
--   MandGroup
--    leClientStatisticsGroup
--   MandGroup
--    leClientServerVccGroup
--   MandGroup
--    leClientAtmAddressesGroup
--   MandGroup
--    leClientMacAddressesGroup
--   MandGroup
--    leClientArpGroup
--   OptGroup
--    leClientRouteDescriptorsGroup
--   OptGroup
--    leClientRDArpGroup
--   ObjVar
--    lecRowStatus
--   ObjVar
--    lecOwner
--   ObjVar
--    lecConfigMode
--   ObjVar
--    lecConfigLanType
--   ObjVar
--    lecConfigMaxDataFrameSize
--   ObjVar
--    lecConfigLanName
--   ObjVar
--    lecConfigLesAtmAddress
--   ObjVar
--    lecControlTimeout
--   ObjVar
--    lecMaxUnknownFrameCount
--   ObjVar
--    lecMaxUnknownFrameTime
--   ObjVar
--    lecVccTimeoutPeriod
--   ObjVar
--    lecMaxRetryCount
--   ObjVar
--    lecAgingTime
--   ObjVar
--    lecForwardDelayTime
--   ObjVar
--    lecExpectedArpResponseTime
--   ObjVar
--    lecFlushTimeOut
--   ObjVar
--    lecPathSwitchingDelay
--   ObjVar
--    lecLocalSegmentID
--   ObjVar
--    lecMulticastSendType
--   ObjVar
--    lecMulticastSendAvgRate
--   ObjVar
--    lecMulticastSendPeakRate
--   ObjVar
--    lecConnectionCompleteTimer
--   ObjVar
--    lecAtmAddressStatus
--   ObjVar
--    leArpAtmAddress
--   ObjVar
--    leArpEntryType
--   ObjVar
--    leArpRowStatus
--   ObjVar
--    leRDArpAtmAddress
--   ObjVar
--    leRDArpEntryType
--   ObjVar
--    leRDArpRowStatus

leClientMIBCompliance2 OBJECT IDENTIFIER ::= { leClientMIBCompliances 2 }
-- MODULE-COMPLIANCE
--  Status
--    mandatory
--  Descr
--    The compliance statement for SNMP entities
--     that support LECs and Version 2 of the LEC
--     management specification.
--    
--    For a host to conform to this MIB, it must also implement
--    
--    - RFC 1213 - MIB II.
--    
--    - Interfaces table entries for each LE Client, as per the
--    LAN Emulation Client management specification.
--    
--    - The AToM MIB (RFC 1695 - Definitions of Managed Objects
--    for ATM Management), according to the conformance
--    statements defined in that RFC.
--    
--    Optionally, a host may implement
--    
--    - RFC 1573 - Evolution of the Interfaces Group of MIB-II.
--    
--    - The 'ifRcvAddressGroup' from RFC 1573, which provides a
--    way to represent and configure interfaces with multiple
--    addresses.
--    
--    See the LAN Emulation Client management specification for
--    interpretations of RFC 1573 / MIB-II as they apply to LAN
--    Emulation Clients.
--  Module
--    >>current<<
--   MandGroup
--    leClientStatusGroup
--   MandGroup
--    leClientMappingGroup
--   MandGroup
--    leClientStatisticsGroup
--   MandGroup
--    leClientServerVccGroup
--   MandGroup
--    leClientAtmAddressesGroup
--   MandGroup
--    leClientMacAddressesGroup
--   MandGroup
--    leClientArpGroup
--   MandGroup
--    leClientConfigGroupV1
--   MandGroup
--    leClientConfigGroupV2
--   MandGroup
--    leClientStatusGroupV2
--   MandGroup
--    leClientStatisticsGroupV2
--   MandGroup
--    leClientAtmAddressesGroupV2
--   MandGroup
--    leClientMacAddressesGroupV2
--   MandGroup
--    leClientArpGroupV2
--   MandGroup
--    leClientMcForwardGroup
--   OptGroup
--    leClientRouteDescriptorsGroup
--   OptGroup
--    leClientRouteDescriptorsGroupV2
--   OptGroup
--    leClientRDArpGroup
--   OptGroup
--    leClientRDArpGroupV2
--   OptGroup
--    leClientMacQueryGroup
--   OptGroup
--    leClientRDQueryGroup
--   OptGroup
--    leClientTlvGroup
--   ObjVar
--    lecRowStatus
--   ObjVar
--    lecOwner
--   ObjVar
--    lecConfigMode
--   ObjVar
--    lecConfigLanType
--   ObjVar
--    lecConfigMaxDataFrameSize
--   ObjVar
--    lecConfigLanName
--   ObjVar
--    lecConfigLesAtmAddress
--   ObjVar
--    lecControlTimeout
--   ObjVar
--    lecMaxUnknownFrameTime
--   ObjVar
--    lecVccTimeoutPeriod
--   ObjVar
--    lecMaxRetryCount
--   ObjVar
--    lecAgingTime
--   ObjVar
--    lecForwardDelayTime
--   ObjVar
--    lecExpectedArpResponseTime
--   ObjVar
--    lecFlushTimeOut
--   ObjVar
--    lecPathSwitchingDelay
--   ObjVar
--    lecMulticastSendType
--   ObjVar
--    lecMulticastSendAvgRate
--   ObjVar
--    lecMulticastSendPeakRate
--   ObjVar
--    lecConnectionCompleteTimer
--   ObjVar
--    lecConfigLecsAtmAddress
--   ObjVar
--    lecInitialControlTimeout
--   ObjVar
--    lecControlTimeoutMultiplier
--   ObjVar
--    lecV2MaxUnknownFrameCount
--   ObjVar
--    lecConfigLocalSegmentID
--   ObjVar
--    lecConfigV2Capable
--   ObjVar
--    lecConfigSelectiveMulticast
--   ObjVar
--    lecForwardDisconnectTimeout
--   ObjVar
--    lecConfigLLCMultiplexCapable
--   ObjVar
--    lecMinReconfigureDelay
--   ObjVar
--    lecMaxReconfigureDelay
--   ObjVar
--    lecMaxBusConnectRetries
--   ObjVar
--    lecTokenRingExplorerExclude
--   ObjVar
--    lecAtmAddressStatus
--   ObjVar
--    lecAtmAddressMuxed
--   ObjVar
--    leArpAtmAddress
--   ObjVar
--    leArpEntryType
--   ObjVar
--    leArpRowStatus
--   ObjVar
--    leArpMuxedAtmAddress
--   ObjVar
--    leArpServiceCategory
--   ObjVar
--    leRDArpAtmAddress
--   ObjVar
--    leRDArpEntryType
--   ObjVar
--    leRDArpRowStatus
--   ObjVar
--    leRDArpMuxedAtmAddress
--   ObjVar
--    leRDArpServiceCategory
--   ObjVar
--    lecTlvType
--   ObjVar
--    lecTlvValue
--   ObjVar
--    lecTlvRowStatus


END

-- MIB created 3/21/96 14:37:01, by
--   SMIC (the next generation) version 1.6.31, December 11, 1994.

LAN-EMULATION-ELAN-MIB DEFINITIONS ::= BEGIN

-- From file: "atm1129r5.mi2"

IMPORTS
    Counter32, Integer32
            FROM SNMPv2-SMI-v1
    OBJECT-TYPE
            FROM RFC-1212
    DisplayString, RowStatus, MacAddress, AutonomousType, TimeStamp
            FROM SNMPv2-TC-v1
    LecDataFrameSize, LecDataFrameFormat, AtmLaneAddress, 
    atmfLanEmulation, VpiInteger, VciInteger
            FROM LAN-EMULATION-CLIENT-MIB;

elanMIB OBJECT IDENTIFIER ::= { atmfLanEmulation 2 }
-- MODULE-IDENTITY
--  LastUpdated
--    9602121200Z
--  OrgName
--    ATM Forum LAN Emulation Sub-Working Group
--  ContactInfo
--    
--      The ATM Forum
--    
--      2570 West El Camino Real,
--      Ste 304,
--      Mountain View, CA 94040-1313
--      Tel: 415-949-6711
--      E-mail: info@atmforum.com
--  Descr
--    This is the MIB module for managing ATM
--     Emulated LANs as well as LAN Emulation
--     Configuration Server (LECS).  It provides 
--     mechanism for constructing and destroying 
--     ELANs, for distributing members of an 
--     ELAN and for figuring out the topology 
--     of an ELAN.  It also provides management
--     information for LECS.

elanAdminGroup  OBJECT IDENTIFIER ::= { elanMIB 1 }
elanConfGroup   OBJECT IDENTIFIER ::= { elanMIB 2 }
elanLecsGroup   OBJECT IDENTIFIER ::= { elanMIB 3 }
elanLecsConfGroup OBJECT IDENTIFIER ::= { elanLecsGroup 1 }
elanLecsFaultGroup OBJECT IDENTIFIER ::= { elanLecsGroup 2 }
elanLecsStatGroup OBJECT IDENTIFIER ::= { elanLecsGroup 3 }
elanAdminPolicyVal OBJECT IDENTIFIER ::= { elanAdminGroup 1 }
byAtmAddr       OBJECT IDENTIFIER ::= { elanAdminPolicyVal 1 }
byMacAddr       OBJECT IDENTIFIER ::= { elanAdminPolicyVal 2 }
byRouteDescriptor OBJECT IDENTIFIER ::= { elanAdminPolicyVal 3 }
byLanType       OBJECT IDENTIFIER ::= { elanAdminPolicyVal 4 }
byPktSize       OBJECT IDENTIFIER ::= { elanAdminPolicyVal 5 }
byElanName      OBJECT IDENTIFIER ::= { elanAdminPolicyVal 6 }
elanMIBConformance OBJECT IDENTIFIER ::= { elanMIB 4 }
elanMIBGroups   OBJECT IDENTIFIER ::= { elanMIBConformance 1 }
elanMIBCompliances OBJECT IDENTIFIER ::= { elanMIBConformance 2 }

IfIndexOrZero ::= INTEGER(0..65535)
-- TEXTUAL-CONVENTION
--  Status
--    mandatory
--  Descr
--    An integer defined as to equivalent
--     to ifIndex in the ifTable defined
--     in RFC 1213 and the value zero.

ElanLocalIndex ::= Integer32
-- TEXTUAL-CONVENTION
--  Status
--    mandatory
--  Descr
--    A value which uniquely identifies a
--     conceptual row in the elanConfTable.
--     This number is only used locally by the agent to
--     distinguish between ELANs.

AtmLaneMask ::= OCTET STRING(SIZE(20))
-- TEXTUAL-CONVENTION
--  Status
--    mandatory
--  Descr
--    A twenty-octet binary string, containing a standard
--     ATM Forum address mask.

TlvSelectorIndexType ::= Integer32
-- TEXTUAL-CONVENTION
--  Status
--    mandatory
--  Descr
--    An arbitrary integer used in identifying
--     a set of TLV encoding.  This number
--     is locally managed by the agent.

PolicySelectorIndexType ::= Integer32
-- TEXTUAL-CONVENTION
--  Status
--    mandatory
--  Descr
--    An arbitrary integer used in identifying
--     a set of LEC assignment policies.  
--     This number is locally managed by the
--     agent.

LecsErrLogIndexType ::= Integer32(1..2147483647)
-- TEXTUAL-CONVENTION
--  Status
--    mandatory
--  Descr
--    An arbitrary integer used in identifying
--     an error log associated with a LECS.

elanConfNextId OBJECT-TYPE
    SYNTAX ElanLocalIndex
--    Rsyntax Integer32
    ACCESS read-only
    STATUS mandatory
    DESCRIPTION
        "The next available ELAN index provided
         by the agent.  The value of this object 
         can be used as the index to the 
         elanConfTable during creation."
    ::= { elanConfGroup 1 }

elanConfTable OBJECT-TYPE
    SYNTAX SEQUENCE OF ElanConfEntry
    ACCESS not-accessible
    STATUS mandatory
    DESCRIPTION
        "This table contains all Emulated LANs
        (ELANs) this agent manages.  An ELAN
        is defined by the ELAN name, a set of
        TLVs, and other parameters.  After an
        ELAN is created, members of the ELAN
        such as the LAN Emulation Server (LES)
        or Client (LEC) can be added to this
        ELAN entry in their repective tables.
        There are four memebers to an ELAN and
        they are LECS, LES, BUS (Broadcast and
        Unknown Server ) and LEC.  The support
        of LECS is optional.  The addition and
        deletion of LECS is done in the 
        elanLecsConfGroup defined in this MIB.
        The addition and deletion of the LEC
        are done in the LEC Assignment tables
        defined in this ELAN Configuration group.
        The addition and deletion of the LES
        are also defined in this group.  The
        addition and deletion of the BUS are
        done in the LES MIB due to the fact that
        LEC learns the BUS address only from
        the LES it corresponds to."
    ::= { elanConfGroup 2 }

elanConfEntry OBJECT-TYPE
    SYNTAX ElanConfEntry
    ACCESS not-accessible
    STATUS mandatory
    DESCRIPTION
        "Each entry in this table represents an
        Emulated LAN.  Objects elanConfIndex
        and elanConfRowStatus are required
        during row creation and deletion. "
    INDEX { elanConfIndex }
    ::= { elanConfTable 1 }

ElanConfEntry ::= SEQUENCE {
    elanConfIndex ElanLocalIndex,
    elanConfName DisplayString,
    elanConfTlvIndex TlvSelectorIndexType,
    elanConfLanType LecDataFrameFormat,
    elanConfMaxFrameSize LecDataFrameSize,
    elanConfRowStatus RowStatus
    }

elanConfIndex OBJECT-TYPE
    SYNTAX ElanLocalIndex
--    Rsyntax Integer32
    ACCESS not-accessible
    STATUS mandatory
    DESCRIPTION
        "A value which uniquely identifies a
         conceptual row in the elanConfTable.
           
         If the conceptual row identified by this value
         of elanConfIndex is recreated following an agent
         restart, the same value of elanConfIndex must be
         used to identify the recreated row."
    ::= { elanConfEntry 1 }

elanConfName OBJECT-TYPE
    SYNTAX DisplayString(SIZE(0..32))
--    Rsyntax OCTET STRING(SIZE(0..32))
    ACCESS read-write
    STATUS mandatory
    DESCRIPTION
        "The name of this Emulated LAN entry.
        When this object length is zero then the 
        ELAN name is not specified.  The clients
        assigned to this ELAN will also have
        a zero length string as the ELAN name.
        
        The value of this object is used in the
        LE CONFIGURE response by the LECS if supported.
        
        Note that ELAN name may be used as cross
        reference to the LES MIB and BUS MIB 
        though not required.  Multiple ELANs 
        with no ELAN name specified will cause 
        conflicts in reference to LES and BUS MIBs."
    REFERENCE
        "LAN Emulation Over ATM Specification -
        version 1.0. C5."
    DEFVAL { "" }
    ::= { elanConfEntry 2 }

elanConfTlvIndex OBJECT-TYPE
    SYNTAX TlvSelectorIndexType
--    Rsyntax Integer32
    ACCESS read-write
    STATUS mandatory
    DESCRIPTION
        "The value of this object identifies
        one or more rows in the lecsTlvTable which
        applies to this ELAN.  This object is 
        set to zero if 1) LECS is not supported.
        or 2) there is no TLV associated with 
        this entry."
    ::= { elanConfEntry 3 }

elanConfLanType OBJECT-TYPE
    SYNTAX LecDataFrameFormat
--    Rsyntax INTEGER {
--        unspecified(1),
--        aflane8023(2),
--        aflane8025(3)
--        }
    ACCESS read-write
    STATUS mandatory
    DESCRIPTION
        "The LAN type of this ELAN entry."
    REFERENCE
        "LAN Emulation Over ATM Specification -
         version 1.0. S2."
    DEFVAL { unspecified }
    ::= { elanConfEntry 4 }

elanConfMaxFrameSize OBJECT-TYPE
    SYNTAX LecDataFrameSize
--    Rsyntax INTEGER {
--        unspecified(1),
--        max1516(2),
--        max4544(3),
--        max9234(4),
--        max18190(5)
--        }
    ACCESS read-write
    STATUS mandatory
    DESCRIPTION
        "The maximum data frame size of this
        ELAN entry.  The maximum AAL-5 SDU size
        of a data frame that this ELAN can support.
        The value of this object is returned to the
        LEC in the LE CONFIGURE response."
    REFERENCE
        "LAN Emulation Over ATM Specification -
        version 1.0. S3."
    DEFVAL { unspecified }
    ::= { elanConfEntry 5 }

elanConfRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
         delete entries in the elanConfTable."
    REFERENCE
        "RFC 1443, [10] Textual Conventions
        for version 2 of the Simple Network Management 
        Protocol (SNMPv2)."
    ::= { elanConfEntry 6 }

elanLesTable OBJECT-TYPE
    SYNTAX SEQUENCE OF ElanLesEntry
    ACCESS not-accessible
    STATUS mandatory
    DESCRIPTION
        "This table contains all LESs for each 
        ELAN specified in the elanConfTable.
         Each ELAN can have more than
         one LES providing LAN Emulation 
         services.  Each LES can service only
        one ELAN.  The table is indexed by the
        elanConfIndex which points to the ELAN
        this LES is providing service to, and
        elanLesIndex which unquely identifies
        a LES.  This table is used for configuration
        of an ELAN only, that is, creating a
        LES in this table does not instantiate
        a LES in the network.  It is done in
        the LES MIB."
    ::= { elanConfGroup 3 }

elanLesEntry OBJECT-TYPE
    SYNTAX ElanLesEntry
    ACCESS not-accessible
    STATUS mandatory
    DESCRIPTION
        "Each entry in this table represents 
         a LES/Emulated LAN pair.  Object
         elanLesAtmAddress besides elanLesRowStatus
         is also required during row creation."
    INDEX { elanConfIndex, elanLesIndex }
    ::= { elanLesTable 1 }

ElanLesEntry ::= SEQUENCE {
    elanLesIndex Integer32,
    elanLesAtmAddress AtmLaneAddress,
    elanLesRowStatus RowStatus
    }

elanLesIndex OBJECT-TYPE
    SYNTAX Integer32
    ACCESS not-accessible
    STATUS mandatory
    DESCRIPTION
        "An arbitrary number which uniquely
        identifies the LES this entry pertains
        to."
    ::= { elanLesEntry 1 }

elanLesAtmAddress OBJECT-TYPE
    SYNTAX AtmLaneAddress
--    Rsyntax OCTET STRING(SIZE(0 | 20))
    ACCESS read-write
    STATUS mandatory
    DESCRIPTION
        "The ATM address of the LES entry.
        If LECS is supported, the value of
        this object is the LES ATM address 
        LECS returns to the LEC in the
        CONFIGURE response.  If LECS
        is not supported, the value of this
        object pertains to the LES ATM address
        network manager provides to the
        LEC."
    DEFVAL { "" }
    ::= { elanLesEntry 2 }

elanLesRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
         delete entries in the elanLesfTable."
    REFERENCE
        "RFC 1443, [10] Textual Conventions
        for version 2 of the Simple Network Management 
        Protocol (SNMPv2)."
    ::= { elanLesEntry 3 }

elanPolicyTable OBJECT-TYPE
    SYNTAX SEQUENCE OF ElanPolicyEntry
    ACCESS not-accessible
    STATUS mandatory
    DESCRIPTION
        "This table contains all policies this
        agent supports for assigning a LEC to
        an ELAN. 
        A set of policies with the same or
        different priorities can be selected
        by the entity which provides ELAN
        configuration service such
        as the LECS.  The policy with the
        highest priority or with the smallest
        elanPolicyPriority , is evaluated
        first.  The policies with the same
        elanPolicyPriority are evaluated
        at the same time with the AND operation.
        When LECS receives a configure
        request, it checks it's policies selected
        from this table to determine which 
        ELAN and LES the LEC will join.
        This table is indexed by a selector
        index and a policy index.  The policy
        index unquely identifies a policy and
        the selector index allows multiple
        policies be selected by one LECS or
        an entity that is providing ELAN
        configuration service."
    ::= { elanConfGroup 4 }

elanPolicyEntry OBJECT-TYPE
    SYNTAX ElanPolicyEntry
    ACCESS not-accessible
    STATUS mandatory
    DESCRIPTION
        "Each entry in this table represents a
         policy supported by the entity which 
         provides ELAN configuration 
         services.  Each policy can be used to
         evaluate the CONFIGURE request from
         the LEC in determining which ELAN it
         belongs to. "
    INDEX { elanPolicySelectorIndex, elanPolicyIndex }
    ::= { elanPolicyTable 1 }

ElanPolicyEntry ::= SEQUENCE {
    elanPolicySelectorIndex PolicySelectorIndexType,
    elanPolicyIndex Integer32,
    elanPolicyPriority Integer32,
    elanPolicyType AutonomousType,
    elanPolicyRowStatus RowStatus
    }

elanPolicySelectorIndex OBJECT-TYPE
    SYNTAX PolicySelectorIndexType
--    Rsyntax Integer32
    ACCESS not-accessible
    STATUS mandatory
    DESCRIPTION
        "The value of this object indicates
        a group of policies that can be selected
        by the ELAN configuration service
            provider such as the LECS."
    ::= { elanPolicyEntry 1 }

elanPolicyIndex OBJECT-TYPE
    SYNTAX Integer32(1..65000)
    ACCESS not-accessible
    STATUS mandatory
    DESCRIPTION
        "The value of this object uniquely
         identifies a single policy entry in
         this table. "
    ::= { elanPolicyEntry 2 }

elanPolicyPriority OBJECT-TYPE
    SYNTAX Integer32(1..65000)
    ACCESS read-write
    STATUS mandatory
    DESCRIPTION
        "The priority of this policy entry. 
         Policies are evaluated by the 
         entity which provides ELAN configuration
         service (LECS) by their
         priorities.  Policies with the
         same priority values should be
         evludated at the same time with
         an AND operation.  That is, if
         one of the policy with the same
         priority is not met,
         the evluation should fail.
         The value 1 has the highest priority. "
    ::= { elanPolicyEntry 3 }

elanPolicyType OBJECT-TYPE
    SYNTAX AutonomousType
--    Rsyntax OBJECT IDENTIFIER
    ACCESS read-write
    STATUS mandatory
    DESCRIPTION
        "
         The value of this object must
         reference a definition of a type
         of policy.  Some of such definition
         exist within the elanAdminPolicyVal
         subtree.  Others may be defined 
         within enterprise specific subtrees.
         The agent is not required to 
         support every types defined
         within the elanAdminPolicyVal subtree."
    ::= { elanPolicyEntry 4 }

elanPolicyRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
         delete entries in the elanPolicyTable."
    REFERENCE
        "RFC 1443, [10] Textual Conventions
        for version 2 of the Simple Network Management 
        Protocol (SNMPv2)."
    ::= { elanPolicyEntry 5 }

elanLecAtmAddrTable OBJECT-TYPE
    SYNTAX SEQUENCE OF ElanLecAtmAddrEntry
    ACCESS not-accessible
    STATUS mandatory
    DESCRIPTION
        "This table is used to assign a LEC
         to an ELAN by ATM address.
         When the by ATM address policy is 
         used, this table is used to specify
         the LEC's ATM address or portion of an ATM
         address.  The ATM address is used by
         the LECS or other entity which serves
         the LANE configuration function to
         determine the ELAN membership.
        
         This table is indexed
         by the elanConfIndex which points
         to the ELAN this LEC belongs, the
         elanLesIndex which points to the
         LES this LEC should join, the
         LEC's ATM address and an ATM address
         mask.  Portions of ATM address
         can be used in dertermining ELAN
         membership by using both the ATM
         address and the mask."
    ::= { elanConfGroup 5 }

elanLecAtmAddrEntry OBJECT-TYPE
    SYNTAX ElanLecAtmAddrEntry
    ACCESS not-accessible
    STATUS mandatory
    DESCRIPTION
        "Each entry represents a LEC to ELAN
        binding."
    INDEX { elanConfIndex, elanLesIndex, elanLecAtmAddress, elanLecAtmMask }
    ::= { elanLecAtmAddrTable 1 }

ElanLecAtmAddrEntry ::= SEQUENCE {
    elanLecAtmAddress AtmLaneAddress,
    elanLecAtmMask AtmLaneAddress,
    elanLecAtmRowStatus RowStatus
    }

elanLecAtmAddress OBJECT-TYPE
    SYNTAX AtmLaneAddress
--    Rsyntax OCTET STRING(SIZE(0 | 20))
    ACCESS not-accessible
    STATUS mandatory
    DESCRIPTION
        "The value of this object is the
        ATM address of a LAN Emulation
        client.  This object and the
        object elanLecAtmMask are used
        to form an ATM address or portion
        of an ATM address to be used
        by the LECS in determining the
        ELAN membership when the policy
        of this LECS is by ATM address."
    ::= { elanLecAtmAddrEntry 1 }

elanLecAtmMask OBJECT-TYPE
    SYNTAX AtmLaneAddress
--    Rsyntax OCTET STRING(SIZE(0 | 20))
    ACCESS read-write
    STATUS mandatory
    DESCRIPTION
        "The ATM address mask associated with
        the object elanLecAtmAddress.  The value
        of the mask is an ATM address with
        the don't care portion set to zero
        and the valid ATM address portion set to one."
    ::= { elanLecAtmAddrEntry 2 }

elanLecAtmRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        destroy entries in this table."
    REFERENCE
        "RFC 1443, [10] Textual Conventions
        for version 2 of the Simple Network Management 
        Protocol (SNMPv2)."
    ::= { elanLecAtmAddrEntry 4 }

elanLecMacAddrTable OBJECT-TYPE
    SYNTAX SEQUENCE OF ElanLecMacAddrEntry
    ACCESS not-accessible
    STATUS mandatory
    DESCRIPTION
        "This table is used to assign a LEC
         to an ELAN by MAC address.
         When the byMacAddress policy is 
         used, this table is used to specify
         the LEC's ELAN membership by ATM
         address.  This table is indexed
         by the elanConfIndex which points
         to the ELAN this LEC belongs, the
         elanLesIndex which points to the
         LES this LEC should join, and the
         LEC's MAC address."
    ::= { elanConfGroup 6 }

elanLecMacAddrEntry OBJECT-TYPE
    SYNTAX ElanLecMacAddrEntry
    ACCESS not-accessible
    STATUS mandatory
    DESCRIPTION
        "Each entry represents a LEC to ELAN
        binding."
    INDEX { elanConfIndex, elanLesIndex, elanLecMacAddress }
    ::= { elanLecMacAddrTable 1 }

ElanLecMacAddrEntry ::= SEQUENCE {
    elanLecMacAddress MacAddress,
    elanLecMacRowStatus RowStatus
    }

elanLecMacAddress OBJECT-TYPE
    SYNTAX MacAddress
--    Rsyntax OCTET STRING(SIZE(6))
    ACCESS not-accessible
    STATUS mandatory
    DESCRIPTION
        "The value of this object is the
        MAC address of a LAN Emulation
        client.  When a CONFIGURE request
        is received with this MAC address,
        it will be assigned to the ELAN
        which elanConfIndex is pointing
        to."
    ::= { elanLecMacAddrEntry 1 }

elanLecMacRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        destroy entries in this table."
    REFERENCE
        "RFC 1443, [10] Textual Conventions
        for version 2 of the Simple Network Management 
        Protocol (SNMPv2)."
    ::= { elanLecMacAddrEntry 2 }

elanLecRdTable OBJECT-TYPE
    SYNTAX SEQUENCE OF ElanLecRdEntry
    ACCESS not-accessible
    STATUS mandatory
    DESCRIPTION
        "This table is used to assign a LEC
        to an ELAN by Route Descriptor.
         When the by Route Descriptor policy is 
        used, this table is used to specify
        the LEC's ELAN membership by Route
        Descriptor.  This table is indexed
        by the elanConfIndex which points
        to the ELAN this LEC belongs, the
        elanLesIndex which points to the
        LES this LEC should join, and the
        LEC's Route Descriptors."
    ::= { elanConfGroup 7 }

elanLecRdEntry OBJECT-TYPE
    SYNTAX ElanLecRdEntry
    ACCESS not-accessible
    STATUS mandatory
    DESCRIPTION
        "Each entry represents a LEC to ELAN
        binding. "
    INDEX { elanConfIndex, elanLesIndex, elanLecRdSegId, elanLecRdBridgeNum }
    ::= { elanLecRdTable 1 }

ElanLecRdEntry ::= SEQUENCE {
    elanLecRdSegId Integer32,
    elanLecRdBridgeNum Integer32,
    elanLecRdRowStatus RowStatus
    }

elanLecRdSegId OBJECT-TYPE
    SYNTAX Integer32(0..4095)
    ACCESS not-accessible
    STATUS mandatory
    DESCRIPTION
        "The LAN ID portion of the IEEE 802.5
        route descriptor associated with this
        conceptual row."
    ::= { elanLecRdEntry 1 }

elanLecRdBridgeNum OBJECT-TYPE
    SYNTAX Integer32(0..15)
    ACCESS not-accessible
    STATUS mandatory
    DESCRIPTION
        "The Bridge Number portion of the
         IEEE 802.5 route descriptor associated
         with this conceptual row."
    ::= { elanLecRdEntry 2 }

elanLecRdRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        destroy entries in this table."
    REFERENCE
        "RFC 1443, [10] Textual Conventions
        for version 2 of the Simple Network Management 
        Protocol (SNMPv2)."
    ::= { elanLecRdEntry 4 }

elanLecPktSizeTable OBJECT-TYPE
    SYNTAX SEQUENCE OF ElanLecPktSizeEntry
    ACCESS not-accessible
    STATUS mandatory
    DESCRIPTION
        "This table is used to assign a LEC
        to an ELAN by Packet Size. When the by 
        Packet Size policy is used, this table is 
        used to specifythe LEC's ELAN membership 
        by Packet Size.  This table is indexed by 
        the elanConfIndex which points to the 
        ELAN this LEC belongs, the elanLesIndex 
        which points to the
        LES this LEC should join, and the
        LEC's Packet Size."
    ::= { elanConfGroup 8 }

elanLecPktSizeEntry OBJECT-TYPE
    SYNTAX ElanLecPktSizeEntry
    ACCESS not-accessible
    STATUS mandatory
    DESCRIPTION
        "Each entry represents a LEC to ELAN
        binding. "
    INDEX { elanConfIndex, elanLesIndex, elanLecFrameSize }
    ::= { elanLecPktSizeTable 1 }

ElanLecPktSizeEntry ::= SEQUENCE {
    elanLecFrameSize LecDataFrameSize,
    elanLecPktSizeRowStatus RowStatus
    }

elanLecFrameSize OBJECT-TYPE
    SYNTAX LecDataFrameSize
--    Rsyntax INTEGER {
--        unspecified(1),
--        max1516(2),
--        max4544(3),
--        max9234(4),
--        max18190(5)
--        }
    ACCESS not-accessible
    STATUS mandatory
    DESCRIPTION
        "The maximum AAL-5 SDU size this LEC can 
        support. "
    ::= { elanLecPktSizeEntry 1 }

elanLecPktSizeRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        destroy entries in this table."
    REFERENCE
        "RFC 1443, [10] Textual Conventions
        for version 2 of the Simple Network Management 
        Protocol (SNMPv2)."
    ::= { elanLecPktSizeEntry 2 }

elanLecNameTable OBJECT-TYPE
    SYNTAX SEQUENCE OF ElanLecNameEntry
    ACCESS not-accessible
    STATUS mandatory
    DESCRIPTION
        "This table is used to assign a LEC
        to an ELAN by ELAN name. When the by ELAN 
        name policy is used, this table is used 
        to specifythe LEC's ELAN membership by 
        ELAN name.  This table is indexed by the 
        elanConfIndex which points to the ELAN 
        this LEC belongs, the elanLesIndex which 
        points to the
        LES this LEC should join, and the
        LEC's ELAN name."
    ::= { elanConfGroup 9 }

elanLecNameEntry OBJECT-TYPE
    SYNTAX ElanLecNameEntry
    ACCESS not-accessible
    STATUS mandatory
    DESCRIPTION
        "Each entry represents a LEC to ELAN
        binding. "
    INDEX { elanConfIndex, elanLesIndex, elanLecElanName }
    ::= { elanLecNameTable 1 }

ElanLecNameEntry ::= SEQUENCE {
    elanLecElanName DisplayString,
    elanLecNameRowStatus RowStatus
    }

elanLecElanName OBJECT-TYPE
    SYNTAX DisplayString(SIZE(0..32))
--    Rsyntax OCTET STRING(SIZE(0..32))
    ACCESS not-accessible
    STATUS mandatory
    DESCRIPTION
        "The name of the ELAN this LEC belongs. "
    ::= { elanLecNameEntry 1 }

elanLecNameRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        destroy entries in this table."
    REFERENCE
        "RFC 1443, [10] Textual Conventions
        for version 2 of the Simple Network Management 
        Protocol (SNMPv2)."
    ::= { elanLecNameEntry 2 }

lecsConfNextId OBJECT-TYPE
    SYNTAX ElanLocalIndex
--    Rsyntax Integer32
    ACCESS read-only
    STATUS mandatory
    DESCRIPTION
        "The next available LECS index.  The
        value of this object can be used as
        the index to the lecsTable during
        creation."
    ::= { elanLecsConfGroup 1 }

lecsConfTable OBJECT-TYPE
    SYNTAX SEQUENCE OF LecsConfEntry
    ACCESS not-accessible
    STATUS mandatory
    DESCRIPTION
        "This table contains the configuration 
         information of all LECS this agent
         manages.  This table can also be
         used to create, delete or configure
         a LECS."
    ::= { elanLecsConfGroup 2 }

lecsConfEntry OBJECT-TYPE
    SYNTAX LecsConfEntry
    ACCESS not-accessible
    STATUS mandatory
    DESCRIPTION
        "Each entry represents a LECS this
        agent maintains. 
        Objects lecsAtmIfIndex, lecsAtmAddrSpec,
        and lecsAtmAddrMask cannot be modified
        unless the lecsAdminStatus is set to
        down(2).  And the change does not take
        effect until the lecsAdminStatus is set
        to up(1)."
    INDEX { lecsConfIndex }
    ::= { lecsConfTable 1 }

LecsConfEntry ::= SEQUENCE {
    lecsConfIndex Integer32,
    lecsAtmIfIndex IfIndexOrZero,
    lecsAtmAddrSpec AtmLaneAddress,
    lecsAtmAddrMask AtmLaneMask,
    lecsAtmAddrActual AtmLaneAddress,
    lecsPolicySelIndex PolicySelectorIndexType,
    lecsLastInitialized TimeStamp,
    lecsOperStatus INTEGER,
    lecsAdminStatus INTEGER,
    lecsRowStatus RowStatus
    }

lecsConfIndex OBJECT-TYPE
    SYNTAX Integer32
    ACCESS not-accessible
    STATUS mandatory
    DESCRIPTION
        "An arbitrary integer which represents
        a LECS this agent manages.  
        If the conceptual row identified by this value
        of lecsConfIndex is recreated following an agent
        restart, the same value of elanConfIndex must be
        used to identify the recreated row."
    ::= { lecsConfEntry 1 }

lecsAtmIfIndex OBJECT-TYPE
    SYNTAX IfIndexOrZero
--    Rsyntax INTEGER(0..65535)
    ACCESS read-write
    STATUS mandatory
    DESCRIPTION
        "An ATM interface which the LECS receives 
         CONFIGURE requests 
         from.  This value must match an existing
         value  in the   ifTable.  This object
         is set to zero when the ATM interface
         is not specified or there is more than
         one ATM interface used by the LECS."
    DEFVAL { '0'h }
    ::= { lecsConfEntry 2 }

lecsAtmAddrSpec OBJECT-TYPE
    SYNTAX AtmLaneAddress
--    Rsyntax OCTET STRING(SIZE(0 | 20))
    ACCESS read-write
    STATUS mandatory
    DESCRIPTION
        "An ATM  address specified by  the  
        network or local management that, 
        with the ATM address mask, determines
        a  portion of  the  ATM address  that 
        the  LECS on the designated ATM interface  
        will use  to derive the actual ATM
        address from the network or ILMI.  The derived
        ATM address is specified in the object
        lecsAtmAddrActual, which is used to
        receive CONFIGURE requests.
        The value of this object, if not
        specified, is defaulted to the 
        well-known LECS ATM address specified
        in the LAN Emulation Spec. 1.0."
    DEFVAL { '4700790000000000000000000000A03E00000100'h }
    ::= { lecsConfEntry 3 }

lecsAtmAddrMask OBJECT-TYPE
    SYNTAX AtmLaneMask
--    Rsyntax OCTET STRING(SIZE(20))
    ACCESS read-write
    STATUS mandatory
    DESCRIPTION
        "The ATM address mask associated with
        the object lecsAtmAddrSpec.  The value
        of the mask is an ATM address with
        the don't care portion set to zero
        and the valid ATM address portion set to one."
    DEFVAL { 'FFFFFFFFFFFFFFFFFFFFFFFFFFFFFFFFFFFFFFFF'h }
    ::= { lecsConfEntry 4 }

lecsAtmAddrActual OBJECT-TYPE
    SYNTAX AtmLaneAddress
--    Rsyntax OCTET STRING(SIZE(0 | 20))
    ACCESS read-only
    STATUS mandatory
    DESCRIPTION
        " The resulting ATM address that the   
        LECS is accepting CONFIGURE    
        requests on the interface indicated
        by the object lecsAtmIfIndex.
        This  address is   the  result of  the 
        specified   ATM address,  its   mask   and 
        interaction through the ILMI  with  the  
        switch. Note  that   this object is only 
        valid  when the corresponding lecsOperStatus 
        is 'up'."
    ::= { lecsConfEntry 5 }

lecsPolicySelIndex OBJECT-TYPE
    SYNTAX PolicySelectorIndexType
--    Rsyntax Integer32
    ACCESS read-only
    STATUS mandatory
    DESCRIPTION
        "The set of policies used
        by this LECS in dertermining
        requesters ELAN membership.
        The policies are defined in
        the elanPolicyTable.  The value
        of this object must exist in the
        elanPolicyTable."
    ::= { lecsConfEntry 6 }

lecsLastInitialized OBJECT-TYPE
    SYNTAX TimeStamp
--    Rsyntax TimeTicks
    ACCESS read-only
    STATUS mandatory
    DESCRIPTION
        "The value of the sysUpTime since
         LECS has last entered the state
         indicated by the object lecsOperStatus."
    ::= { lecsConfEntry 7 }

lecsOperStatus OBJECT-TYPE
    SYNTAX INTEGER {
        other(1),
        up(2),
        down(3)
        }
    ACCESS read-only
    STATUS mandatory
    DESCRIPTION
        " This  object reflects the actual  
        state of  the LECS which  may differ  
        from that   of the  lecsAdminStatus
        object.   This     can occur    when    
        the  interface ifOperStatus     is   
        'down'   but the   corresponding
        lecsAdminStatus is 'up'."
    ::= { lecsConfEntry 8 }

lecsAdminStatus OBJECT-TYPE
    SYNTAX INTEGER {
        up(1),
        down(2)
        }
    ACCESS read-write
    STATUS mandatory
    DESCRIPTION
        "The desired  state of the  LECS on 
        this interface as prescribed by the 
        operator.   The actions of the agent
        will,  if  at all possible,  eventually  
        result in the desired  state being 
        reflected in the lecsOperStatus."
    DEFVAL { up }
    ::= { lecsConfEntry 9 }

lecsRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        delete entries in this table."
    REFERENCE
        "RFC 1443, [10] Textual Conventions
        for version 2 of the Simple Network Management 
        Protocol (SNMPv2)."
    ::= { lecsConfEntry 10 }

lecsElanTable OBJECT-TYPE
    SYNTAX SEQUENCE OF LecsElanEntry
    ACCESS not-accessible
    STATUS mandatory
    DESCRIPTION
        "This table contains the mapping between 
         ELANs and LECS.
        
         When a LECS is deleted from the lecsConfTable, 
         all entries associated with this entry will 
         also be deleted."
    ::= { elanLecsConfGroup 3 }

lecsElanEntry OBJECT-TYPE
    SYNTAX LecsElanEntry
    ACCESS not-accessible
    STATUS mandatory
    DESCRIPTION
        "Each entry represents an ELAN to LECS
         mapping."
    INDEX { elanConfIndex, lecsConfIndex }
    ::= { lecsElanTable 1 }

LecsElanEntry ::= SEQUENCE {
    elanLecsRowStatus RowStatus
    }

elanLecsRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        delete an entry from this table."
    REFERENCE
        "RFC 1443, [10] Textual Conventions
        for version 2 of the Simple Network Management 
        Protocol (SNMPv2)."
    ::= { lecsElanEntry 1 }

lecsTlvTable OBJECT-TYPE
    SYNTAX SEQUENCE OF LecsTlvEntry
    ACCESS not-accessible
    STATUS mandatory
    DESCRIPTION
        "This table contains currently configured
        sets of TLVs in this LECS. These sets can
        include not only the standard TLVs specified
        in the LAN Emulation Spec. 1.0 [1] but
        also the additional parameters
        exchanged between the LECS and LEC.
        This table is indexed by a selector
        index, which allows more than one
        TLV to be selected by an ELAN; and
        the TLV tag, which specified the type
        of the TLV; and a TLV index which
        is used to distinguish between different
        entries with the same TLV tag.
        How does the LECS treat the TLVs
        that are not specified in this table
        in the CONFIGURE requests are not
        defined in this MIB."
    ::= { elanLecsConfGroup 4 }

lecsTlvEntry OBJECT-TYPE
    SYNTAX LecsTlvEntry
    ACCESS not-accessible
    STATUS mandatory
    DESCRIPTION
        "Each entry represents a set of TLV 
        encodings for an ELAN represented 
        by the elanConfIndex.  Objects lecsTlvVal 
        and lecsTlvRowStatus are required during 
        row creation."
    INDEX { lecsTlvSelectorIndex, lecsTlvTag, lecsTlvIndex }
    ::= { lecsTlvTable 1 }

LecsTlvEntry ::= SEQUENCE {
    lecsTlvSelectorIndex TlvSelectorIndexType,
    lecsTlvTag OCTET STRING,
    lecsTlvIndex Integer32,
    lecsTlvVal OCTET STRING,
    lecsTlvRowStatus RowStatus
    }

lecsTlvSelectorIndex OBJECT-TYPE
    SYNTAX TlvSelectorIndexType
--    Rsyntax Integer32
    ACCESS not-accessible
    STATUS mandatory
    DESCRIPTION
        "The value of this object indicates 
        a group of TLVs that can be selected."
    ::= { lecsTlvEntry 1 }

lecsTlvTag OBJECT-TYPE
    SYNTAX OCTET STRING(SIZE(4))
    ACCESS not-accessible
    STATUS mandatory
    DESCRIPTION
        "The value of this object represents the 
        type of the contents of the lecsTlvVal 
        field in the entry.  The OUI field
        in this object occupies the first
        ( or most significant )3 octets.  
        The OUI value 00-A0-3E is used for 
        the standard values defined by the ATM 
        Forum specification."
    ::= { lecsTlvEntry 2 }

lecsTlvIndex OBJECT-TYPE
    SYNTAX Integer32(1..2147483647)
    ACCESS not-accessible
    STATUS mandatory
    DESCRIPTION
        "The index of this TLV encoding entry.  
         The value of this object can be used 
         to distinguish between different entries 
         with the same lecsTlvTag value."
    ::= { lecsTlvEntry 3 }

lecsTlvVal OBJECT-TYPE
    SYNTAX OCTET STRING(SIZE(0..1024))
    ACCESS read-write
    STATUS mandatory
    DESCRIPTION
        "The value of this TLV entry.  Note that
         the length is implied by the length of
         the OCTET STRING."
    ::= { lecsTlvEntry 4 }

lecsTlvRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        destroy entries in this table. "
    REFERENCE
        "RFC 1443, [10] Textual Conventions
        for version 2 of the Simple Network Management 
        Protocol (SNMPv2)."
    ::= { lecsTlvEntry 5 }

lecsVccTable OBJECT-TYPE
    SYNTAX SEQUENCE OF LecsVccEntry
    ACCESS not-accessible
    STATUS mandatory
    DESCRIPTION
        "This table contains all the CONFIG VCCs of the
         LECS.  The CONFIG VCC is used by the LEC to send/
         receive ATM LE CONFIGURE request/response to/from
         the LECS.  This table is writable if PVC is used
         and read only if SVC is used. "
    ::= { elanLecsConfGroup 5 }

lecsVccEntry OBJECT-TYPE
    SYNTAX LecsVccEntry
    ACCESS not-accessible
    STATUS mandatory
    DESCRIPTION
        "Each entry represents a CONFIG VCC
         between a pair of LEC and LECS."
    INDEX { lecsConfIndex, lecsVccIfIndex, lecsVccVpi, lecsVccVci }
    ::= { lecsVccTable 1 }

LecsVccEntry ::= SEQUENCE {
    lecsVccIfIndex IfIndexOrZero,
    lecsVccVpi VpiInteger,
    lecsVccVci VciInteger,
    lecsVccRowStatus RowStatus
    }

lecsVccIfIndex OBJECT-TYPE
    SYNTAX IfIndexOrZero
--    Rsyntax INTEGER(0..65535)
    ACCESS not-accessible
    STATUS mandatory
    DESCRIPTION
        "The ATM interface which the CONFIG VCC is established.
         This value must be an existing value in the 
         ifTable.  The value of this object is set to zero
         when the ATM interface is an internal connection. "
    ::= { lecsVccEntry 1 }

lecsVccVpi OBJECT-TYPE
    SYNTAX VpiInteger
--    Rsyntax INTEGER(0..255)
    ACCESS not-accessible
    STATUS mandatory
    DESCRIPTION
        "The VPI value of the CONFIG VCC.  The object
         lecsVccIfIndex, lecsVccVci and this object
         uniquely identifies a VCC within an ATM system."
    ::= { lecsVccEntry 2 }

lecsVccVci OBJECT-TYPE
    SYNTAX VciInteger
--    Rsyntax INTEGER(0..65535)
    ACCESS not-accessible
    STATUS mandatory
    DESCRIPTION
        "The VCI value of the CONFIG VCC. The object
         lecsVccIfIndex, lecsVccVpi and this object
         uniquely identifies a VCC within an ATM system "
    ::= { lecsVccEntry 3 }

lecsVccRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        destroy entries in this table. "
    REFERENCE
        "RFC 1443, [10] Textual Conventions
        for version 2 of the Simple Network Management 
        Protocol (SNMPv2)."
    ::= { lecsVccEntry 4 }

lecsStatsTable OBJECT-TYPE
    SYNTAX SEQUENCE OF LecsStatsEntry
    ACCESS not-accessible
    STATUS mandatory
    DESCRIPTION
        " A (conceptual) table of statistics 
        associated with all
        LECS instances on the device."
    ::= { elanLecsStatGroup 1 }

lecsStatsEntry OBJECT-TYPE
    SYNTAX LecsStatsEntry
    ACCESS not-accessible
    STATUS mandatory
    DESCRIPTION
        " A (conceptual) row in the 
        lecsStatsTable which corresponds 
        to the statistics kept by a particular
        instance of a LECS."
    INDEX { lecsConfIndex }
-- Augments lecsConfEntry
    ::= { lecsStatsTable 1 }

LecsStatsEntry ::= SEQUENCE {
    lecsStatSuccessful Counter32,
    lecsStatInBadFrames Counter32,
    lecsStatInvalidParam Counter32,
    lecsStatInsufRes Counter32,
    lecsStatAccDenied Counter32,
    lecsStatInvalidReq Counter32,
    lecsStatInvalidDest Counter32,
    lecsStatInvalidAddr Counter32,
    lecsStatNoConf Counter32,
    lecsStatConfError Counter32,
    lecsStatInsufInfo Counter32
    }

lecsStatSuccessful OBJECT-TYPE
    SYNTAX Counter32
    ACCESS read-only
    STATUS mandatory
    DESCRIPTION
        "The number of CONFIGURE requests 
        successfully granted since the agent 
        was last initialized."
    ::= { lecsStatsEntry 1 }

lecsStatInBadFrames OBJECT-TYPE
    SYNTAX Counter32
    ACCESS read-only
    STATUS mandatory
    DESCRIPTION
        "The number of mal formed CONFIGURE
        requests dropped by the LECS."
    ::= { lecsStatsEntry 2 }

lecsStatInvalidParam OBJECT-TYPE
    SYNTAX Counter32
    ACCESS read-only
    STATUS mandatory
    DESCRIPTION
        "The number of CONFIGURE requests 
        rejected due to the invalid request 
        parameters error."
    REFERENCE
        "LAN Emulation Over ATM Spec. v1.0. Table 13"
    ::= { lecsStatsEntry 3 }

lecsStatInsufRes OBJECT-TYPE
    SYNTAX Counter32
    ACCESS read-only
    STATUS mandatory
    DESCRIPTION
        "The number of CONFIGURE requests rejected due
        to the insufficent resources to grant request 
        error."
    REFERENCE
        "LAN Emulation Over ATM Spec. v1.0. Table 13"
    ::= { lecsStatsEntry 4 }

lecsStatAccDenied OBJECT-TYPE
    SYNTAX Counter32
    ACCESS read-only
    STATUS mandatory
    DESCRIPTION
        "The number of CONFIGURE requests rejected due
        to the access denied error."
    REFERENCE
        "LAN Emulation Over ATM Spec. v1.0. Table 13"
    ::= { lecsStatsEntry 5 }

lecsStatInvalidReq OBJECT-TYPE
    SYNTAX Counter32
    ACCESS read-only
    STATUS mandatory
    DESCRIPTION
        "The number of CONFIGURE requests rejected due
        to the invalid requester-id error."
    REFERENCE
        "LAN Emulation Over ATM Spec. v1.0. Table 13"
    ::= { lecsStatsEntry 6 }

lecsStatInvalidDest OBJECT-TYPE
    SYNTAX Counter32
    ACCESS read-only
    STATUS mandatory
    DESCRIPTION
        "The number of CONFIGURE requests rejected due
        to the invalid destination error."
    REFERENCE
        "LAN Emulation Over ATM Spec. v1.0. Table 13"
    ::= { lecsStatsEntry 7 }

lecsStatInvalidAddr OBJECT-TYPE
    SYNTAX Counter32
    ACCESS read-only
    STATUS mandatory
    DESCRIPTION
        "The number of CONFIGURE requests rejected due
        to the invalid ATM address error."
    REFERENCE
        "LAN Emulation Over ATM Spec. v1.0. Table 13"
    ::= { lecsStatsEntry 8 }

lecsStatNoConf OBJECT-TYPE
    SYNTAX Counter32
    ACCESS read-only
    STATUS mandatory
    DESCRIPTION
        "The number of CONFIGURE requests rejected due
        to the LE Client is not recognized error."
    REFERENCE
        "LAN Emulation Over ATM Spec. v1.0. Table 13"
    ::= { lecsStatsEntry 9 }

lecsStatConfError OBJECT-TYPE
    SYNTAX Counter32
    ACCESS read-only
    STATUS mandatory
    DESCRIPTION
        "The number of CONFIGURE requests rejected due
        to the LE_CONFIGURE error."
    REFERENCE
        "LAN Emulation Over ATM Spec. v1.0. Table 13"
    ::= { lecsStatsEntry 10 }

lecsStatInsufInfo OBJECT-TYPE
    SYNTAX Counter32
    ACCESS read-only
    STATUS mandatory
    DESCRIPTION
        "The number of CONFIGURE requests rejected due
        to the insufficient information error."
    REFERENCE
        "LAN Emulation Over ATM Spec. v1.0. Table 13"
    ::= { lecsStatsEntry 11 }

lecsErrCtlTable OBJECT-TYPE
    SYNTAX SEQUENCE OF LecsErrCtlEntry
    ACCESS not-accessible
    STATUS mandatory
    DESCRIPTION
        "This table contains error log control 
         information of all LECS instances.
         This table is an extention to the
         lecsConfTable.  It is used to enable
         or disable error logs for a particular
         LECS entry."
    ::= { elanLecsFaultGroup 1 }

lecsErrCtlEntry OBJECT-TYPE
    SYNTAX LecsErrCtlEntry
    ACCESS not-accessible
    STATUS mandatory
    DESCRIPTION
        "Each entry represents a LECS entry
        in the lecsConfTable."
    INDEX { lecsConfIndex }
-- Augments lecsConfEntry
    ::= { lecsErrCtlTable 1 }

LecsErrCtlEntry ::= SEQUENCE {
    lecsErrCtlAdminStatus INTEGER,
    lecsErrCtlOperStatus INTEGER,
    lecsErrCtlClearLog INTEGER,
    lecsErrCtlMaxEntries INTEGER,
    lecsErrCtlLastEntry LecsErrLogIndexType
    }

lecsErrCtlAdminStatus OBJECT-TYPE
    SYNTAX INTEGER {
        enable(1),
        disable(2)
        }
    ACCESS read-write
    STATUS mandatory
    DESCRIPTION
        "This object is used to enable/disable error 
             logging for the LECS."
    ::= { lecsErrCtlEntry 1 }

lecsErrCtlOperStatus OBJECT-TYPE
    SYNTAX INTEGER {
        other(1),
        active(2),
        outOfRes(3),
        failed(4),
        disabled(5)
        }
    ACCESS read-only
    STATUS mandatory
    DESCRIPTION
        "This object is used to indicate
        the result of a set operation to the
        object lecsErrCtlAdminStatus.
        If the error log was successfully
        started, it is in active(2) mode.
        Otherwise, it is set to either
        outOfRes(3) or failed(4) for
        the respective reasons."
    ::= { lecsErrCtlEntry 2 }

lecsErrCtlClearLog OBJECT-TYPE
    SYNTAX INTEGER {
        noOp(1),
        clear(2)
        }
    ACCESS read-write
    STATUS mandatory
    DESCRIPTION
        "This object is used to clear the error log
         entries associated with this LECS."
    ::= { lecsErrCtlEntry 3 }

lecsErrCtlMaxEntries OBJECT-TYPE
    SYNTAX INTEGER(1..65535)
    ACCESS read-only
    STATUS mandatory
    DESCRIPTION
        "The maximum entries of the error
        log a LECS can support."
    ::= { lecsErrCtlEntry 4 }

lecsErrCtlLastEntry OBJECT-TYPE
    SYNTAX LecsErrLogIndexType
--    Rsyntax Integer32(1..2147483647)
    ACCESS read-write
    STATUS mandatory
    DESCRIPTION
        "The index to the last entry in the error
        log table associated with this LECS."
    ::= { lecsErrCtlEntry 5 }

lecsErrLogTable OBJECT-TYPE
    SYNTAX SEQUENCE OF LecsErrLogEntry
    ACCESS not-accessible
    STATUS mandatory
    DESCRIPTION
        "This table contains error logs
        of the LECS instances enabled
        in the lecsErrCtlTable.  This table
        is indexed by the LECS instance
        index and an arbitrary integer
        uniquely identifies an error
        log."
    ::= { elanLecsFaultGroup 2 }

lecsErrLogEntry OBJECT-TYPE
    SYNTAX LecsErrLogEntry
    ACCESS not-accessible
    STATUS mandatory
    DESCRIPTION
        "Each entry represents a LEC that
         was rejected due to a violation 
         against the policies or an error."
    INDEX { lecsConfIndex, lecsErrLogIndex }
    ::= { lecsErrLogTable 1 }

LecsErrLogEntry ::= SEQUENCE {
    lecsErrLogIndex LecsErrLogIndexType,
    lecsErrLogAtmAddr AtmLaneAddress,
    lecsErrLogErrCode INTEGER,
    lecsErrLogTime TimeStamp
    }

lecsErrLogIndex OBJECT-TYPE
    SYNTAX LecsErrLogIndexType
--    Rsyntax Integer32(1..2147483647)
    ACCESS read-only
    STATUS mandatory
    DESCRIPTION
        "An arbitrary integer which uniquely
        identifies an error log entry. The first
        entry after reset or clearing the error
        log is an assigned value (2^32-1).  Succeding
        entries are assigned with descending values 
        consecutively.  Entries after 1 are discarded.The enabling/disabling 
        of
        the error log capability is done in
        the lecsErrCtlTable."
    ::= { lecsErrLogEntry 1 }

lecsErrLogAtmAddr OBJECT-TYPE
    SYNTAX AtmLaneAddress
--    Rsyntax OCTET STRING(SIZE(0 | 20))
    ACCESS read-only
    STATUS mandatory
    DESCRIPTION
        "The ATM address of the requester
        which sends the CONFIGURE request
        and causes the error to occur. 
        The corresponding error code is
        specified in the object lecsErrLogErrCode."
    ::= { lecsErrLogEntry 2 }

lecsErrLogErrCode OBJECT-TYPE
    SYNTAX INTEGER(0..22)
    ACCESS read-only
    STATUS mandatory
    DESCRIPTION
        "The Error code which indicates the
        cause of the error triggered by the
        CONFIGURE request sent by the
        requester indicated by the value of
        the object lecsErrLogAtmAddr."
    ::= { lecsErrLogEntry 3 }

lecsErrLogTime OBJECT-TYPE
    SYNTAX TimeStamp
--    Rsyntax TimeTicks
    ACCESS read-only
    STATUS mandatory
    DESCRIPTION
        "The sysUpTime when this entry was logged by
         the LECS."
    ::= { lecsErrLogEntry 4 }

elanCConfGroup OBJECT IDENTIFIER ::= { elanMIBGroups 1 }
-- OBJECT-GROUP
--  Status
--    mandatory
--  Descr
--    A collection of objects providing configuration
--     information about an Emulated LAN.
--  objects
--    elanConfNextId, elanConfName, elanConfTlvIndex, 
--    elanConfLanType, elanConfMaxFrameSize, elanConfRowStatus, 
--    elanLecPktSizeRowStatus, elanLecNameRowStatus, 
--    elanLesAtmAddress, elanLesRowStatus, elanPolicyPriority, 
--    elanPolicyType, elanPolicyRowStatus

elanLecAssignByAtmGroup OBJECT IDENTIFIER ::= { elanMIBGroups 2 }
-- OBJECT-GROUP
--  Status
--    mandatory
--  Descr
--    A collection of objects providing ATM addresses
--    of LECs.
--  objects
--    elanLecAtmRowStatus, elanLecAtmMask

elanLecAssignByMacGroup OBJECT IDENTIFIER ::= { elanMIBGroups 3 }
-- OBJECT-GROUP
--  Status
--    mandatory
--  Descr
--    A collection of objects providing MAC addresses
--    of LECs.
--  objects
--    elanLecMacRowStatus

elanLecAssignByRdGroup OBJECT IDENTIFIER ::= { elanMIBGroups 4 }
-- OBJECT-GROUP
--  Status
--    mandatory
--  Descr
--    A collection of objects providing Route Descriptors
--    of LECs.
--  objects
--    elanLecRdRowStatus

lecsCStatGroup OBJECT IDENTIFIER ::= { elanMIBGroups 5 }
-- OBJECT-GROUP
--  Status
--    mandatory
--  Descr
--    A collection of objects providing information
--    about LECS statistics.
--  objects
--    lecsStatSuccessful, lecsStatInBadFrames, lecsStatInvalidParam, 
--    lecsStatInsufRes, lecsStatAccDenied, lecsStatInvalidReq, 
--    lecsStatInvalidDest, lecsStatInvalidAddr, lecsStatNoConf, 
--    lecsStatConfError, lecsStatInsufInfo

lecsCGroup OBJECT IDENTIFIER ::= { elanMIBGroups 6 }
-- OBJECT-GROUP
--  Status
--    mandatory
--  Descr
--    A group of objects used for LECS
--    management only.
--  objects
--    lecsConfNextId, lecsAtmIfIndex, lecsAtmAddrSpec, 
--    lecsAtmAddrMask, lecsAtmAddrActual, elanLecsRowStatus, 
--    lecsPolicySelIndex, lecsTlvVal, lecsTlvRowStatus, 
--    lecsVccRowStatus, lecsLastInitialized, lecsOperStatus, 
--    lecsAdminStatus, lecsRowStatus

lecsCFaultGroup OBJECT IDENTIFIER ::= { elanMIBGroups 7 }
-- OBJECT-GROUP
--  Status
--    mandatory
--  Descr
--    A group of objects used for LECS
--     fault management only.
--  objects
--    lecsErrCtlAdminStatus, lecsErrCtlOperStatus, 
--    lecsErrCtlClearLog, lecsErrCtlMaxEntries, lecsErrCtlLastEntry, 
--    lecsErrLogTime, lecsErrLogIndex, lecsErrLogAtmAddr, 
--    lecsErrLogErrCode

elanMIBCompliance OBJECT IDENTIFIER ::= { elanMIBCompliances 1 }
-- MODULE-COMPLIANCE
--  Status
--    mandatory
--  Descr
--    The compliance statement for SNMP 
--    entities which support ATM LAN Emulation
--    ELAN MIB.
--  Module
--    >>current<<
--   MandGroup
--    elanCConfGroup
--   OptGroup
--    elanLecAssignByAtmGroup
--   OptGroup
--    elanLecAssignByMacGroup
--   OptGroup
--    elanLecAssignByRdGroup
--   OptGroup
--    lecsCStatGroup
--   OptGroup
--    lecsCGroup
--   OptGroup
--    lecsCFaultGroup


END


LAN-EMULATION-LES-MIB DEFINITIONS ::= BEGIN

-- From file: "atm1129r5.mi2"

IMPORTS
    Counter32, Integer32
            FROM SNMPv2-SMI-v1
    OBJECT-TYPE
            FROM RFC-1212
    DisplayString, RowStatus, MacAddress, TruthValue, TimeStamp
            FROM SNMPv2-TC-v1
    LeArpTableEntryType, AtmLaneAddress, VpiInteger, VciInteger, 
    atmfLanEmulation
            FROM LAN-EMULATION-CLIENT-MIB
    IfIndexOrZero, AtmLaneMask
            FROM LAN-EMULATION-ELAN-MIB;

lesMIB OBJECT IDENTIFIER ::= { atmfLanEmulation 3 }
-- MODULE-IDENTITY
--  LastUpdated
--    9602121200Z
--  OrgName
--    ATM Forum LAN Emulation Sub-Working Group
--  ContactInfo
--    
--      The ATM Forum
--    
--      2570 West EL camino Real,
--      Ste 304, Mountain View,
--      CA 94040-1313, USA
--      Tel: 415-578-6860
--      E-mail: info@atmforum.com
--  Descr
--    This is the MIB module for managing ATM
--    LAN Emulation Servers.

lesConfGroup    OBJECT IDENTIFIER ::= { lesMIB 1 }
lesStatGroup    OBJECT IDENTIFIER ::= { lesMIB 2 }
lesLecStatGroup OBJECT IDENTIFIER ::= { lesMIB 3 }
lesFaultGroup   OBJECT IDENTIFIER ::= { lesMIB 4 }
lesMIBConformance OBJECT IDENTIFIER ::= { lesMIB 5 }
lesMIBGroups    OBJECT IDENTIFIER ::= { lesMIBConformance 1 }
lesMIBCompliances OBJECT IDENTIFIER ::= { lesMIBConformance 2 }

LecId ::= INTEGER(0..65279)
-- TEXTUAL-CONVENTION
--  Status
--    mandatory
--  Descr
--    C14 LE Client Identifier.

BusConfIndex ::= Integer32
-- TEXTUAL-CONVENTION
--  Status
--    mandatory
--  Descr
--    A value which uniquely identifies a BUS.
--    This number is only used locally by the agent to
--    distinguish between BUSs.

LesLocalIndex ::= Integer32
-- TEXTUAL-CONVENTION
--  Status
--    mandatory
--  Descr
--    A value which uniquely identifies a 
--    conceptual row in the lesConfTable.
--    This number is only used locally by the agent to
--    distinguish between LESs.

LesLecDataFrameFormat ::= INTEGER {
        aflane8023(2),
        aflane8025(3)
        }
-- TEXTUAL-CONVENTION
--  Status
--    mandatory
--  Descr
--    A 'LAN Type' value.
--    
--     S2  LAN Type.  The type of LAN that the LE Server is servicing.
--  Refer
--    ATM Forum LAN Emulation Over ATM Specification, V1.0,
--     Section 5.1.2.

LesLecDataFrameSize ::= INTEGER {
        max1516(2),
        max4544(3),
        max9234(4),
        max18190(5)
        }
-- TEXTUAL-CONVENTION
--  Status
--    mandatory
--  Descr
--    A 'Maximum Data Frame Size' value.
--    
--    S3  Maximum Data Frame Size.  The maximum AAL-5 SDU size.
--  Refer
--    ATM Forum LAN Emulation Over ATM Specification, V1.0,
--     Section 5.1.2.

LesErrLogIndexType ::= Integer32(1..2147483647)
-- TEXTUAL-CONVENTION
--  Status
--    mandatory
--  Descr
--    An arbitrary integer used in identifying
--    an erro log associated with a LES.

lesConfNextId OBJECT-TYPE
    SYNTAX LesLocalIndex
--    Rsyntax Integer32
    ACCESS read-only
    STATUS mandatory
    DESCRIPTION
        "The next available LES index.  The
        value of this object can be used as
        the index by the network manager to
        create an entry in the lesConfTable."
    ::= { lesConfGroup 1 }

lesConfTable OBJECT-TYPE
    SYNTAX SEQUENCE OF LesConfEntry
    ACCESS not-accessible
    STATUS mandatory
    DESCRIPTION
        "This table contains all LAN Emulation
        Servers this agent manages.  The LES
        is one of the components in the Emulated
        LAN which implements the control coordination function.
        It is the address resolution server for a given ELAN.
        The LES provides a facility for registering and resolving 
        MAC addresses and/or route descriptors to ATM
        addresses.  There can be multiple LES per ELAN 
        but a LES can serve only one ELAN."
    ::= { lesConfGroup 2 }

lesConfEntry OBJECT-TYPE
    SYNTAX LesConfEntry
    ACCESS not-accessible
    STATUS mandatory
    DESCRIPTION
        "Each entry in this table represents a
        LES.  The parameters in each entry apply
        to one emulated LAN served by one LES.
        Objects lesLanType and lesMaxFrameSize
        are also required besides lesRowStatus
        during row creation."
    INDEX { lesConfIndex }
    ::= { lesConfTable 1 }

LesConfEntry ::= SEQUENCE {
    lesConfIndex LesLocalIndex,
    lesAtmAddrSpec AtmLaneAddress,
    lesAtmAddrMask AtmLaneMask,
    lesAtmAddrActual AtmLaneAddress,
    lesElanName DisplayString,
    lesLanType LesLecDataFrameFormat,
    lesLastChange TimeStamp,
    lesMaxFrameSize LesLecDataFrameSize,
    lesControlTimeOut INTEGER,
    lesOperStatus INTEGER,
    lesAdminStatus INTEGER,
    lesRowStatus RowStatus
    }

lesConfIndex OBJECT-TYPE
    SYNTAX LesLocalIndex
--    Rsyntax Integer32
    ACCESS not-accessible
    STATUS mandatory
    DESCRIPTION
        "A value which uniquely identifies a
        conceptual row in the lesConfTable.
        
        If the conceptual row identified by this value
        of lesConfIndex is recreated following an agent
        restart, the same value of lesConfIndex must be
        used to identify the recreated row."
    ::= { lesConfEntry 1 }

lesAtmAddrSpec OBJECT-TYPE
    SYNTAX AtmLaneAddress
--    Rsyntax OCTET STRING(SIZE(0 | 20))
    ACCESS read-write
    STATUS mandatory
    DESCRIPTION
        "An ATM  address specified by  the  
        network or local management that, 
        with the ATM address mask, determines
        a  portion of  the  ATM address  that 
        the  LES on the designated ATM interface  
        will use  to derive the actual ATM
        address from the network or ILMI.  The derived
        ATM address is specified in the object
        lesAtmAddrActual, which is used to
        receive ATM ARP requests."
    REFERENCE
        "LAN Emulation Over ATM Specification -
        version 1.0. S1."
    ::= { lesConfEntry 2 }

lesAtmAddrMask OBJECT-TYPE
    SYNTAX AtmLaneMask
--    Rsyntax OCTET STRING(SIZE(20))
    ACCESS read-write
    STATUS mandatory
    DESCRIPTION
        "The ATM address mask associated with
        the object lesAtmAddrSpec.  The value
        of the mask is an ATM address with
        the don't care portion set to zero
        and the valid ATM address portion set to one."
    REFERENCE
        "LAN Emulation Over ATM Specification -
        version 1.0. S1."
    DEFVAL { 'FFFFFFFFFFFFFFFFFFFFFFFFFFFFFFFFFFFFFFFF'h }
    ::= { lesConfEntry 3 }

lesAtmAddrActual OBJECT-TYPE
    SYNTAX AtmLaneAddress
--    Rsyntax OCTET STRING(SIZE(0 | 20))
    ACCESS read-only
    STATUS mandatory
    DESCRIPTION
        " The resultant ATM address  in use by  the LES.  This
        object is a product of the specified ATM address, mask
        and  interaction  with  the network.  This object is
        created by the agent."
    REFERENCE
        "LAN Emulation Over ATM Specification -
        version 1.0. S1."
    ::= { lesConfEntry 4 }

lesElanName OBJECT-TYPE
    SYNTAX DisplayString(SIZE(0..32))
--    Rsyntax OCTET STRING(SIZE(0..32))
    ACCESS read-write
    STATUS mandatory
    DESCRIPTION
        "The name of the Emulated LAN this LES
        is providing service for.  This object
        may be used to identify the ELAN the LES
        is in."
    REFERENCE
        "LAN Emulation Over ATM Specification -
        version 1.0. C5."
    DEFVAL { "" }
    ::= { lesConfEntry 5 }

lesLanType OBJECT-TYPE
    SYNTAX LesLecDataFrameFormat
--    Rsyntax INTEGER {
--        aflane8023(2),
--        aflane8025(3)
--        }
    ACCESS read-write
    STATUS mandatory
    DESCRIPTION
        "The type of the ATM Emulated LAN this
        LES is providing service to."
    REFERENCE
        "LAN Emulation Over ATM Specification -
        version 1.0. S2."
    ::= { lesConfEntry 6 }

lesLastChange OBJECT-TYPE
    SYNTAX TimeStamp
--    Rsyntax TimeTicks
    ACCESS read-only
    STATUS mandatory
    DESCRIPTION
        "The  value of   sysUpTime  when  this LES 
        has entered the state indicated by the 
        object lesOperStatus."
    ::= { lesConfEntry 7 }

lesMaxFrameSize OBJECT-TYPE
    SYNTAX LesLecDataFrameSize
--    Rsyntax INTEGER {
--        max1516(2),
--        max4544(3),
--        max9234(4),
--        max18190(5)
--        }
    ACCESS read-write
    STATUS mandatory
    DESCRIPTION
        "The maximum AAL-5 SDU size of a data
        frame that the LE service can guarantee
        not to drop because it is too large."
    REFERENCE
        "LAN Emulation Over ATM Specification -
        version 1.0. S3."
    ::= { lesConfEntry 8 }

lesControlTimeOut OBJECT-TYPE
    SYNTAX INTEGER(10..300)
--  Units
--    “seconds
    ACCESS read-write
    STATUS mandatory
    DESCRIPTION
        "Time out period used for timing out most
        request/response control frame interactions.
        This is the time a Client has to issue a join
        request to a LES after a control direct VCC is
        established with a LES."
    REFERENCE
        "LAN Emulation Over ATM Specification -
        version 1.0. S4."
    DEFVAL { 120 }
    ::= { lesConfEntry 9 }

lesOperStatus OBJECT-TYPE
    SYNTAX INTEGER {
        other(1),
        up(2),
        down(3)
        }
    ACCESS read-only
    STATUS mandatory
    DESCRIPTION
        "The operational state of this LES entry. 
         When in 'up' state the LES will respond
         to LEC requests.  Any other state the
         LES is notavailable for service and may
         release all the existing VCCs and refuse
         service to all clients."
    ::= { lesConfEntry 11 }

lesAdminStatus OBJECT-TYPE
    SYNTAX INTEGER {
        up(2),
        down(3)
        }
    ACCESS read-write
    STATUS mandatory
    DESCRIPTION
        "  The  desired  state   of  the  designated   LES  as
        prescribed by the operator. The  actions of the  agent
        will, if at  all  possible, eventually  result  in the
        desired state being  reflected in  the lesOperStatus."
    DEFVAL { up }
    ::= { lesConfEntry 12 }

lesRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        delete entries in the elanConfTable."
    REFERENCE
        "RFC 1443, [10] Textual Conventions
        for version 2 of the Simple Network Management 
        Protocol (SNMPv2)."
    ::= { lesConfEntry 13 }

lesVccTable OBJECT-TYPE
    SYNTAX SEQUENCE OF LesVccEntry
    ACCESS not-accessible
    STATUS mandatory
    DESCRIPTION
        "This table contains all the Control Distribute 
        VCCs used by the LES to distribute control traffic
        to the participating LECs.  The Control Distribute
        VCC can either be point-to-point or point-to-
        multipoint calls.  This table is read only if
        SVCs are used and writable if PVCs are used."
    ::= { lesConfGroup 3 }

lesVccEntry OBJECT-TYPE
    SYNTAX LesVccEntry
    ACCESS not-accessible
    STATUS mandatory
    DESCRIPTION
        "Each entry in this table represents a
        LES entry and it's associated Control Distribute VCC. "
    INDEX { lesConfIndex, lesVccAtmIfIndex, lesVccCtlDistVpi, lesVccCtlDistVci }
    ::= { lesVccTable 1 }

LesVccEntry ::= SEQUENCE {
    lesVccAtmIfIndex IfIndexOrZero,
    lesVccCtlDistVpi VpiInteger,
    lesVccCtlDistVci VciInteger,
    lesVccRowStatus RowStatus
    }

lesVccAtmIfIndex OBJECT-TYPE
    SYNTAX IfIndexOrZero
--    Rsyntax INTEGER(0..65535)
    ACCESS read-write
    STATUS mandatory
    DESCRIPTION
        "The ATM interface which the Control
        Distribute VCC is running on.
        This value must match an existing
        value  in the   ifTable.  
        The value of this object is set
        to zero when the ATM interface is
        an internal connection."
    ::= { lesVccEntry 1 }

lesVccCtlDistVpi OBJECT-TYPE
    SYNTAX VpiInteger
--    Rsyntax INTEGER(0..255)
    ACCESS read-write
    STATUS mandatory
    DESCRIPTION
        "The VPI value of the Control
        Distribute VCC.  The object
        lesVccAtmIfIndex, lesVccCtlDistVci
        and the value of this object uniquely
        identfies a VCC within a ATM host."
    ::= { lesVccEntry 2 }

lesVccCtlDistVci OBJECT-TYPE
    SYNTAX VciInteger
--    Rsyntax INTEGER(0..65535)
    ACCESS read-write
    STATUS mandatory
    DESCRIPTION
        "The VCI value of the Control
        Distribute VCC.  The object
        lesVccAtmIfIndex, lesVccCtlDistVci
        and the value of this object uniquely
        identfies a VCC within a ATM host."
    ::= { lesVccEntry 3 }

lesVccRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        delete entries in the elanConfTable."
    REFERENCE
        "RFC 1443, [10] Textual Conventions
        for version 2 of the Simple Network Management 
        Protocol (SNMPv2)."
    ::= { lesVccEntry 4 }

lesBusTable OBJECT-TYPE
    SYNTAX SEQUENCE OF LesBusEntry
    ACCESS not-accessible
    STATUS mandatory
    DESCRIPTION
        "This table contains the BUSs paired
        with the LESs found in the lesConfTable.
        The BUS (Broadcast and Unknown Server)
        handles data sent by a LE client to
        the broadcast MAC address, all multicast
        traffic, and initial unicast frames
        which are sent by a LAN Emulation Client
        before the data direct target ATM address
        has been resolved."
    ::= { lesConfGroup 4 }

lesBusEntry OBJECT-TYPE
    SYNTAX LesBusEntry
    ACCESS not-accessible
    STATUS mandatory
    DESCRIPTION
        "Each entry in this table represents aLES/BUS 
        pair. Object lesBusAddress is required duringrow 
        creation. This table is indexed by lesConfIndex 
        and lesBusConfIndexto show the pairing 
        relationship betweenthe LES and BUS."
    INDEX { lesConfIndex, lesBusConfIndex }
    ::= { lesBusTable 1 }

LesBusEntry ::= SEQUENCE {
    lesBusConfIndex BusConfIndex,
    lesBusAddress AtmLaneAddress
    }

lesBusConfIndex OBJECT-TYPE
    SYNTAX BusConfIndex
--    Rsyntax Integer32
    ACCESS not-accessible
    STATUS mandatory
    DESCRIPTION
        "A value which uniquely identifies a
        BUS ATM address.
               
        If the BUS ATM address identified by this value
        of lesBusConfIndex is recreated following an agent
        restart, the same value of lesBusConfIndex must be
        used to identify the recreated BUS ATM address."
    ::= { lesBusEntry 1 }

lesBusAddress OBJECT-TYPE
    SYNTAX AtmLaneAddress
--    Rsyntax OCTET STRING(SIZE(0 | 20))
    ACCESS read-only
    STATUS mandatory
    DESCRIPTION
        "The ATM address of the BUS. This BUS is associated
        with LES specified by the lesConfIndex. A BUS may
        have several ATM addresses, this object provides
        the ATM address the LES returns in response to the
        LE-ARP request by the LEC."
    REFERENCE
        "LAN Emulation Over ATM Specification -
        version 1.0. S6."
    ::= { lesBusEntry 2 }

lesLeArpMacTable OBJECT-TYPE
    SYNTAX SEQUENCE OF LesLeArpMacEntry
    ACCESS not-accessible
    STATUS mandatory
    DESCRIPTION
        "This table provides access to an ATM LAN Emulation
        Server's MAC-to-ATM ARP table.  It contains entries
        for unicast addressed, the broadcast address.
        
        When the entry is for broadcast MAC address the 
        corresponding ATM address is of a BUS.
        When the entry is for unicast MAC 
        address the corresponding ATM address represents
        a LEC."
    ::= { lesConfGroup 5 }

lesLeArpMacEntry OBJECT-TYPE
    SYNTAX LesLeArpMacEntry
    ACCESS not-accessible
    STATUS mandatory
    DESCRIPTION
        "An ATM LAN Emulation ARP table entry containing
        information about the binding of one MAC address
        to one ATM address."
    INDEX { lesConfIndex, lesLeArpMacAddr }
    ::= { lesLeArpMacTable 1 }

LesLeArpMacEntry ::= SEQUENCE {
    lesLeArpMacAddr MacAddress,
    lesLeArpLecId LecId,
    lesLeArpAtmAddr AtmLaneAddress,
    lesLeArpEntryType LeArpTableEntryType,
    lesLeArpRowStatus RowStatus
    }

lesLeArpMacAddr OBJECT-TYPE
    SYNTAX MacAddress
--    Rsyntax OCTET STRING(SIZE(6))
    ACCESS not-accessible
    STATUS mandatory
    DESCRIPTION
        "The MAC address for which this table entry provides
         a translation.  Since ATM LAN Emulation uses an LE ARP
         protocol to locate the Broadcast and Unknown Server,
         the value of this object could be the broadcast MAC
         address.
        
         MAC addresses should be unique within any given ATM
         Emulated LAN.  However, there's no requirement that
         they be unique across disjoint emulated LANs."
    ::= { lesLeArpMacEntry 1 }

lesLeArpLecId OBJECT-TYPE
    SYNTAX LecId
--    Rsyntax INTEGER(0..65279)
    ACCESS read-only
    STATUS mandatory
    DESCRIPTION
        "The LE Client Identifier (LECID) of this
        entry.  Each LE Client requires a LECID
        assigned by the LE Server during the
        Join phase.  
        If this entry is for a BUS then this object
        value will be zero."
    ::= { lesLeArpMacEntry 2 }

lesLeArpAtmAddr OBJECT-TYPE
    SYNTAX AtmLaneAddress
--    Rsyntax OCTET STRING(SIZE(0 | 20))
    ACCESS read-write
    STATUS mandatory
    DESCRIPTION
        "The ATM address of the Broadcast & Unknown Server
         or LAN Emulation Client whose MAC address is stored
         in 'lesLeArpMacAddr'.
         This volume may be registered by a LAN Emulation
         Client or specified by network management."
    ::= { lesLeArpMacEntry 3 }

lesLeArpEntryType OBJECT-TYPE
    SYNTAX LeArpTableEntryType
--    Rsyntax INTEGER {
--        other(1),
--        learnedViaControl(2),
--        learnedViaData(3),
--        staticVolatile(4),
--        staticNonVolatile(5)
--        }
    ACCESS read-write
    STATUS mandatory
    DESCRIPTION
        "This object is used to indicate how
        this LE-ARP entry was created.
        The possible values for this object are:
        
          viaRegister(1),  -  agent
          staticVolatile(2), - network manager
          staticNonVolatile(3) - network manager
        
        This object is filled in by agent or network
        manager depending on the type."
    REFERENCE
        "LAN Emulation Client MIB definition."
    DEFVAL { staticVolatile }
    ::= { lesLeArpMacEntry 4 }

lesLeArpRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        delete entries in the elanConfTable."
    REFERENCE
        "RFC 1443, [10] Textual Conventions
        for version 2 of the Simple Network Management 
        Protocol (SNMPv2)."
    ::= { lesLeArpMacEntry 5 }

lesLeArpRdTable OBJECT-TYPE
    SYNTAX SEQUENCE OF LesLeArpRdEntry
    ACCESS not-accessible
    STATUS mandatory
    DESCRIPTION
        "This table provides access to an ATM LAN Emulation
        Server's RouteDescriptor-to-ATM ARP cache.  
        The entries in this table are set-up by the agent
        or network manager depending on the entry type.
        
        The Route Descriptors are presented as Segment Id 
        (ring number) and Bridge number."
    ::= { lesConfGroup 6 }

lesLeArpRdEntry OBJECT-TYPE
    SYNTAX LesLeArpRdEntry
    ACCESS not-accessible
    STATUS mandatory
    DESCRIPTION
        "An ATM LAN Emulation ARP cache entry containing
        information about the binding of one Route
        Descriptor to one ATM address."
    INDEX { lesConfIndex, lesLeArpRdSegId, lesLeArpRdBridgeNum }
    ::= { lesLeArpRdTable 1 }

LesLeArpRdEntry ::= SEQUENCE {
    lesLeArpRdSegId INTEGER,
    lesLeArpRdBridgeNum INTEGER,
    lesLeArpRdLecId LecId,
    lesLeArpRdAtmAddr AtmLaneAddress,
    lesLeArpRdEntryType LeArpTableEntryType,
    lesLeArpRdRowStatus RowStatus
    }

lesLeArpRdSegId OBJECT-TYPE
    SYNTAX INTEGER(0..4095)
    ACCESS not-accessible
    STATUS mandatory
    DESCRIPTION
        "The LAN ID (ring number) portion of the 
         IEEE 802.5 route descriptor associated 
         with this LES."
    ::= { lesLeArpRdEntry 1 }

lesLeArpRdBridgeNum OBJECT-TYPE
    SYNTAX INTEGER(0..15)
    ACCESS not-accessible
    STATUS mandatory
    DESCRIPTION
        "The Bridge Number portion of the 
         IEEE 802.5 route descriptor associated 
         with this LES."
    ::= { lesLeArpRdEntry 2 }

lesLeArpRdLecId OBJECT-TYPE
    SYNTAX LecId
--    Rsyntax INTEGER(0..65279)
    ACCESS read-only
    STATUS mandatory
    DESCRIPTION
        "The LE Client Identifier (LECID) of this
        entry.  Each LE Client requires a LECID
        assigned by the LE Server during the
        Join phase.  "
    ::= { lesLeArpRdEntry 3 }

lesLeArpRdAtmAddr OBJECT-TYPE
    SYNTAX AtmLaneAddress
--    Rsyntax OCTET STRING(SIZE(0 | 20))
    ACCESS read-write
    STATUS mandatory
    DESCRIPTION
        "The ATM address associated with the 
        Route Descriptor."
    ::= { lesLeArpRdEntry 4 }

lesLeArpRdEntryType OBJECT-TYPE
    SYNTAX LeArpTableEntryType
--    Rsyntax INTEGER {
--        other(1),
--        learnedViaControl(2),
--        learnedViaData(3),
--        staticVolatile(4),
--        staticNonVolatile(5)
--        }
    ACCESS read-write
    STATUS mandatory
    DESCRIPTION
        "This object is used to indicate how
        this LE-ARP entry was learned:
        
          viaRegister(1),  -  agent
          staticVolatile(2), - network manager
          staticNonVolatile(3) - network manager
        
        This object is filled in by agent or network
        manager depending on the type."
    DEFVAL { staticVolatile }
    ::= { lesLeArpRdEntry 5 }

lesLeArpRdRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        delete entries in the elanConfTable."
    REFERENCE
        "RFC 1443, [10] Textual Conventions
        for version 2 of the Simple Network Management 
        Protocol (SNMPv2)."
    ::= { lesLeArpRdEntry 6 }

lesLecTableLastChange OBJECT-TYPE
    SYNTAX TimeStamp
--    Rsyntax TimeTicks
    ACCESS read-only
    STATUS mandatory
    DESCRIPTION
        "The value of sysUptime when an entry was created/deleted."
    ::= { lesConfGroup 7 }

lesLecTable OBJECT-TYPE
    SYNTAX SEQUENCE OF LesLecEntry
    ACCESS not-accessible
    STATUS mandatory
    DESCRIPTION
        "This table contains all LAN Emulation
        clients serviced by LESs specified in
        the lesConfTable.  This table can be
        used to retrieve the topology of an
        ELAN, in particular, the LES to LECs
        mapping information.
        
        An entry in this table is filled in 
        by the agent when a LEC registers successfully 
        with the LES.  Objects lesLecCtlDirectVpi
        and lesLecCtlDirectVci can be modified  by the
        network manager after creation if PVC is used."
    ::= { lesConfGroup 8 }

lesLecEntry OBJECT-TYPE
    SYNTAX LesLecEntry
    ACCESS not-accessible
    STATUS mandatory
    DESCRIPTION
        "Each entry represents a LANE client to LES
        binding."
    INDEX { lesConfIndex, lesLecIndex }
    ::= { lesLecTable 1 }

LesLecEntry ::= SEQUENCE {
    lesLecIndex INTEGER,
    lesLecAtmAddr AtmLaneAddress,
    lesLecProxy TruthValue,
    lesLecId LecId,
    lesLecAtmIfIndex IfIndexOrZero,
    lesLecCtlDirectVpi VpiInteger,
    lesLecCtlDirectVci VciInteger,
    lesLecLastChange TimeStamp,
    lesLecState INTEGER,
    lesLecRowStatus RowStatus
    }

lesLecIndex OBJECT-TYPE
    SYNTAX INTEGER(1..65535)
    ACCESS not-accessible
    STATUS mandatory
    DESCRIPTION
        "An arbitrary integer which uniquely identifies
        a LEC in this table."
    ::= { lesLecEntry 1 }

lesLecAtmAddr OBJECT-TYPE
    SYNTAX AtmLaneAddress
--    Rsyntax OCTET STRING(SIZE(0 | 20))
    ACCESS read-only
    STATUS mandatory
    DESCRIPTION
        "The ATM address of the LANE client.  This
        is the primary ATM address of the LEC used
        in joining phase."
    REFERENCE
        "ATM Forum LAN Emulation Over ATM Specification, V1.0,
         Section 5.4.3"
    ::= { lesLecEntry 2 }

lesLecProxy OBJECT-TYPE
    SYNTAX TruthValue
--    Rsyntax INTEGER {
--        true(1),
--        false(2)
--        }
    ACCESS read-only
    STATUS mandatory
    DESCRIPTION
        "Whether this client is acting as a 
        proxy.  Proxy clients are allowed 
        to represent unregistered MAC addresses, 
        and receive copies of LE_ARP_REQUEST
        packets for such addresses."
    REFERENCE
        "ATM Forum LAN Emulation Over ATM Specification, V1.0,
         Section 5.1.1"
    DEFVAL { false }
    ::= { lesLecEntry 3 }

lesLecId OBJECT-TYPE
    SYNTAX LecId
--    Rsyntax INTEGER(0..65279)
    ACCESS read-only
    STATUS mandatory
    DESCRIPTION
        "The LE Client Identifier (LECID) of this
        entry.  Each LE Client requires a LECID 
        assigned by the LE Server during the 
        Join phase.  The LECID is placed
        in control requests by the LE Client and MAY be
        used for echo suppression on multicast data frames
        sent by that LE Client."
    DEFVAL { 0 }
    ::= { lesLecEntry 4 }

lesLecAtmIfIndex OBJECT-TYPE
    SYNTAX IfIndexOrZero
--    Rsyntax INTEGER(0..65535)
    ACCESS read-write
    STATUS mandatory
    DESCRIPTION
        "The ifIndex of ATM port where this LEC entry
        has established the control direct VCC to 
        the LES.  The value of this object 
        maps to an existing ifIndex value in the 
        ifTable of MIB-II. 
        When an internal connection is used, this object is 
        set to zero."
    ::= { lesLecEntry 5 }

lesLecCtlDirectVpi OBJECT-TYPE
    SYNTAX VpiInteger
--    Rsyntax INTEGER(0..255)
    ACCESS read-write
    STATUS mandatory
    DESCRIPTION
        " The VPI of the bi-directional control 
        direct connection between the LEC and LES."
    ::= { lesLecEntry 6 }

lesLecCtlDirectVci OBJECT-TYPE
    SYNTAX VciInteger
--    Rsyntax INTEGER(0..65535)
    ACCESS read-write
    STATUS mandatory
    DESCRIPTION
        " The VCI of the bi-directional control 
        direct connection between the LEC and LES."
    ::= { lesLecEntry 7 }

lesLecLastChange OBJECT-TYPE
    SYNTAX TimeStamp
--    Rsyntax TimeTicks
    ACCESS read-only
    STATUS mandatory
    DESCRIPTION
        "The value of sysUpTime of this entry when the LEC enters
         the state indicated by the object lesLecState."
    ::= { lesLecEntry 8 }

lesLecState OBJECT-TYPE
    SYNTAX INTEGER {
        other(1),
        noLesConnect(2),
        lesConnect(3),
        joining(4),
        addLec(5),
        joinedLes(6)
        }
    ACCESS read-only
    STATUS mandatory
    DESCRIPTION
        "This object is used to indicate the
        status this LEC entry is in from the
        LES's perspective.  The state of this
        object is updated by the agent as 
        it discovers various phases of this LEC."
    ::= { lesLecEntry 9 }

lesLecRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        " This object provides a way for the network manager
        to selectively remove a LE Client from the designated
        LES.  Or in a system where PVCs are used, this table
        is used to configure Control Direct VCCs between LES
        and LEC."
    REFERENCE
        "RFC 1443, [10] Textual Conventions
        for version 2 of the Simple Network Management 
        Protocol (SNMPv2)."
    ::= { lesLecEntry 10 }

lesStatTable OBJECT-TYPE
    SYNTAX SEQUENCE OF LesStatEntry
    ACCESS not-accessible
    STATUS mandatory
    DESCRIPTION
        "This table contains all counters the
        LES maintain.  This table is an extention
        to the lesConfTable.  It provides performance
        and fault counters on a per LES basis."
    ::= { lesStatGroup 1 }

lesStatEntry OBJECT-TYPE
    SYNTAX LesStatEntry
    ACCESS not-accessible
    STATUS mandatory
    DESCRIPTION
        "Each entry in this table contains a
        LES and its counters."
    INDEX { lesConfIndex }
-- Augments lesConfEntry
    ::= { lesStatTable 1 }

LesStatEntry ::= SEQUENCE {
    lesStatJoinOk Counter32,
    lesStatVerNotSup Counter32,
    lesStatInvalidReqParam Counter32,
    lesStatDupLanDest Counter32,
    lesStatDupAtmAddr Counter32,
    lesStatInsRes Counter32,
    lesStatAccDenied Counter32,
    lesStatInvalidReqId Counter32,
    lesStatInvalidLanDest Counter32,
    lesStatInvalidAtmAddr Counter32,
    lesStatInBadPkts Counter32,
    lesStatOutRegFails Counter32,
    lesStatLeArpIn Counter32,
    lesStatLeArpFwd Counter32
    }

lesStatJoinOk OBJECT-TYPE
    SYNTAX Counter32
    ACCESS read-only
    STATUS mandatory
    DESCRIPTION
        "Number of successful Join responses
        send out by the LAN Emulation Server."
    ::= { lesStatEntry 1 }

lesStatVerNotSup OBJECT-TYPE
    SYNTAX Counter32
    ACCESS read-only
    STATUS mandatory
    DESCRIPTION
        "Number of version not supported errors."
    REFERENCE
        "ATM Forum LAN Emulation Over ATM Specification, V1.0,
         Table 13."
    ::= { lesStatEntry 2 }

lesStatInvalidReqParam OBJECT-TYPE
    SYNTAX Counter32
    ACCESS read-only
    STATUS mandatory
    DESCRIPTION
        "Number of invalid request parameters errors."
    REFERENCE
        "ATM Forum LAN Emulation Over ATM Specification, V1.0,
         Table 13."
    ::= { lesStatEntry 3 }

lesStatDupLanDest OBJECT-TYPE
    SYNTAX Counter32
    ACCESS read-only
    STATUS mandatory
    DESCRIPTION
        "Number of duplicate LAN destination errors."
    ::= { lesStatEntry 4 }

lesStatDupAtmAddr OBJECT-TYPE
    SYNTAX Counter32
    ACCESS read-only
    STATUS mandatory
    DESCRIPTION
        "Number of duplicate ATM address errors."
    REFERENCE
        "ATM Forum LAN Emulation Over ATM Specification, V1.0,
         Table 13."
    ::= { lesStatEntry 5 }

lesStatInsRes OBJECT-TYPE
    SYNTAX Counter32
    ACCESS read-only
    STATUS mandatory
    DESCRIPTION
        "Number of insufficient resources to grant 
        errors."
    REFERENCE
        "ATM Forum LAN Emulation Over ATM Specification, V1.0,
         Table 13."
    ::= { lesStatEntry 6 }

lesStatAccDenied OBJECT-TYPE
    SYNTAX Counter32
    ACCESS read-only
    STATUS mandatory
    DESCRIPTION
        "Number of access denied for security 
        reasons errors."
    REFERENCE
        "ATM Forum LAN Emulation Over ATM Specification, V1.0,
         Table 13."
    ::= { lesStatEntry 7 }

lesStatInvalidReqId OBJECT-TYPE
    SYNTAX Counter32
    ACCESS read-only
    STATUS mandatory
    DESCRIPTION
        "Number of invalid LEC ID errors."
    REFERENCE
        "ATM Forum LAN Emulation Over ATM Specification, V1.0,
         Table 13."
    ::= { lesStatEntry 8 }

lesStatInvalidLanDest OBJECT-TYPE
    SYNTAX Counter32
    ACCESS read-only
    STATUS mandatory
    DESCRIPTION
        "Number of invalid LAN destination errors."
    REFERENCE
        "ATM Forum LAN Emulation Over ATM Specification, V1.0,
         Table 13."
    ::= { lesStatEntry 9 }

lesStatInvalidAtmAddr OBJECT-TYPE
    SYNTAX Counter32
    ACCESS read-only
    STATUS mandatory
    DESCRIPTION
        "Number of invalid ATM address errors."
    REFERENCE
        "ATM Forum LAN Emulation Over ATM Specification, V1.0,
         Table 13."
    ::= { lesStatEntry 10 }

lesStatInBadPkts OBJECT-TYPE
    SYNTAX Counter32
    ACCESS read-only
    STATUS mandatory
    DESCRIPTION
        "Number of mal formed ATM ARP requests
        received by the LES."
    ::= { lesStatEntry 11 }

lesStatOutRegFails OBJECT-TYPE
    SYNTAX Counter32
    ACCESS read-only
    STATUS mandatory
    DESCRIPTION
        "Number of registration failures sent
         out by this LES."
    ::= { lesStatEntry 12 }

lesStatLeArpIn OBJECT-TYPE
    SYNTAX Counter32
    ACCESS read-only
    STATUS mandatory
    DESCRIPTION
        "The total number of LE_ARP_REQUEST frames the LES has
        accepted since its last initialization."
    ::= { lesStatEntry 13 }

lesStatLeArpFwd OBJECT-TYPE
    SYNTAX Counter32
    ACCESS read-only
    STATUS mandatory
    DESCRIPTION
        "The number of LE_ARP_REQUESTs that the LES forwarded
        onto the clients (either via the control distribute or
        individually over each control direct) rather than
        answering directly.  This may be due to implementation
        decision (forward all requests) or because the resolution
        to the request did not reside in the LES's LE ARP cache."
    ::= { lesStatEntry 14 }

lesLecStatTable OBJECT-TYPE
    SYNTAX SEQUENCE OF LesLecStatEntry
    ACCESS not-accessible
    STATUS mandatory
    DESCRIPTION
        "This table contains all LE-ARP request
        related counters and error counts on 
        a per LEC-LES pair basis."
    ::= { lesLecStatGroup 1 }

lesLecStatEntry OBJECT-TYPE
    SYNTAX LesLecStatEntry
    ACCESS not-accessible
    STATUS mandatory
    DESCRIPTION
        "Each entry in this table represents a
        LEC and its ARP counters.  This table
        is an extention to the lesLecTable."
    INDEX { lesConfIndex, lesLecIndex }
-- Augments lesLecEntry
    ::= { lesLecStatTable 1 }

LesLecStatEntry ::= SEQUENCE {
    lesLecRecvs Counter32,
    lesLecSends Counter32,
    lesLecInRegReq Counter32,
    lesLecInUnReg Counter32,
    lesLecInLeArpUcast Counter32,
    lesLecInLeArpBcast Counter32,
    lesLecInLeArpResp Counter32,
    lesLecInNarp Counter32
    }

lesLecRecvs OBJECT-TYPE
    SYNTAX Counter32
    ACCESS read-only
    STATUS mandatory
    DESCRIPTION
        "Number of requests received from this
        LEC.  This includes all control
        frames as well as LE-ARP requests."
    ::= { lesLecStatEntry 1 }

lesLecSends OBJECT-TYPE
    SYNTAX Counter32
    ACCESS read-only
    STATUS mandatory
    DESCRIPTION
        "Number of requests or responses
        sent to the LEC entry from this
        LES."
    ::= { lesLecStatEntry 3 }

lesLecInRegReq OBJECT-TYPE
    SYNTAX Counter32
    ACCESS read-only
    STATUS mandatory
    DESCRIPTION
        "Number of Register requests received 
        from this LEC.  "
    ::= { lesLecStatEntry 4 }

lesLecInUnReg OBJECT-TYPE
    SYNTAX Counter32
    ACCESS read-only
    STATUS mandatory
    DESCRIPTION
        "Number of UnRegister requests received 
        from this LEC.  "
    ::= { lesLecStatEntry 5 }

lesLecInLeArpUcast OBJECT-TYPE
    SYNTAX Counter32
    ACCESS read-only
    STATUS mandatory
    DESCRIPTION
        "Number of LE-ARP requests for UNICAST
        address received from this LEC. "
    ::= { lesLecStatEntry 6 }

lesLecInLeArpBcast OBJECT-TYPE
    SYNTAX Counter32
    ACCESS read-only
    STATUS mandatory
    DESCRIPTION
        "Number of LE-ARP requests for MULTICAST
        and Broadcast address received from this LEC. "
    ::= { lesLecStatEntry 7 }

lesLecInLeArpResp OBJECT-TYPE
    SYNTAX Counter32
    ACCESS read-only
    STATUS mandatory
    DESCRIPTION
        "Number of LE-ARP responses 
        received from this LEC. "
    ::= { lesLecStatEntry 8 }

lesLecInNarp OBJECT-TYPE
    SYNTAX Counter32
    ACCESS read-only
    STATUS mandatory
    DESCRIPTION
        "Number of NARP requests 
        received from this LEC. "
    ::= { lesLecStatEntry 10 }

lesErrCtlTable OBJECT-TYPE
    SYNTAX SEQUENCE OF LesErrCtlEntry
    ACCESS not-accessible
    STATUS mandatory
    DESCRIPTION
        "This table contains error log control 
         information of all LES instances.
         This table is an extention to the
         lesConfTable.  It is used to enable
         or disable error logs for a particular
         LES entry."
    ::= { lesFaultGroup 1 }

lesErrCtlEntry OBJECT-TYPE
    SYNTAX LesErrCtlEntry
    ACCESS not-accessible
    STATUS mandatory
    DESCRIPTION
        "Each entry represents a LES entry
        in the lesConfTable."
    INDEX { lesConfIndex }
-- Augments lesConfEntry
    ::= { lesErrCtlTable 1 }

LesErrCtlEntry ::= SEQUENCE {
    lesErrCtlAdminStatus INTEGER,
    lesErrCtlOperStatus INTEGER,
    lesErrCtlClearLog INTEGER,
    lesErrCtlMaxEntries INTEGER,
    lesErrCtlLastEntry LesErrLogIndexType
    }

lesErrCtlAdminStatus OBJECT-TYPE
    SYNTAX INTEGER {
        enable(1),
        disable(2)
        }
    ACCESS read-write
    STATUS mandatory
    DESCRIPTION
        "This object is used to enable/disable error 
        logging for the LES."
    ::= { lesErrCtlEntry 1 }

lesErrCtlOperStatus OBJECT-TYPE
    SYNTAX INTEGER {
        other(1),
        active(2),
        outOfRes(3),
        failed(4)
        }
    ACCESS read-only
    STATUS mandatory
    DESCRIPTION
        "This object is used to indicate
        the result of a set operation to the
        object lesErrCtlAdminStatus.
        If the error log was successfully
        started, it is in active(2) mode.
        Otherwise, it is set to either
        outOfRes(3) or failed(4) for
        the respective reasons."
    ::= { lesErrCtlEntry 2 }

lesErrCtlClearLog OBJECT-TYPE
    SYNTAX INTEGER {
        noOp(1),
        clear(2)
        }
    ACCESS read-write
    STATUS mandatory
    DESCRIPTION
        "This object is used to clear the error log
         entries associated with this LES."
    ::= { lesErrCtlEntry 3 }

lesErrCtlMaxEntries OBJECT-TYPE
    SYNTAX INTEGER(1..65535)
    ACCESS read-only
    STATUS mandatory
    DESCRIPTION
        "The maximum entries of the error
        log a LES can support."
    ::= { lesErrCtlEntry 4 }

lesErrCtlLastEntry OBJECT-TYPE
    SYNTAX LesErrLogIndexType
--    Rsyntax Integer32(1..2147483647)
    ACCESS read-write
    STATUS mandatory
    DESCRIPTION
        "The index to the last entry in the error
         log table for this LES."
    ::= { lesErrCtlEntry 5 }

lesErrLogTable OBJECT-TYPE
    SYNTAX SEQUENCE OF LesErrLogEntry
    ACCESS not-accessible
    STATUS mandatory
    DESCRIPTION
        "This table contains error logs
        of the LES instances enabled
        in the lesErrCtlTable.  This table
        is indexed by the LES instance
        index and an arbitrary integer
        uniquely identifies an error
        log."
    ::= { lesFaultGroup 2 }

lesErrLogEntry OBJECT-TYPE
    SYNTAX LesErrLogEntry
    ACCESS not-accessible
    STATUS mandatory
    DESCRIPTION
        "Each entry represents a JOIN or REGISTER that
         was rejected due to an error."
    INDEX { lesConfIndex, lesErrLogIndex }
    ::= { lesErrLogTable 1 }

LesErrLogEntry ::= SEQUENCE {
    lesErrLogIndex LesErrLogIndexType,
    lesErrLogAtmAddr AtmLaneAddress,
    lesErrLogErrCode INTEGER,
    lesErrLogTime TimeStamp
    }

lesErrLogIndex OBJECT-TYPE
    SYNTAX LesErrLogIndexType
--    Rsyntax Integer32(1..2147483647)
    ACCESS read-only
    STATUS mandatory
    DESCRIPTION
        "An arbitrary integer which uniquely
        identifies an error log entry. The first
        entry after reset or clearing the error
        log is an assigned value (2^32-1).  Succeding
        entries are assigned with descending values 
        consecutively.  Entries after 1 are discarded. The enabling/disabling 
        of
        the error log capability is done in
        the lesErrCtlTable."
    ::= { lesErrLogEntry 1 }

lesErrLogAtmAddr OBJECT-TYPE
    SYNTAX AtmLaneAddress
--    Rsyntax OCTET STRING(SIZE(0 | 20))
    ACCESS read-only
    STATUS mandatory
    DESCRIPTION
        "The ATM address of the requester
        which sends the JOIN or REGISTER request
        and causes the error to occur. 
        The corresponding error code is
        specified in the object lesErrLogErrCode."
    ::= { lesErrLogEntry 2 }

lesErrLogErrCode OBJECT-TYPE
    SYNTAX INTEGER(0..22)
    ACCESS read-only
    STATUS mandatory
    DESCRIPTION
        "The Error code which indicates the
        cause of the error triggered by the
        JOIN or REGISTER request sent by the
        requester indicated by the value of
        the object lesErrLogAtmAddr."
    ::= { lesErrLogEntry 3 }

lesErrLogTime OBJECT-TYPE
    SYNTAX TimeStamp
--    Rsyntax TimeTicks
    ACCESS read-only
    STATUS mandatory
    DESCRIPTION
        "The sysUpTime when this entry was logged by
         the LES."
    ::= { lesErrLogEntry 4 }

lesCConfGroup OBJECT IDENTIFIER ::= { lesMIBGroups 1 }
-- OBJECT-GROUP
--  Status
--    mandatory
--  Descr
--    A collection of objects providing configuration
--     information about the LAN Emulation Services.
--  objects
--    lesConfNextId, lesAtmAddrSpec, lesAtmAddrMask, 
--    lesAtmAddrActual, lesElanName, lesLanType, lesLastChange, 
--    lesControlTimeOut, lesMaxFrameSize, lesVccAtmIfIndex, 
--    lesVccCtlDistVpi, lesVccCtlDistVci, lesVccRowStatus, 
--    lesOperStatus, lesAdminStatus, lesRowStatus, lesBusAddress, 
--    lesLeArpLecId, lesLeArpAtmAddr, lesLeArpEntryType, 
--    lesLeArpRowStatus, lesLecTableLastChange, lesLecAtmIfIndex, 
--    lesLecProxy, lesLecAtmAddr, lesLecId, lesLecCtlDirectVpi, 
--    lesLecCtlDirectVci, lesLecLastChange, lesLecRowStatus, 
--    lesLecState

lesRdGroup OBJECT IDENTIFIER ::= { lesMIBGroups 2 }
-- OBJECT-GROUP
--  Status
--    mandatory
--  Descr
--    A group of objects used for 802.5 
--    ATM LAN Emulation management only.
--  objects
--    lesLeArpRdLecId, lesLeArpRdAtmAddr, lesLeArpRdEntryType, 
--    lesLeArpRdRowStatus

lesCStatGroup OBJECT IDENTIFIER ::= { lesMIBGroups 3 }
-- OBJECT-GROUP
--  Status
--    mandatory
--  Descr
--    A collection of objects providing
--    monitoring information about the
--    LES.
--  objects
--    lesStatJoinOk, lesStatInBadPkts, lesStatOutRegFails, 
--    lesStatVerNotSup, lesStatInvalidReqParam, lesStatDupLanDest, 
--    lesStatDupAtmAddr, lesStatInsRes, lesStatAccDenied, 
--    lesStatInvalidReqId, lesStatInvalidLanDest, 
--    lesStatInvalidAtmAddr, lesStatLeArpIn, lesStatLeArpFwd

lesLecCStatGroup OBJECT IDENTIFIER ::= { lesMIBGroups 4 }
-- OBJECT-GROUP
--  Status
--    mandatory
--  Descr
--    A collection of objects providing
--    monitoring information about the
--    LEC to/from LES traffic.
--  objects
--    lesLecRecvs, lesLecSends, lesLecInRegReq, lesLecInUnReg, 
--    lesLecInLeArpUcast, lesLecInLeArpBcast, lesLecInLeArpResp, 
--    lesLecInNarp

lesFaultCGroup OBJECT IDENTIFIER ::= { lesMIBGroups 5 }
-- OBJECT-GROUP
--  Status
--    mandatory
--  Descr
--    A collection of objects providing
--    fault management for the LES.
--  objects
--    lesErrCtlAdminStatus, lesErrCtlOperStatus, lesErrCtlClearLog, 
--    lesErrCtlMaxEntries, lesErrCtlLastEntry, lesErrLogIndex, 
--    lesErrLogAtmAddr, lesErrLogErrCode, lesErrLogTime

lesMIBCompliance OBJECT IDENTIFIER ::= { lesMIBCompliances 1 }
-- MODULE-COMPLIANCE
--  Status
--    mandatory
--  Descr
--    The compliance statement for SNMP 
--    entities which support the ATM LAN Emulation
--    LES MIB.
--  Module
--    >>current<<
--   MandGroup
--    lesCConfGroup
--   MandGroup
--    lesCStatGroup
--   MandGroup
--    lesLecCStatGroup
--   MandGroup
--    lesFaultCGroup
--   ObjVar
--    lesVccCtlDistVpi
--   ObjVar
--    lesVccCtlDistVci
--   ObjVar
--    lesVccRowStatus
--   ObjVar
--    lesLecAtmIfIndex
--   ObjVar
--    lesLecCtlDirectVpi
--   ObjVar
--    lesLecCtlDirectVci
--   ObjVar
--    lesLecRowStatus
--   OptGroup
--    lesRdGroup


END


LAN-EMULATION-BUS-MIB DEFINITIONS ::= BEGIN

-- From file: "atm1129r5.mi2"

IMPORTS
    Counter32, Integer32
            FROM SNMPv2-SMI-v1
    OBJECT-TYPE
            FROM RFC-1212
    RowStatus, DisplayString, TimeStamp
            FROM SNMPv2-TC-v1
    AtmLaneAddress, VpiInteger, VciInteger, atmfLanEmulation
            FROM LAN-EMULATION-CLIENT-MIB
    IfIndexOrZero, AtmLaneMask
            FROM LAN-EMULATION-ELAN-MIB;

busMIB OBJECT IDENTIFIER ::= { atmfLanEmulation 4 }
-- MODULE-IDENTITY
--  LastUpdated
--    9602121200Z
--  OrgName
--    ATM Forum LAN Emulation Sub-Working Group
--  ContactInfo
--    
--      The ATM Forum
--    
--      2570 West El Camino Real, Ste 304,
--      Mountain View, CA 94040-1313
--      E-mail: info@atmforum.com
--  Descr
--     The MIB module for the management of LANE broadcast and 
--    known servers. This MIB should be used in conjunction
--    with the ELAN and LES MIBs.

busConfGroup    OBJECT IDENTIFIER ::= { busMIB 1 }
busStatGroup    OBJECT IDENTIFIER ::= { busMIB 2 }
busFaultGroup   OBJECT IDENTIFIER ::= { busMIB 3 }
busMIBConformance OBJECT IDENTIFIER ::= { busMIB 4 }
busMIBGroups    OBJECT IDENTIFIER ::= { busMIBConformance 1 }
busMIBCompliances OBJECT IDENTIFIER ::= { busMIBConformance 2 }

BusLocalIndex ::= Integer32
-- TEXTUAL-CONVENTION
--  Status
--    mandatory
--  Descr
--    An unique number identifying an
--    BUS.  This number is only
--    used locally by the agent to
--    distinguish between BUS.

BusErrLogIndexType ::= Integer32(1..2147483647)
-- TEXTUAL-CONVENTION
--  Status
--    mandatory
--  Descr
--    An arbitrary integer used in identifying
--    an erro log associated with a BUS.

busConfNextId OBJECT-TYPE
    SYNTAX BusLocalIndex
--    Rsyntax Integer32
    ACCESS read-only
    STATUS mandatory
    DESCRIPTION
        "The next available BUS index.  The
        value of this object can be used as
        the index by the network manager to
        create an entry in the busConfTable."
    ::= { busConfGroup 1 }

busConfTable OBJECT-TYPE
    SYNTAX SEQUENCE OF BusConfEntry
    ACCESS not-accessible
    STATUS mandatory
    DESCRIPTION
        "This table contains all LAN Emulation
        Broadcast and Unknown Servers (BUS) this 
        agent manages.  The BUS handles data sent
        by an LE Client to the broadcast MAC
        address, all multicast traffic, and initial unicast
        frames which are sent by a LEC before the data
        direct target ATM address has been resolved.
        There can be multiple BUSs per ELAN, but a
        BUS can service only one ELAN."
    ::= { busConfGroup 2 }

busConfEntry OBJECT-TYPE
    SYNTAX BusConfEntry
    ACCESS not-accessible
    STATUS mandatory
    DESCRIPTION
        "Each entry in this table represents a
        BUS.  The parameters in each entry apply
        to one emulated LAN served by one BUS.
        Object busRowStatus is required during
        row creation and deletion.  Object busElanName
        is used to indicate the ELAN this BUS
        is servicing and is used to cross reference
        tables defined in the LAN Emulation Server MIB.
        Note that objects busAtmAddrSpec and busAtmAddrMask
        are used to configure the ATM address of a BUS.
        The BUS typically derives it's ATM address
        from the switch or the network and the actual
        ATM address used is indicated in the object
        busAtmAddrActual."
    INDEX { busConfIndex }
    ::= { busConfTable 1 }

BusConfEntry ::= SEQUENCE {
    busConfIndex BusLocalIndex,
    busConfAtmAddrSpec AtmLaneAddress,
    busConfAtmAddrMask AtmLaneMask,
    busConfAtmAddrActual AtmLaneAddress,
    busConfElanName DisplayString,
    busConfLastChange TimeStamp,
    busConfMaxFrameAge INTEGER,
    busConfOperStatus INTEGER,
    busConfAdminStatus INTEGER,
    busConfRowStatus RowStatus
    }

busConfIndex OBJECT-TYPE
    SYNTAX BusLocalIndex
--    Rsyntax Integer32
    ACCESS not-accessible
    STATUS mandatory
    DESCRIPTION
        "A value which uniquely identifies a
        conceptual row in the busConfTable.
        
        If the conceptual row identified by this value
        of busConfIndex is recreated following an agent
        restart, the same value of busConfIndex must be
        used to identify the recreated row."
    ::= { busConfEntry 1 }

busConfAtmAddrSpec OBJECT-TYPE
    SYNTAX AtmLaneAddress
--    Rsyntax OCTET STRING(SIZE(0 | 20))
    ACCESS read-write
    STATUS mandatory
    DESCRIPTION
        "An ATM  address specified by  the  
        network or local management that, 
        with the ATM address mask, determines
        a  portion of  the  ATM address  that 
        the  BUS on the designated ATM interface  
        will use  to derive the actual ATM
        address from the network or ILMI.  The derived
        ATM address is specified in the object
        busAtmAddrActual, which is used to
        receive multicast or broadcast traffic."
    ::= { busConfEntry 2 }

busConfAtmAddrMask OBJECT-TYPE
    SYNTAX AtmLaneMask
--    Rsyntax OCTET STRING(SIZE(20))
    ACCESS read-write
    STATUS mandatory
    DESCRIPTION
        "The ATM address mask associated with
        the object busAtmAddrSpec.  The value
        of the mask is an ATM address with
        the don't care portion set to zero
        and the valid ATM address portion set to one."
    DEFVAL { 'FFFFFFFFFFFFFFFFFFFFFFFFFFFFFFFFFFFFFFF'h }
    ::= { busConfEntry 3 }

busConfAtmAddrActual OBJECT-TYPE
    SYNTAX AtmLaneAddress
--    Rsyntax OCTET STRING(SIZE(0 | 20))
    ACCESS read-only
    STATUS mandatory
    DESCRIPTION
        " The resultant ATM address  in use by  the BUS.  This
        object is a product of the specified ATM address, mask
        and  interaction  with  the network.  This object is
        created by the agent."
    ::= { busConfEntry 4 }

busConfElanName OBJECT-TYPE
    SYNTAX DisplayString(SIZE(0..32))
--    Rsyntax OCTET STRING(SIZE(0..32))
    ACCESS read-write
    STATUS mandatory
    DESCRIPTION
        "The name of the ELAN this BUS is providing service to."
    ::= { busConfEntry 5 }

busConfLastChange OBJECT-TYPE
    SYNTAX TimeStamp
--    Rsyntax TimeTicks
    ACCESS read-only
    STATUS mandatory
    DESCRIPTION
        "The  value of the sysUpTime  when  this BUS 
        has entered the state indicated by the 
        object busConfOperStatus."
    ::= { busConfEntry 6 }

busConfMaxFrameAge OBJECT-TYPE
    SYNTAX INTEGER(1..4)
    ACCESS read-write
    STATUS mandatory
    DESCRIPTION
        "Time out period for a frame that has been
        received but not been transmitted by BUS
        to all relevant Multicast Send VCCs or
        Multicast Forward VCCs."
    REFERENCE
        "LAN Emulation Over ATM Specification -
        version 1.0. S5."
    DEFVAL { 1 }
    ::= { busConfEntry 7 }

busConfOperStatus OBJECT-TYPE
    SYNTAX INTEGER {
        other(1),
        up(2),
        down(3)
        }
    ACCESS read-only
    STATUS mandatory
    DESCRIPTION
        "The operational state of this BUS entry. 
         When in 'up' state the BUS will forward
         LEC traffic.  Any other state the
         BUS is not available for service and may
         release all the existing VCCs and refuse
         service to all clients."
    ::= { busConfEntry 8 }

busConfAdminStatus OBJECT-TYPE
    SYNTAX INTEGER {
        up(2),
        down(3)
        }
    ACCESS read-write
    STATUS mandatory
    DESCRIPTION
        "  The  desired  state   of  the  designated   BUS  as
        prescribed by the operator. The  actions of the  agent
        will, if at  all  possible, eventually  result  in the
        desired state being  reflected in  the busOperStatus."
    DEFVAL { up }
    ::= { busConfEntry 9 }

busConfRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        delete entries in the busConfTable."
    REFERENCE
        "RFC 1443, [10] Textual Conventions
        for version 2 of the Simple Network Management 
        Protocol (SNMPv2)."
    ::= { busConfEntry 10 }

busVccTable OBJECT-TYPE
    SYNTAX SEQUENCE OF BusVccEntry
    ACCESS not-accessible
    STATUS mandatory
    DESCRIPTION
        "This table contains all the Multicast Forward
        VCCs used by the BUS to forward multicast traffic
        to the participating LECs.  The Multicast Forward
        VCC can either be point-to-point or point-to-
        multipoint calls.  This table is read only if
        SVCs are used and writable if PVCs are used."
    ::= { busConfGroup 3 }

busVccEntry OBJECT-TYPE
    SYNTAX BusVccEntry
    ACCESS not-accessible
    STATUS mandatory
    DESCRIPTION
        "Each entry in this table represents a
         Multicast Forward VCC of the BUS."
    INDEX { busConfIndex, busVccAtmIfIndex, busVccMtFwdVpi, busVccMtFwdVci }
    ::= { busVccTable 1 }

BusVccEntry ::= SEQUENCE {
    busVccAtmIfIndex IfIndexOrZero,
    busVccMtFwdVpi VpiInteger,
    busVccMtFwdVci VciInteger,
    busVccRowStatus RowStatus
    }

busVccAtmIfIndex OBJECT-TYPE
    SYNTAX IfIndexOrZero
--    Rsyntax INTEGER(0..65535)
    ACCESS read-write
    STATUS mandatory
    DESCRIPTION
        "The ATM interface which the Multicast
        Forward VCC is running on.
        This value must match an existing
        value  in the   ifTable.  
        The value of this object is set
        to zero when the ATM interface is
        undefined."
    ::= { busVccEntry 1 }

busVccMtFwdVpi OBJECT-TYPE
    SYNTAX VpiInteger
--    Rsyntax INTEGER(0..255)
    ACCESS read-write
    STATUS mandatory
    DESCRIPTION
        "The VPI value of the Multicast
        Forward VCC.  The object
        busVccAtmIfIndex, busVccMtFwdVci
        and the value of this object uniquely
        identfies a VCC within a ATM host."
    ::= { busVccEntry 2 }

busVccMtFwdVci OBJECT-TYPE
    SYNTAX VciInteger
--    Rsyntax INTEGER(0..65535)
    ACCESS read-write
    STATUS mandatory
    DESCRIPTION
        "The VCI value of the Multicast
        Forward VCC.  The object
        busVccAtmIfIndex, busVccMtFwdVpi
        and the value of this object uniquely
        identfies a VCC within a ATM host."
    ::= { busVccEntry 3 }

busVccRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create or
        delete entries in the busConfTable."
    REFERENCE
        "RFC 1443, [10] Textual Conventions
        for version 2 of the Simple Network Management 
        Protocol (SNMPv2)."
    ::= { busVccEntry 4 }

busLecTableLastChange OBJECT-TYPE
    SYNTAX TimeStamp
--    Rsyntax TimeTicks
    ACCESS read-only
    STATUS mandatory
    DESCRIPTION
        "The value of sysUpTime when an entry of the
         busLecTable was created/deleted."
    ::= { busConfGroup 4 }

busLecTable OBJECT-TYPE
    SYNTAX SEQUENCE OF BusLecEntry
    ACCESS not-accessible
    STATUS mandatory
    DESCRIPTION
        " This table contains the BUS and the 
        actual LECs being serviced by the BUS.
        It can be used as the actual mapping
        between BUS and LEC.
        
        This table provides information
        for Multicast send VCCs
        between BUS and clients.  Objects
        busLecMcastSendAtmIfIndex, busLecMcastSendVpi,
        and busLecMcstSendVci can only be modified
        if PVC is used."
    ::= { busConfGroup 5 }

busLecEntry OBJECT-TYPE
    SYNTAX BusLecEntry
    ACCESS not-accessible
    STATUS mandatory
    DESCRIPTION
        "Each entry represents a BUS to LEC
        mapping."
    INDEX { busConfIndex, busLecAtmAddr }
    ::= { busLecTable 1 }

BusLecEntry ::= SEQUENCE {
    busLecAtmAddr AtmLaneAddress,
    busLecMcastSendAtmIfIndex IfIndexOrZero,
    busLecMcastSendVpi VpiInteger,
    busLecMcastSendVci VciInteger,
    busLecRowStatus RowStatus
    }

busLecAtmAddr OBJECT-TYPE
    SYNTAX AtmLaneAddress
--    Rsyntax OCTET STRING(SIZE(0 | 20))
    ACCESS not-accessible
    STATUS mandatory
    DESCRIPTION
        "The ATM address of the LEC.  This
        is the primary ATM address of the LEC."
    ::= { busLecEntry 1 }

busLecMcastSendAtmIfIndex OBJECT-TYPE
    SYNTAX IfIndexOrZero
--    Rsyntax INTEGER(0..65535)
    ACCESS read-write
    STATUS mandatory
    DESCRIPTION
        "The  ATM  interface  index this BUS uses for 
        Multicast Send traffic.  The value of this
        object has to exist in the ifTable in MIB II
        unless an internal connection is used.  When
        an internal connection is used, this object
        is set to zero."
    ::= { busLecEntry 2 }

busLecMcastSendVpi OBJECT-TYPE
    SYNTAX VpiInteger
--    Rsyntax INTEGER(0..255)
    ACCESS read-write
    STATUS mandatory
    DESCRIPTION
        " The   virtual  path  identifier used to receive
        multicast traffic by this BUS."
    ::= { busLecEntry 4 }

busLecMcastSendVci OBJECT-TYPE
    SYNTAX VciInteger
--    Rsyntax INTEGER(0..65535)
    ACCESS read-write
    STATUS mandatory
    DESCRIPTION
        " The   virtual  channel  identifier used to receive
        multicast traffic by this BUS."
    ::= { busLecEntry 5 }

busLecRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        " This object provides a way for the network manager
        to selectively remove a LE Client from the designated
        BUS.  Or in a system where PVCs are used, this table
        is used to create Multicast Send VCCs between BUS
        and LEC."
    ::= { busLecEntry 6 }

busStatTable OBJECT-TYPE
    SYNTAX SEQUENCE OF BusStatEntry
    ACCESS not-accessible
    STATUS mandatory
    DESCRIPTION
        "This table contains all counters the
        BUS maintain.  This table is an extention
        to the busConfTable."
    ::= { busStatGroup 1 }

busStatEntry OBJECT-TYPE
    SYNTAX BusStatEntry
    ACCESS not-accessible
    STATUS mandatory
    DESCRIPTION
        "Each entry in this table contains a
        BUS and its counters."
    INDEX { busConfIndex }
-- Augments busConfEntry
    ::= { busStatTable 1 }

BusStatEntry ::= SEQUENCE {
    busStatInDiscards Counter32,
    busStatInOctets Counter32,
    busStatInUcastFrms Counter32,
    busStatInMcastFrms Counter32,
    busStatFrmTimeOuts Counter32,
    busStatMcastSendRefused Counter32,
    busStatMcastFwdFailure Counter32
    }

busStatInDiscards OBJECT-TYPE
    SYNTAX Counter32
    ACCESS read-only
    STATUS mandatory
    DESCRIPTION
        "  The number of frames discarded due to resource
        error."
    ::= { busStatEntry 1 }

busStatInOctets OBJECT-TYPE
    SYNTAX Counter32
    ACCESS read-only
    STATUS mandatory
    DESCRIPTION
        "  The number of  octets that  this  BUS has received
        since its initialization."
    ::= { busStatEntry 2 }

busStatInUcastFrms OBJECT-TYPE
    SYNTAX Counter32
    ACCESS read-only
    STATUS mandatory
    DESCRIPTION
        " The number  of  frames that  the BUS  has  received
        which were  unicast data frames  and all control
        frames (i.e. they were flooded from the client)."
    ::= { busStatEntry 3 }

busStatInMcastFrms OBJECT-TYPE
    SYNTAX Counter32
    ACCESS read-only
    STATUS mandatory
    DESCRIPTION
        "  The number of  frames  that  the BUS has  received
        which were multicast frames."
    ::= { busStatEntry 4 }

busStatFrmTimeOuts OBJECT-TYPE
    SYNTAX Counter32
    ACCESS read-only
    STATUS mandatory
    DESCRIPTION
        " The number of frames dropped by 
        the BUS due to time out."
    ::= { busStatEntry 5 }

busStatMcastSendRefused OBJECT-TYPE
    SYNTAX Counter32
    ACCESS read-only
    STATUS mandatory
    DESCRIPTION
        "  The number of  multicast send VCCconnection setup attempts to 
        the BUS which were refused."
    ::= { busStatEntry 6 }

busStatMcastFwdFailure OBJECT-TYPE
    SYNTAX Counter32
    ACCESS read-only
    STATUS mandatory
    DESCRIPTION
        "  The number of  multicast forward VCCconnection setup attempts 
        from the BUS which were unsuccessful
        for any reason."
    ::= { busStatEntry 7 }

busLecStatTable OBJECT-TYPE
    SYNTAX SEQUENCE OF BusLecStatEntry
    ACCESS not-accessible
    STATUS mandatory
    DESCRIPTION
        "This table contains all LEC counters
        the BUS maintains.  This table can also
        be used to retrieve all LECs a BUS
        is providing service to."
    ::= { busStatGroup 2 }

busLecStatEntry OBJECT-TYPE
    SYNTAX BusLecStatEntry
    ACCESS not-accessible
    STATUS mandatory
    DESCRIPTION
        "Each entry in this table represents a
        LEC and its counters."
    INDEX { busConfIndex, busLecAtmAddr }
-- Augments busLecEntry
    ::= { busLecStatTable 1 }

BusLecStatEntry ::= SEQUENCE {
    busLecRecvs Counter32,
    busLecForwards Counter32,
    busLecDiscards Counter32
    }

busLecRecvs OBJECT-TYPE
    SYNTAX Counter32
    ACCESS read-only
    STATUS mandatory
    DESCRIPTION
        "Number of Multicast, Broadcast and
        Unknown Forward requests received by
        the BUS from this LEC."
    ::= { busLecStatEntry 1 }

busLecForwards OBJECT-TYPE
    SYNTAX Counter32
    ACCESS read-only
    STATUS mandatory
    DESCRIPTION
        "Number of Multicast, Broadcast and
        Unkown Forward requests forwarded by
        the BUS from this LEC.  The value
        of this object indicate how many requests
        have been forwarded by the BUS."
    ::= { busLecStatEntry 2 }

busLecDiscards OBJECT-TYPE
    SYNTAX Counter32
    ACCESS read-only
    STATUS mandatory
    DESCRIPTION
        "Number of Multicast, Broadcast and
        Unkown Forward requests discarded by
        the BUS from this LEC.  The value
        of this object indicate how many requests
        have been discarded by the BUS."
    ::= { busLecStatEntry 3 }

busErrCtlTable OBJECT-TYPE
    SYNTAX SEQUENCE OF BusErrCtlEntry
    ACCESS not-accessible
    STATUS mandatory
    DESCRIPTION
        "This table contains error log control 
         information of all BUS instances.
         This table is an extention to the
         busConfTable.  It is used to enable
         or disable error logs for a particular
         BUS entry."
    ::= { busFaultGroup 1 }

busErrCtlEntry OBJECT-TYPE
    SYNTAX BusErrCtlEntry
    ACCESS not-accessible
    STATUS mandatory
    DESCRIPTION
        "Each entry represents a BUS entry
        in the busConfTable."
    INDEX { busConfIndex }
-- Augments busConfEntry
    ::= { busErrCtlTable 1 }

BusErrCtlEntry ::= SEQUENCE {
    busErrCtlAdminStatus INTEGER,
    busErrCtlOperStatus INTEGER,
    busErrCtlClearLog INTEGER,
    busErrCtlMaxEntries INTEGER,
    busErrCtlLastEntry BusErrLogIndexType
    }

busErrCtlAdminStatus OBJECT-TYPE
    SYNTAX INTEGER {
        enable(1),
        disable(2)
        }
    ACCESS read-write
    STATUS mandatory
    DESCRIPTION
        "This object is used to enable/disable error 
        logging for the BUS."
    ::= { busErrCtlEntry 1 }

busErrCtlOperStatus OBJECT-TYPE
    SYNTAX INTEGER {
        other(1),
        active(2),
        outOfRes(3),
        failed(4)
        }
    ACCESS read-only
    STATUS mandatory
    DESCRIPTION
        "This object is used to indicate
        the result of a set operation to the
        object busErrCtlAdminStatus.
        If the error log was successfully
        started, it is in active(2) mode.
        Otherwise, it is set to either
        outOfRes(3) or failed(4) for
        the respective reasons."
    ::= { busErrCtlEntry 2 }

busErrCtlClearLog OBJECT-TYPE
    SYNTAX INTEGER {
        noOp(1),
        clear(2)
        }
    ACCESS read-write
    STATUS mandatory
    DESCRIPTION
        "This object is used to clear the error log
         entries associated with this BUS."
    ::= { busErrCtlEntry 3 }

busErrCtlMaxEntries OBJECT-TYPE
    SYNTAX INTEGER(1..65535)
    ACCESS read-only
    STATUS mandatory
    DESCRIPTION
        "The maximum entries of the error
        log a BUS can support."
    ::= { busErrCtlEntry 4 }

busErrCtlLastEntry OBJECT-TYPE
    SYNTAX BusErrLogIndexType
--    Rsyntax Integer32(1..2147483647)
    ACCESS read-write
    STATUS mandatory
    DESCRIPTION
        "The index to the last entry in the error
         log table for this BUS."
    ::= { busErrCtlEntry 5 }

busErrLogTable OBJECT-TYPE
    SYNTAX SEQUENCE OF BusErrLogEntry
    ACCESS not-accessible
    STATUS mandatory
    DESCRIPTION
        "This table contains error logs
        of the BUS instances enabled
        in the busErrCtlTable.  This table
        is indexed by the BUS instance
        index and an arbitrary integer
        uniquely identifies an error
        log."
    ::= { busFaultGroup 2 }

busErrLogEntry OBJECT-TYPE
    SYNTAX BusErrLogEntry
    ACCESS not-accessible
    STATUS mandatory
    DESCRIPTION
        "Each entry represents aan error detected by the BUS."
    INDEX { busConfIndex, busErrLogIndex }
    ::= { busErrLogTable 1 }

BusErrLogEntry ::= SEQUENCE {
    busErrLogIndex BusErrLogIndexType,
    busErrLogAtmAddr AtmLaneAddress,
    busErrLogErrCode INTEGER,
    busErrLogTime TimeStamp
    }

busErrLogIndex OBJECT-TYPE
    SYNTAX BusErrLogIndexType
--    Rsyntax Integer32(1..2147483647)
    ACCESS read-only
    STATUS mandatory
    DESCRIPTION
        "An arbitrary integer which uniquely
        identifies an error log entry. The first
        entry after reset or clearing the error
        log is an assigned value (2^32-1).  Succeding
        entries are assigned with descending values 
        consecutively.  Entries after 1 are discarded.The enabling/disabling 
        of
        the error log capability is done in
        the busErrCtlTable."
    ::= { busErrLogEntry 1 }

busErrLogAtmAddr OBJECT-TYPE
    SYNTAX AtmLaneAddress
--    Rsyntax OCTET STRING(SIZE(0 | 20))
    ACCESS read-only
    STATUS mandatory
    DESCRIPTION
        "The primary ATM address of the LE Client on whose Multicast
        Send VCC the error occured. 
        The corresponding error code is
        specified in the object busErrLogErrCode."
    ::= { busErrLogEntry 2 }

busErrLogErrCode OBJECT-TYPE
    SYNTAX INTEGER {
        outOfRes(1),
        badCtlFrame(2),
        badDataFrame(3),
        other(4)
        }
    ACCESS read-only
    STATUS mandatory
    DESCRIPTION
        "The Error code which indicates the
        cause of the error."
    ::= { busErrLogEntry 3 }

busErrLogTime OBJECT-TYPE
    SYNTAX TimeStamp
--    Rsyntax TimeTicks
    ACCESS read-only
    STATUS mandatory
    DESCRIPTION
        "The sysUpTime when this entry was logged by
         the BUS."
    ::= { busErrLogEntry 4 }

busCConfGroup OBJECT IDENTIFIER ::= { busMIBGroups 1 }
-- OBJECT-GROUP
--  Status
--    mandatory
--  Descr
--     A collection of objects for the 
--    managing of BUS operation.
--  objects
--    busConfNextId, busConfAtmAddrSpec, busConfAtmAddrMask, 
--    busConfAtmAddrActual, busConfElanName, busConfLastChange, 
--    busConfMaxFrameAge, busConfOperStatus, busConfAdminStatus, 
--    busConfRowStatus, busVccAtmIfIndex, busVccMtFwdVpi, 
--    busVccMtFwdVci, busVccRowStatus, busLecTableLastChange, 
--    busLecMcastSendAtmIfIndex, busLecMcastSendVpi, 
--    busLecMcastSendVci, busLecRowStatus

busCStatGroup OBJECT IDENTIFIER ::= { busMIBGroups 2 }
-- OBJECT-GROUP
--  Status
--    mandatory
--  Descr
--     A collection of objects providing information
--    about BUS statistics.
--  objects
--    busStatInOctets, busStatInDiscards, busStatInUcastFrms, 
--    busStatInMcastFrms, busStatFrmTimeOuts, 
--    busStatMcastSendRefused, busStatMcastFwdFailure

busCFaultGroup OBJECT IDENTIFIER ::= { busMIBGroups 3 }
-- OBJECT-GROUP
--  Status
--    mandatory
--  Descr
--     A collection of objects providing information
--    about BUS statistics.
--  objects
--    busErrLogAtmAddr, busErrLogIndex, busErrLogErrCode, 
--    busErrLogTime, busErrCtlAdminStatus, busErrCtlOperStatus, 
--    busErrCtlClearLog, busErrCtlMaxEntries, busErrCtlLastEntry

busLecCGroup OBJECT IDENTIFIER ::= { busMIBGroups 4 }
-- OBJECT-GROUP
--  Status
--    mandatory
--  Descr
--     A collection of objects providing information
--    about LEC-BUS statistics.
--  objects
--    busLecRecvs, busLecForwards, busLecDiscards

busMIBCompliance OBJECT IDENTIFIER ::= { busMIBCompliances 1 }
-- MODULE-COMPLIANCE
--  Status
--    mandatory
--  Descr
--     The compliance statement for SNMP entities that support
--    the ATM LAN Emulation BUS MIB.
--  Module
--    >>current<<
--   MandGroup
--    busCConfGroup
--   MandGroup
--    busCStatGroup
--   MandGroup
--    busCFaultGroup
--   ObjVar
--    busConfAtmAddrSpec
--   ObjVar
--    busConfAtmAddrMask
--   ObjVar
--    busConfElanName
--   ObjVar
--    busConfAdminStatus
--   ObjVar
--    busConfRowStatus
--   ObjVar
--    busVccAtmIfIndex
--   ObjVar
--    busVccMtFwdVpi
--   ObjVar
--    busVccMtFwdVci
--   ObjVar
--    busVccRowStatus
--   ObjVar
--    busLecMcastSendAtmIfIndex
--   ObjVar
--    busLecMcastSendVpi
--   ObjVar
--    busLecMcastSendVci
--   ObjVar
--    busLecRowStatus
--   OptGroup
--    busLecCGroup


END

PNNI-MIB DEFINITIONS ::= BEGIN

-- From file: "afpnni.mi2"
-- Compile options "A M"

IMPORTS
    null, enterprises
            FROM RFC1155-SMI
    Counter32, Gauge32, Integer32
            FROM SNMPv2-SMI-v1
    OBJECT-TYPE
            FROM RFC-1212
    RowStatus, DisplayString, TimeStamp, TruthValue
            FROM SNMPv2-TC-v1
    ifIndex
            FROM RFC1213-MIB
    atmForumNetworkManagement
            FROM LAN-EMULATION-CLIENT-MIB
    AtmTrafficDescrParamIndex
            FROM ATM-TC-MIB
    InterfaceIndex
	    FROM IF-MIB;

-- InterfaceIndex ::= INTEGER (0..2147483647)

-- pnniMIB OBJECT IDENTIFIER ::= { atmfPnni 1 }
--    NOTE: ghuie 12/09/97  This leaf definition commented out here to
--          show original location, moved to location below so that
--          SNMPc and HP OpenView MIB compilers can work correctly.
--
-- MODULE-IDENTITY
--  LastUpdated
--    9705010000Z
--  OrgName
--    The ATM Forum
--  ContactInfo
--    The ATM Forum
--     2570 West El Camino Real, Suite 304
--     Mountain View, CA 94040-1313 USA
--     Phone: +1 415-949-6700
--     Fax:   +1 415-949-6705
--     info@atmforum.com
--  Descr
--    The MIB module for managing ATM Forum PNNI routing.
--  RevDate
--    9705010000Z
--  RevDescr
--    Updated version of the PNNI MIB released with the PNNI
--     V1.0 Errata and PICS (af-pnni-0081.000).
--  RevDate
--    9602270000Z
--  RevDescr
--    Initial version of the MIB for monitoring and controlling
--     PNNI routing.

atmfPnni        OBJECT IDENTIFIER ::= { atmForumNetworkManagement 4 }
pnniMIB OBJECT IDENTIFIER ::= { atmfPnni 1 }
pnniMIBObjects  OBJECT IDENTIFIER ::= { pnniMIB 1 }
pnniBaseGroup   OBJECT IDENTIFIER ::= { pnniMIBObjects 1 }
pnniRoutingGroup OBJECT IDENTIFIER ::= { pnniMIBObjects 19 }
pnniRouteBaseGroup OBJECT IDENTIFIER ::= { pnniRoutingGroup 1 }
pnniMIBConformance OBJECT IDENTIFIER ::= { pnniMIB 2 }
pnniMIBCompliances OBJECT IDENTIFIER ::= { pnniMIBConformance 1 }
pnniMIBGroups   OBJECT IDENTIFIER ::= { pnniMIBConformance 2 }

-- zeroDotZero OBJECT IDENTIFIER ::= { ccitt 0 }
-- OBJECT-IDENTITY
--  Status
--    mandatory
--  Descr
--    A value used for null identifiers.
--    
--     This definition, which is in compliance with RFC 1902, is a
--     temporary inclusion in the PNNI MIB until such time as MIB
--     compilers are upgraded and thereby can accept references to
--     the new definitions in RFC 1902.
--  Refer
--    RFC 1902

-- Unsigned32 ::= Gauge32
-- TEXTUAL-CONVENTION
--  Status
--    mandatory
--  Descr
--    This definition, which is in compliance with RFC 1902, is a
--     temporary inclusion in the PNNI MIB until such time as MIB
--     compilers are upgraded and thereby can accept references to
--     the new definitions in RFC 1902.
--  Refer
--    RFC 1902

PnniAtmAddr ::= OCTET STRING(SIZE(0..20))
-- TEXTUAL-CONVENTION
--  Status
--    mandatory
--  Descr
--    The ATM address used by the network entity.  The address
--     types are: no address (0 octets), and NSAP (20 octets).
--  Refer
--    ATM Forum PNNI 1.0 Section 5.2

PnniNodeIndex ::= Integer32(0..65535)
-- TEXTUAL-CONVENTION
--  Status
--    mandatory
--  Descr
--    An index that identifies a logical PNNI entity within the
--     managed system.
--    
--     The distinguished value zero indicates the null instance or
--     no instance in the PnniNodeCfgParentNodeIndex.  In all
--     other cases, the distinguished value zero indicates a
--     logical entity within the switching system that manages
--     routes only over non-PNNI interfaces.
--    
--     By default, only the node identified by node index one is
--     created, and all PNNI interfaces are associated with that
--     node.

PnniNodeId ::= OCTET STRING(SIZE(22))
-- TEXTUAL-CONVENTION
--  Status
--    mandatory
--  Descr
--    A PNNI node ID - this is used to identify the logical PNNI
--     node.
--  Refer
--    ATM Forum PNNI 1.0 Section 5.3.3

PnniPortId ::= INTEGER
-- PnniPortId ::= Unsigned32
-- Rsyntax Gauge32
-- TEXTUAL-CONVENTION
--  Status
--    mandatory
--  Descr
--    A PNNI port ID - this is used to identify a point of
--     attachment of a logical link to a given logical node.
--    
--     The values 0 and 0xffffffff have special meanings in
--     certain contexts and do not identify a specific port.
--    
--     The distinguished value 0 indicates that no port is
--     specified.
--  Refer
--    ATM Forum PNNI 1.0 Section 5.3.4

PnniAggrToken ::= INTEGER
-- PnniAggrToken ::= Unsigned32
-- Rsyntax Gauge32
-- TEXTUAL-CONVENTION
--  Status
--    mandatory
--  Descr
--    A PNNI aggregation token - this is used to determine which
--     links to a given neighbor node are to be aggregated and
--     advertised as a single logical link.
--  Refer
--    ATM Forum PNNI 1.0 Section 5.3.5

PnniPeerGroupId ::= OCTET STRING(SIZE(14))
-- TEXTUAL-CONVENTION
--  Status
--    mandatory
--  Descr
--    A PNNI peer group ID.
--  Refer
--    ATM Forum PNNI 1.0 Section 5.3.2

PnniLevel ::= Integer32(0..104)
-- TEXTUAL-CONVENTION
--  Status
--    mandatory
--  Descr
--    A PNNI routing level indicator.
--  Refer
--    ATM Forum PNNI 1.0 Section 5.3.1

PnniSvccRccIndex ::= Integer32
-- TEXTUAL-CONVENTION
--  Status
--    mandatory
--  Descr
--    The value of this object identifies the SVCC-based RCC for
--     which the entry contains management information.

AtmAddrPrefix ::= OCTET STRING(SIZE(19))
-- TEXTUAL-CONVENTION
--  Status
--    mandatory
--  Descr
--    A prefix of one or more ATM End System Addresses.  The
--     significant portion of a prefix is padded with zeros on the
--     right to fill 19 octets.
--  Refer
--    ATM Forum PNNI 1.0 Section 5.2

PnniPrefixLength ::= Integer32(0..152)
-- TEXTUAL-CONVENTION
--  Status
--    mandatory
--  Descr
--    The number of bits that are significant in an ATM address
--     prefix used by PNNI.
--  Refer
--    ATM Forum PNNI 1.0 Section 5.2

PnniMetricsTag ::= Integer32(0..2147483647)
-- TEXTUAL-CONVENTION
--  Status
--    mandatory
--  Descr
--    An index into the pnniMetricsTable.  The suffix tag is used
--     to indicate that there may be many related entries in the
--     table further discriminated by other index terms.  The
--     distinguished value zero indicates that no metrics are
--     associated with the described entity.

ServiceCategory ::= INTEGER {
        other(1),
        cbr(2),
        rtVbr(3),
        nrtVbr(4),
        abr(5),
        ubr(6)
        }
-- TEXTUAL-CONVENTION
--  Status
--    mandatory
--  Descr
--    Indicates the service category.
--  Refer
--    ATM Forum Traffic Management 4.0 Section 2

ClpType ::= INTEGER {
        clpEqual0(1),
        clpEqual0Or1(2)
        }
-- TEXTUAL-CONVENTION
--  Status
--    mandatory
--  Descr
--    Indicates the CLP type of a traffic stream.

TnsType ::= INTEGER {
        nationalNetworkIdentification(2),
        other(8)
        }
-- TEXTUAL-CONVENTION
--  Status
--    mandatory
--  Descr
--    Indicates the type of network identification of a
--     specified transit network.
--  Refer
--    ATM Forum UNI Signalling 4.0 Section 2 4.5.22/Q.2931

TnsPlan ::= INTEGER {
        carrierIdentificationCode(1),
        other(16)
        }
-- TEXTUAL-CONVENTION
--  Status
--    mandatory
--  Descr
--    Indicates the network identification plan of a
--     specified transit network.
--  Refer
--    ATM Forum UNI Signalling 4.0 Section 2 4.5.22/Q.2931

PnniVersion ::= INTEGER {
        unsupported(1),
        version1point0(2)
        }
-- TEXTUAL-CONVENTION
--  Status
--    mandatory
--  Descr
--    Indicates a version of the PNNI protocol.
--  Refer
--    ATM Forum PNNI 1.0 Section 5.6.1

PnniHelloState ::= INTEGER {
        notApplicable(1),
        down(2),
        attempt(3),
        oneWayInside(4),
        twoWayInside(5),
        oneWayOutside(6),
        twoWayOutside(7),
        commonOutside(8)
        }
-- TEXTUAL-CONVENTION
--  Status
--    mandatory
--  Descr
--    The state of an instance of the PNNI Hello State machine.
--  Refer
--    ATM Forum PNNI 1.0 Section 5.6.2.1.2

pnniHighestVersion OBJECT-TYPE
    SYNTAX PnniVersion
--    Rsyntax INTEGER {
--        unsupported(1),
--        version1point0(2)
--        }
    ACCESS read-only
    STATUS mandatory
    DESCRIPTION
        "The highest version of the PNNI protocol that the
         software in this switching system is capable of executing."
    REFERENCE
        "ATM Forum PNNI 1.0 Section 5.6.1"
    ::= { pnniBaseGroup 1 }

pnniLowestVersion OBJECT-TYPE
    SYNTAX PnniVersion
--    Rsyntax INTEGER {
--        unsupported(1),
--        version1point0(2)
--        }
    ACCESS read-only
    STATUS mandatory
    DESCRIPTION
        "The lowest version of the PNNI Protocol that the
         software in this switching system is capable of executing."
    REFERENCE
        "ATM Forum PNNI 1.0 Section 5.6.1"
    ::= { pnniBaseGroup 2 }

pnniDtlCountOriginator OBJECT-TYPE
    SYNTAX Counter32
    ACCESS read-only
    STATUS mandatory
    DESCRIPTION
        "The total number of DTL stacks that this switching system
         has originated as the DTLOriginator and placed into
         signalling messages. This includes the initial DTL stacks
         computed by this system as well as any alternate route
         (second, third choice etc.) DTL stacks computed by this
         switching system in response to crankbacks."
    ::= { pnniBaseGroup 3 }

pnniDtlCountBorder OBJECT-TYPE
    SYNTAX Counter32
    ACCESS read-only
    STATUS mandatory
    DESCRIPTION
        "The number of partial DTL stacks that this switching system
         has added into signalling messages as an entry border node.
         This includes the initial partial DTL stacks computed by
         this system as well as any alternate route (second, third
         choice etc.) partial DTL stacks computed by this switching
         system in response to crankbacks."
    ::= { pnniBaseGroup 4 }

pnniCrankbackCountOriginator OBJECT-TYPE
    SYNTAX Counter32
    ACCESS read-only
    STATUS mandatory
    DESCRIPTION
        "The count of the total number of connection setup messages
         including DTL stacks originated by this switching system
         that have cranked back to this switching system at all
         levels of the hierarchy."
    ::= { pnniBaseGroup 5 }

pnniCrankbackCountBorder OBJECT-TYPE
    SYNTAX Counter32
    ACCESS read-only
    STATUS mandatory
    DESCRIPTION
        "The count of the total number of connection setup messages
         including DTLs added by this switching system as an entry
         border node that have cranked back to this switching system
         at all levels of the hierarchy. This count does not include
         Crankbacks for which this switching system was not the
         crankback destination, only those crankbacks that were
         directed to this switching system are counted here."
    ::= { pnniBaseGroup 6 }

pnniAltRouteCountOriginator OBJECT-TYPE
    SYNTAX Counter32
    ACCESS read-only
    STATUS mandatory
    DESCRIPTION
        "The total number of alternate DTL stacks that this
         switching system has computed and placed into
         signalling messages as the DTLOriginator."
    ::= { pnniBaseGroup 7 }

pnniAltRouteCountBorder OBJECT-TYPE
    SYNTAX Counter32
    ACCESS read-only
    STATUS mandatory
    DESCRIPTION
        "The total number of alternate partial DTL stacks that this
         switching system has computed and placed into signalling
         messages as an entry border node."
    ::= { pnniBaseGroup 8 }

pnniRouteFailCountOriginator OBJECT-TYPE
    SYNTAX Counter32
    ACCESS read-only
    STATUS mandatory
    DESCRIPTION
        "The total number of times where the switching system failed
         to compute a viable DTL stack as the DTLOriginator for some
         call.  It indicates the number of times a call was cleared
         from this switching system due to originator routing
         failure."
    ::= { pnniBaseGroup 9 }

pnniRouteFailCountBorder OBJECT-TYPE
    SYNTAX Counter32
    ACCESS read-only
    STATUS mandatory
    DESCRIPTION
        "The total number of times where the switching system failed
         to compute a viable partial DTL stack as an entry border
         node for some call.  It indicates the number of times a
         call was either cleared or cranked back from this switching
         system due to border routing failure."
    ::= { pnniBaseGroup 10 }

pnniRouteFailUnreachableOriginator OBJECT-TYPE
    SYNTAX Counter32
    ACCESS read-only
    STATUS mandatory
    DESCRIPTION
        "The total number of times where the switching system failed
         to compute a viable DTL stack as the DTLOriginator because
         the destination was unreachable, i.e., those calls that are
         cleared with cause #2 `specified transit network
         unreachable' or cause #3 `destination unreachable' in the
         cause IE."
    ::= { pnniBaseGroup 11 }

pnniRouteFailUnreachableBorder OBJECT-TYPE
    SYNTAX Counter32
    ACCESS read-only
    STATUS mandatory
    DESCRIPTION
        "The total number of times where the switching system failed
         to compute a viable partial DTL stack as an entry border
         node because the target of the path calculation was
         unreachable, i.e., those calls that are cleared or cranked
         back with cause #2 `specified transit network unreachable'
         or cause #3 `destination unreachable' in the cause IE."
    ::= { pnniBaseGroup 12 }

pnniNodeTable OBJECT-TYPE
    SYNTAX SEQUENCE OF PnniNodeEntry
    ACCESS not-accessible
    STATUS mandatory
    DESCRIPTION
        "The pnniNodeTable collects attributes that affect the
         operation of a PNNI logical node.
        
         There is a single row in this table for each PNNI peer
         group that the managed system is expected or eligible
         to become a member of."
    REFERENCE
        "ATM Forum PNNI 1.0 Annex F"
    ::= { pnniMIBObjects 2 }

pnniNodeEntry OBJECT-TYPE
    SYNTAX PnniNodeEntry
    ACCESS not-accessible
    STATUS mandatory
    DESCRIPTION
        "An entry in the table, containing information about a PNNI
         logical node in this switching system."
    REFERENCE
        "ATM Forum PNNI 1.0 Annex F"
    INDEX { pnniNodeIndex }
    ::= { pnniNodeTable 1 }

PnniNodeEntry ::= SEQUENCE {
    pnniNodeIndex PnniNodeIndex,
    pnniNodeLevel PnniLevel,
    pnniNodeId PnniNodeId,
    pnniNodeLowest TruthValue,
    pnniNodeAdminStatus INTEGER,
    pnniNodeOperStatus INTEGER,
    pnniNodeDomainName DisplayString,
    pnniNodeAtmAddress PnniAtmAddr,
    pnniNodePeerGroupId PnniPeerGroupId,
    pnniNodeRestrictedTransit TruthValue,
    pnniNodeComplexRep TruthValue,
    pnniNodeRestrictedBranching TruthValue,
    pnniNodeDatabaseOverload TruthValue,
    pnniNodePtses Gauge32,
    pnniNodeRowStatus RowStatus
    }

pnniNodeIndex OBJECT-TYPE
    SYNTAX PnniNodeIndex
--    Rsyntax Integer32(0..65535)
    ACCESS read-only 
    STATUS mandatory
    DESCRIPTION
        "A value assigned to a node in this switching system that
         uniquely identifies it in the MIB."
    ::= { pnniNodeEntry 1 }

pnniNodeLevel OBJECT-TYPE
    SYNTAX PnniLevel
--    Rsyntax Integer32(0..104)
    ACCESS read-write
    STATUS mandatory
    DESCRIPTION
        "The level of PNNI hierarchy at which this node exists. This
         attribute is used to determine the default node ID and the
         default peer group ID for this node. This object may only
         be written when pnniNodeAdminStatus has the value down."
    REFERENCE
        "ATM Forum PNNI 1.0 Section 5.3.1, Annex F"
    DEFVAL { 96 }
    ::= { pnniNodeEntry 2 }

pnniNodeId OBJECT-TYPE
    SYNTAX PnniNodeId
--    Rsyntax OCTET STRING(SIZE(22))
    ACCESS read-write
    STATUS mandatory
    DESCRIPTION
        "The value the switching system is using to represent
         itself as this node. This object may only be written when
         pnniNodeAdminStatus has the value down.
        
         If pnniNodeLowest is true, then the default node ID takes
         the form defined in Section 5.3.3 for lowest level nodes,
         with the first octet equal to pnniNodeLevel, the second
         octet equal to 160, and the last 20 octets equal to
         pnniNodeAtmAddress.
        
         If pnniNodeLowest is false, then the default
         node ID takes the form defined in Section 5.3.3 for logical
         group nodes, with the first octet equal to pnniNodeLevel,
         the next fourteen octets equal to the value of
         pnniNodePeerGroupId for the child node whose election as
         PGL causes this LGN to be instantiated, the next six octets
         equal to the ESI of pnniNodeAtmAddress, and the last octet
         equal to zero."
    REFERENCE
        "ATM Forum PNNI 1.0 Section 5.3.3, Annex F"
    ::= { pnniNodeEntry 3 }

pnniNodeLowest OBJECT-TYPE
    SYNTAX TruthValue
--    Rsyntax INTEGER {
--        true(1),
--        false(2)
--        }
    ACCESS read-write
    STATUS mandatory
    DESCRIPTION
        "Indicates whether this node acts as a lowest level node or
         whether this node is a logical group node that becomes
         active when one of the other nodes in this switching system
         becomes a peer group leader.  The value 'false' must not be
         used with nodes that are not PGL/LGN capable.
        
         This object may only be
         written when pnniNodeAdminStatus has the value down."
    DEFVAL { true }
    ::= { pnniNodeEntry 4 }

pnniNodeAdminStatus OBJECT-TYPE
    SYNTAX INTEGER {
        up(1),
        down(2)
        }
    ACCESS read-write
    STATUS mandatory
    DESCRIPTION
        "Indicates whether the administrative status of the node is
         up (the node is allowed to become active) or down (the node
         is forced to be inactive).
        
         When pnniNodeAdminStatus is down, then pnniNodeOperStatus
         must also be down."
    DEFVAL { up }
    ::= { pnniNodeEntry 5 }

pnniNodeOperStatus OBJECT-TYPE
    SYNTAX INTEGER {
        up(1),
        down(2)
        }
    ACCESS read-only
    STATUS mandatory
    DESCRIPTION
        "Indicates whether the node is active or whether the node
         has yet to become operational.  When the value is down, all
         state has been cleared from the node and the node is not
         communicating with any of its neighbor nodes."
    ::= { pnniNodeEntry 6 }

pnniNodeDomainName OBJECT-TYPE
    SYNTAX DisplayString
--    Rsyntax OCTET STRING(SIZE(0..255))
    ACCESS read-write
    STATUS mandatory
    DESCRIPTION
        "The name of the PNNI routing
         domain in which this node participates.  All lowest-level
         PNNI nodes with the same pnniNodeDomainName are presumed to
         be connected."
    DEFVAL { "" }
    ::= { pnniNodeEntry 7 }

pnniNodeAtmAddress OBJECT-TYPE
    SYNTAX PnniAtmAddr
--    Rsyntax OCTET STRING(SIZE(0 | 20))
    ACCESS read-write
    STATUS mandatory
    DESCRIPTION
        "This node's ATM End System Address.  Remote systems wishing
         to exchange PNNI protocol packets with this node should
         direct packets or calls to this address.
        
         This attribute may only be written when pnniNodeAdminStatus
         has the value down."
    REFERENCE
        "ATM Forum PNNI 1.0 Section 5.2.2"
    ::= { pnniNodeEntry 8 }

pnniNodePeerGroupId OBJECT-TYPE
    SYNTAX PnniPeerGroupId
--    Rsyntax OCTET STRING(SIZE(14))
    ACCESS read-write
    STATUS mandatory
    DESCRIPTION
        "The Peer Group Identifier of the peer group that the given
         node is to become a member of.
        
         The default value of this attribute has the first octet
         equal to pnniNodeLevel, the next pnniNodeLevel bits equal
         to the pnniNodeLevel bits starting from the third octet of
         pnniNodeId, and the remainder padded with zeros.
        
         This object may only be written when pnniNodeAdminStatus
         has the value down."
    REFERENCE
        "ATM Forum PNNI 1.0 Section 5.3.2, Annex F"
    ::= { pnniNodeEntry 9 }

pnniNodeRestrictedTransit OBJECT-TYPE
    SYNTAX TruthValue
--    Rsyntax INTEGER {
--        true(1),
--        false(2)
--        }
    ACCESS read-write
    STATUS mandatory
    DESCRIPTION
        "Specifies whether the node is restricted to not allowing
         support of SVCs transiting this node.  This attribute
         determines the setting of the restricted transit bit in the
         nodal information group originated by this node."
    REFERENCE
        "ATM Forum PNNI 1.0 Section 5.8.1.2.3"
    DEFVAL { false }
    ::= { pnniNodeEntry 10 }

pnniNodeComplexRep OBJECT-TYPE
    SYNTAX TruthValue
--    Rsyntax INTEGER {
--        true(1),
--        false(2)
--        }
    ACCESS read-write
    STATUS mandatory
    DESCRIPTION
        "Specifies whether this node uses the complex node
         representation.  A value of `true' indicates that the
         complex node representation is used, whereas a value of
         `false' indicates that the simple node representation is
         used.  This attribute determines the setting of the nodal
         representation bit in the nodal information group
         originated by this node."
    REFERENCE
        "ATM Forum PNNI 1.0 Section 5.8.1.2.3"
    ::= { pnniNodeEntry 11 }

pnniNodeRestrictedBranching OBJECT-TYPE
    SYNTAX TruthValue
--    Rsyntax INTEGER {
--        true(1),
--        false(2)
--        }
    ACCESS read-only
    STATUS mandatory
    DESCRIPTION
        "Indicates whether the node is able to support additional
         point-to-multipoint branches.  A value of 'false' indicates
         that additional branches can be supported, and a value of
         'true' indicates that additional branches cannot be
         supported.  This attribute reflects the setting of the
         restricted branching bit in the nodal information group
         originated by this node."
    REFERENCE
        "ATM Forum PNNI 1.0 Section 5.8.1.2.3"
    ::= { pnniNodeEntry 12 }

pnniNodeDatabaseOverload OBJECT-TYPE
    SYNTAX TruthValue
--    Rsyntax INTEGER {
--        true(1),
--        false(2)
--        }
    ACCESS read-only
    STATUS mandatory
    DESCRIPTION
        "Specifies whether the node is currently operating in
         topology database overload state.  This attribute has the
         same value as the Non-transit for PGL Election bit in the
         nodal information group originated by this node."
    REFERENCE
        "ATM Forum PNNI 1.0 Section 5.8.1.2.3"
    ::= { pnniNodeEntry 13 }

pnniNodePtses OBJECT-TYPE
    SYNTAX Gauge32
    ACCESS read-only
    STATUS mandatory
    DESCRIPTION
        "Gauges the total number of PTSEs currently in this
         node's topology database(s)."
    ::= { pnniNodeEntry 14 }

pnniNodeRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "To create, delete, activate and de-activate a Node."
    ::= { pnniNodeEntry 15 }

pnniNodePglTable OBJECT-TYPE
    SYNTAX SEQUENCE OF PnniNodePglEntry
    ACCESS not-accessible
    STATUS mandatory
    DESCRIPTION
        "Peer group leader election information for a PNNI node in
         this switching system."
    REFERENCE
        "ATM Forum PNNI 1.0 Section 5.10.1"
    ::= { pnniMIBObjects 3 }

pnniNodePglEntry OBJECT-TYPE
    SYNTAX PnniNodePglEntry
    ACCESS not-accessible
    STATUS mandatory
    DESCRIPTION
        "An entry in the table, containing PGL election information
         of a PNNI logical node in this switching system."
    REFERENCE
        "ATM Forum PNNI 1.0 Section 5.10.1"
    INDEX { pnniNodeIndex }
-- Augments pnniNodeEntry
    ::= { pnniNodePglTable 1 }

PnniNodePglEntry ::= SEQUENCE {
    pnniNodePglLeadershipPriority INTEGER,
    pnniNodeCfgParentNodeIndex PnniNodeIndex,
    pnniNodePglInitTime Integer32,
    pnniNodePglOverrideDelay Integer32,
    pnniNodePglReelectTime Integer32,
    pnniNodePglState INTEGER,
    pnniNodePreferredPgl PnniNodeId,
    pnniNodePeerGroupLeader PnniNodeId,
    pnniNodePglTimeStamp TimeStamp,
    pnniNodeActiveParentNodeId PnniNodeId
    }

pnniNodePglLeadershipPriority OBJECT-TYPE
    SYNTAX INTEGER(0..205)
    ACCESS read-write
    STATUS mandatory
    DESCRIPTION
        "The Leadership priority value this node should advertise in
         its nodal information group for the given peer group.  Only
         the value zero can be used with nodes that are not PGL/LGN
         capable.  If there is no configured parent node index or no
         corresponding entry in the pnniNodeTable, then the
         advertised leadership priority is zero regardless of this
         value."
    REFERENCE
        "ATM Forum PNNI 1.0 Section 5.10.1.2"
    DEFVAL { 0 }
    ::= { pnniNodePglEntry 1 }

pnniNodeCfgParentNodeIndex OBJECT-TYPE
    SYNTAX PnniNodeIndex
--    Rsyntax Integer32(0..65535)
    ACCESS read-write
    STATUS mandatory
    DESCRIPTION
        "The local node index used to identify the node that will
         represent this peer group at the next higher level of
         hierarchy, if this node becomes peer group leader.  The
         value 0 indicates that there is no parent node."
    REFERENCE
        "ATM Forum PNNI 1.0 Annex F"
    DEFVAL { 0 }
    ::= { pnniNodePglEntry 2 }

pnniNodePglInitTime OBJECT-TYPE
    SYNTAX Integer32
--  Units
--    seconds
    ACCESS read-write
    STATUS mandatory
    DESCRIPTION
        "The amount of time in seconds this node will delay
         advertising its choice of preferred PGL after having
         initialized operation and reached the full state with at
         least one neighbor in the peer group."
    REFERENCE
        "ATM Forum PNNI 1.0 Annex G PGLInitTime"
    DEFVAL { 15 }
    ::= { pnniNodePglEntry 3 }

pnniNodePglOverrideDelay OBJECT-TYPE
    SYNTAX Integer32
--  Units
--    seconds
    ACCESS read-write
    STATUS mandatory
    DESCRIPTION
        "The amount of time in seconds a node will wait for itself
         to be declared the preferred PGL by unanimous agreement
         among its peers.  In the absence of unanimous agreement
         this will be the amount of time that will pass before this
         node considers a two thirds majority as sufficient
         agreement to declare itself peer group leader, abandoning
         the attempt to get unanimous agreement."
    REFERENCE
        "ATM Forum PNNI 1.0 Annex G OverrideDelay"
    DEFVAL { 30 }
    ::= { pnniNodePglEntry 4 }

pnniNodePglReelectTime OBJECT-TYPE
    SYNTAX Integer32
--  Units
--    seconds
    ACCESS read-write
    STATUS mandatory
    DESCRIPTION
        "The amount of time in seconds after losing connectivity to
         the current peer group leader, that this node will wait
         before re-starting the process of electing a new peer group
         leader."
    REFERENCE
        "ATM Forum PNNI 1.0 Annex G ReElectionInterval"
    DEFVAL { 15 }
    ::= { pnniNodePglEntry 5 }

pnniNodePglState OBJECT-TYPE
    SYNTAX INTEGER {
        starting(1),
        awaiting(2),
        awaitingFull(3),
        initialDelay(4),
        calculating(5),
        awaitUnanimity(6),
        operPgl(7),
        operNotPgl(8),
        hungElection(9),
        awaitReElection(10)
        }
    ACCESS read-only
    STATUS mandatory
    DESCRIPTION
        "Indicates the state that this node is in with respect to
         the Peer Group Leader election that takes place in the
         node's peer group. The values are enumerated in the Peer
         Group Leader State Machine."
    REFERENCE
        "ATM Forum PNNI 1.0 Section 5.10.1.1.2"
    ::= { pnniNodePglEntry 6 }

pnniNodePreferredPgl OBJECT-TYPE
    SYNTAX PnniNodeId
--    Rsyntax OCTET STRING(SIZE(22))
    ACCESS read-only
    STATUS mandatory
    DESCRIPTION
        "The Node ID of
         the node which the local node believes should be or become
         the peer group leader.  This is also the value the local
         node is currently advertising in the `Preferred Peer Group
         Leader Node ID' field of its nodal information group within
         the given peer group.  If a Preferred PGL has not been
         chosen, this attribute's value is set to (all) zero(s)."
    REFERENCE
        "ATM Forum PNNI 1.0 Section 5.10.1.1.6"
    ::= { pnniNodePglEntry 7 }

pnniNodePeerGroupLeader OBJECT-TYPE
    SYNTAX PnniNodeId
--    Rsyntax OCTET STRING(SIZE(22))
    ACCESS read-only
    STATUS mandatory
    DESCRIPTION
        "The Node Identifier of the node which is currently
         operating as peer group leader of the peer group this node
         belongs to. If a PGL has not been elected, this attribute's
         value is set to (all) zero(s)."
    ::= { pnniNodePglEntry 8 }

pnniNodePglTimeStamp OBJECT-TYPE
    SYNTAX TimeStamp
--    Rsyntax TimeTicks
    ACCESS read-only
    STATUS mandatory
    DESCRIPTION
        "The time at which the current Peer Group Leader established
         itself."
    ::= { pnniNodePglEntry 9 }

pnniNodeActiveParentNodeId OBJECT-TYPE
    SYNTAX PnniNodeId
--    Rsyntax OCTET STRING(SIZE(22))
    ACCESS read-only
    STATUS mandatory
    DESCRIPTION
        "The Node Identifier value being used by the Peer Group
         Leader to represent this peer group at the next higher
         level of the hierarchy. If this node is at the highest
         level of the hierarchy or if no PGL has yet been elected
         the PNNI Protocol Entity sets the value of this attribute
         to (all) zero(s)."
    ::= { pnniNodePglEntry 10 }

pnniNodeTimerTable OBJECT-TYPE
    SYNTAX SEQUENCE OF PnniNodeTimerEntry
    ACCESS not-accessible
    STATUS mandatory
    DESCRIPTION
        "A table of initial PNNI timer values and significant
         change thresholds."
    ::= { pnniMIBObjects 4 }

pnniNodeTimerEntry OBJECT-TYPE
    SYNTAX PnniNodeTimerEntry
    ACCESS not-accessible
    STATUS mandatory
    DESCRIPTION
        "An entry in the table, containing initial PNNI timer values
         and significant change thresholds of a PNNI logical node in
         this switching system."
    INDEX { pnniNodeIndex }
-- Augments pnniNodeEntry
    ::= { pnniNodeTimerTable 1 }

PnniNodeTimerEntry ::= SEQUENCE {
    pnniNodePtseHolddown Integer32,
    pnniNodeHelloHolddown Integer32,
    pnniNodeHelloInterval Integer32,
    pnniNodeHelloInactivityFactor Integer32,
    pnniNodeHlinkInact Integer32,
    pnniNodePtseRefreshInterval Integer32,
    pnniNodePtseLifetimeFactor INTEGER,
    pnniNodeRxmtInterval Integer32,
    pnniNodePeerDelayedAckInterval Integer32,
    pnniNodeAvcrPm INTEGER,
    pnniNodeAvcrMt INTEGER,
    pnniNodeCdvPm INTEGER,
    pnniNodeCtdPm INTEGER
    }

pnniNodePtseHolddown OBJECT-TYPE
    SYNTAX Integer32
--  Units
--    100 milliseconds
    ACCESS read-write
    STATUS mandatory
    DESCRIPTION
        "The initial value for the PTSE hold down timer that will be
         used by the given node to limit the rate at which it can
         re-originate PTSEs. It must be a positive non-zero number."
    REFERENCE
        "ATM Forum PNNI 1.0 Annex G MinPTSEInterval"
    DEFVAL { 10 }
    ::= { pnniNodeTimerEntry 1 }

pnniNodeHelloHolddown OBJECT-TYPE
    SYNTAX Integer32
--  Units
--    100 milliseconds
    ACCESS read-write
    STATUS mandatory
    DESCRIPTION
        "The initial value for the Hello hold down timer that will
         be used by the given node to limit the rate at which it
         sends Hellos. It must be a positive non-zero number."
    REFERENCE
        "ATM Forum PNNI 1.0 Annex G MinHelloInterval"
    DEFVAL { 10 }
    ::= { pnniNodeTimerEntry 2 }

pnniNodeHelloInterval OBJECT-TYPE
    SYNTAX Integer32
--  Units
--    seconds
    ACCESS read-write
    STATUS mandatory
    DESCRIPTION
        "The initial value for the Hello Timer.
         In the absence of triggered Hellos, this node will send one
         Hello packet on each of its ports on this interval."
    REFERENCE
        "ATM Forum PNNI 1.0 Annex G HelloInterval"
    DEFVAL { 15 }
    ::= { pnniNodeTimerEntry 3 }

pnniNodeHelloInactivityFactor OBJECT-TYPE
    SYNTAX Integer32
    ACCESS read-write
    STATUS mandatory
    DESCRIPTION
        "The value for the Hello Inactivity factor that this
         node will use to determine when a neighbor has gone down."
    REFERENCE
        "ATM Forum PNNI 1.0 Annex G InactivityFactor"
    DEFVAL { 5 }
    ::= { pnniNodeTimerEntry 4 }

pnniNodeHlinkInact OBJECT-TYPE
    SYNTAX Integer32
--  Units
--    seconds
    ACCESS read-write
    STATUS mandatory
    DESCRIPTION
        "The amount of time a node will continue to
         advertise a horizontal (logical) link for which it has
         not received and processed a LGN Horizontal Link
         information group."
    REFERENCE
        "ATM Forum PNNI 1.0 Annex G HorizontalLinkInactivityTime"
    DEFVAL { 120 }
    ::= { pnniNodeTimerEntry 5 }

pnniNodePtseRefreshInterval OBJECT-TYPE
    SYNTAX Integer32
--  Units
--    seconds
    ACCESS read-write
    STATUS mandatory
    DESCRIPTION
        "The initial value for the Refresh timer that this node will
         use to drive (re-)origination of PTSEs in the absence of
         triggered updates."
    REFERENCE
        "ATM Forum PNNI 1.0 Annex G PTSERefreshInterval"
    DEFVAL { 1800 }
    ::= { pnniNodeTimerEntry 6 }

pnniNodePtseLifetimeFactor OBJECT-TYPE
    SYNTAX INTEGER(101..1000)
--  Units
--    percent
    ACCESS read-write
    STATUS mandatory
    DESCRIPTION
        "The value for the lifetime multiplier, expressed as a
         percentage.  The result of multiplying the
         pnniNodePtseRefreshInterval attribute value by this
         attribute value is used as the initial lifetime that this
         node places into self-originated PTSEs."
    REFERENCE
        "ATM Forum PNNI 1.0 Annex G PTSELifetimeFactor"
    DEFVAL { 200 }
    ::= { pnniNodeTimerEntry 7 }

pnniNodeRxmtInterval OBJECT-TYPE
    SYNTAX Integer32
--  Units
--    seconds
    ACCESS read-write
    STATUS mandatory
    DESCRIPTION
        "The period between retransmissions of unacknowledged
         Database Summary packets, PTSE Request packets, and PTSPs."
    REFERENCE
        "ATM Forum PNNI 1.0 Annex G DSRxmtInterval,
         RequestRxmtInterval, PTSERetransmissionInterval"
    DEFVAL { 5 }
    ::= { pnniNodeTimerEntry 8 }

pnniNodePeerDelayedAckInterval OBJECT-TYPE
    SYNTAX Integer32
--  Units
--    100 milliseconds
    ACCESS read-write
    STATUS mandatory
    DESCRIPTION
        "The minimum amount of time between transmissions of
         delayed PTSE acknowledgement packets."
    REFERENCE
        "ATM Forum PNNI 1.0 Annex G PeerDelayedAckInterval,
         Appendix G"
    DEFVAL { 10 }
    ::= { pnniNodeTimerEntry 9 }

pnniNodeAvcrPm OBJECT-TYPE
    SYNTAX INTEGER(1..99)
--  Units
--    percent
    ACCESS read-write
    STATUS mandatory
    DESCRIPTION
        "The proportional multiplier used in the algorithms that
         determine significant change for AvCR parameters, expressed
         as a percentage."
    REFERENCE
        "ATM Forum PNNI 1.0 Section 5.8.5.2.5.4, Annex G AvCR_PM"
    DEFVAL { 50 }
    ::= { pnniNodeTimerEntry 10 }

pnniNodeAvcrMt OBJECT-TYPE
    SYNTAX INTEGER(1..99)
--  Units
--    percent
    ACCESS read-write
    STATUS mandatory
    DESCRIPTION
        "The minimum threshold used in the algorithms that determine
         significant change for AvCR parameters, expressed as a
         percentage."
    REFERENCE
        "ATM Forum PNNI 1.0 Section 5.8.5.2.5.4, Annex G AvCR_mT"
    DEFVAL { 3 }
    ::= { pnniNodeTimerEntry 11 }

pnniNodeCdvPm OBJECT-TYPE
    SYNTAX INTEGER(1..99)
--  Units
--    percent
    ACCESS read-write
    STATUS mandatory
    DESCRIPTION
        "The proportional multiplier used in the algorithms that
         determine significant change for CDV metrics, expressed as
         a percentage."
    REFERENCE
        "ATM Forum PNNI 1.0 Section 5.8.5.2.5.6, Annex G CDV_PM"
    DEFVAL { 25 }
    ::= { pnniNodeTimerEntry 12 }

pnniNodeCtdPm OBJECT-TYPE
    SYNTAX INTEGER(1..99)
--  Units
--    percent
    ACCESS read-write
    STATUS mandatory
    DESCRIPTION
        "The proportional multiplier used in the algorithms that
         determine significant change for CTD metrics, expressed as
         a percentage."
    REFERENCE
        "ATM Forum PNNI 1.0 Section 5.8.5.2.5.5, Annex G maxCTD_PM"
    DEFVAL { 50 }
    ::= { pnniNodeTimerEntry 13 }

pnniNodeSvccTable OBJECT-TYPE
    SYNTAX SEQUENCE OF PnniNodeSvccEntry
    ACCESS not-accessible
    STATUS mandatory
    DESCRIPTION
        "A table of variables related to SVCC-based routing control
         channels."
    REFERENCE
        "ATM Forum PNNI 1.0 Section 5.5"
    ::= { pnniMIBObjects 5 }

pnniNodeSvccEntry OBJECT-TYPE
    SYNTAX PnniNodeSvccEntry
    ACCESS not-accessible
    STATUS mandatory
    DESCRIPTION
        "An entry in the table, containing SVCC-based RCC variables
         of a PNNI logical node in this switching system."
    REFERENCE
        "ATM Forum PNNI 1.0 Section 5.5"
    INDEX { pnniNodeIndex }
-- Augments pnniNodeEntry
    ::= { pnniNodeSvccTable 1 }

PnniNodeSvccEntry ::= SEQUENCE {
    pnniNodeSvccInitTime Integer32,
    pnniNodeSvccRetryTime Integer32,
    pnniNodeSvccCallingIntegrityTime Integer32,
    pnniNodeSvccCalledIntegrityTime Integer32,
    pnniNodeSvccTrafficDescriptorIndex AtmTrafficDescrParamIndex
    }

pnniNodeSvccInitTime OBJECT-TYPE
    SYNTAX Integer32
--  Units
--    seconds
    ACCESS read-write
    STATUS mandatory
    DESCRIPTION
        "The amount of time this node will delay initiating
         establishment of an SVCC to a neighbor with a numerically
         lower ATM address, after determining that such an SVCC
         should be established."
    REFERENCE
        "ATM Forum PNNI 1.0 Annex G InitialLGNSVCTimeout"
    DEFVAL { 4 }
    ::= { pnniNodeSvccEntry 1 }

pnniNodeSvccRetryTime OBJECT-TYPE
    SYNTAX Integer32
--  Units
--    seconds
    ACCESS read-write
    STATUS mandatory
    DESCRIPTION
        "The amount of time this node will delay after an apparently
         still necessary and viable SVCC-based RCC is unexpectedly
         torn down, before attempting to re-establish it."
    REFERENCE
        "ATM Forum PNNI 1.0 Annex G RetryLGNSVCTimeout"
    DEFVAL { 30 }
    ::= { pnniNodeSvccEntry 2 }

pnniNodeSvccCallingIntegrityTime OBJECT-TYPE
    SYNTAX Integer32
--  Units
--    seconds
    ACCESS read-write
    STATUS mandatory
    DESCRIPTION
        "The amount of time this node will wait for an SVCC, which
         it has initiated establishment of as the calling party, to
         become fully established before giving up and tearing it
         down."
    REFERENCE
        "ATM Forum PNNI 1.0 Annex G SVCCallingIntegrityTime"
    DEFVAL { 35 }
    ::= { pnniNodeSvccEntry 3 }

pnniNodeSvccCalledIntegrityTime OBJECT-TYPE
    SYNTAX Integer32
--  Units
--    seconds
    ACCESS read-write
    STATUS mandatory
    DESCRIPTION
        "The amount of time this node will wait for an SVCC, which
         it has decided to accept as the called party, to become
         fully established before giving up and tearing it down."
    REFERENCE
        "ATM Forum PNNI 1.0 Annex G SVCCalledIntegrityTime"
    DEFVAL { 50 }
    ::= { pnniNodeSvccEntry 4 }

pnniNodeSvccTrafficDescriptorIndex OBJECT-TYPE
    SYNTAX AtmTrafficDescrParamIndex
--    Rsyntax INTEGER(0..2147483647)
    ACCESS read-write
    STATUS mandatory
    DESCRIPTION
        "An index into the atmTrafficDescrParamTable defined in
         RFC 1695.  This traffic descriptor is used when
         establishing switched virtual channels for use as
         SVCC-based RCCs to/from PNNI logical group nodes."
    REFERENCE
        "ATM Forum PNNI 1.0 Section 5.5.2, Annex G
         RCCMaximumBurstSize, RCCPeakCellRate,
         RCCSustainableCellRate"
    ::= { pnniNodeSvccEntry 5 }

pnniScopeMappingTable OBJECT-TYPE
    SYNTAX SEQUENCE OF PnniScopeMappingEntry
    ACCESS not-accessible
    STATUS mandatory
    DESCRIPTION
        "The pnniScopeTable contains the mappings of membership and
         connection scope from organizational scope values (used at
         UNI interfaces) to PNNI scope (i.e. in terms of PNNI
         routing level indicators)."
    REFERENCE
        "ATM Forum PNNI 1.0 Section 5.3.6"
    ::= { pnniMIBObjects 6 }

pnniScopeMappingEntry OBJECT-TYPE
    SYNTAX PnniScopeMappingEntry
    ACCESS not-accessible
    STATUS mandatory
    DESCRIPTION
        "An entry in the table, containing scope mapping information
         for a PNNI logical node in this switching system."
    REFERENCE
        "ATM Forum PNNI 1.0 Section 5.3.6"
    INDEX { pnniNodeIndex }
-- Augments pnniNodeEntry
    ::= { pnniScopeMappingTable 1 }

PnniScopeMappingEntry ::= SEQUENCE {
    pnniScopeLocalNetwork PnniLevel,
    pnniScopeLocalNetworkPlusOne PnniLevel,
    pnniScopeLocalNetworkPlusTwo PnniLevel,
    pnniScopeSiteMinusOne PnniLevel,
    pnniScopeIntraSite PnniLevel,
    pnniScopeSitePlusOne PnniLevel,
    pnniScopeOrganizationMinusOne PnniLevel,
    pnniScopeIntraOrganization PnniLevel,
    pnniScopeOrganizationPlusOne PnniLevel,
    pnniScopeCommunityMinusOne PnniLevel,
    pnniScopeIntraCommunity PnniLevel,
    pnniScopeCommunityPlusOne PnniLevel,
    pnniScopeRegional PnniLevel,
    pnniScopeInterRegional PnniLevel,
    pnniScopeGlobal PnniLevel
    }

pnniScopeLocalNetwork OBJECT-TYPE
    SYNTAX PnniLevel
--    Rsyntax Integer32(0..104)
    ACCESS read-write
    STATUS mandatory
    DESCRIPTION
        "The highest level of PNNI hierarchy (i.e. smallest PNNI
         routing level) that lies within the organizational scope
         value localNetwork(1)."
    DEFVAL { 96 }
    ::= { pnniScopeMappingEntry 1 }

pnniScopeLocalNetworkPlusOne OBJECT-TYPE
    SYNTAX PnniLevel
--    Rsyntax Integer32(0..104)
    ACCESS read-write
    STATUS mandatory
    DESCRIPTION
        "The highest level of PNNI hierarchy (i.e. smallest PNNI
         routing level) that lies within the organizational scope
         value localNetworkPlusOne(2)."
    DEFVAL { 96 }
    ::= { pnniScopeMappingEntry 2 }

pnniScopeLocalNetworkPlusTwo OBJECT-TYPE
    SYNTAX PnniLevel
--    Rsyntax Integer32(0..104)
    ACCESS read-write
    STATUS mandatory
    DESCRIPTION
        "The highest level of PNNI hierarchy (i.e. smallest PNNI
         routing level) that lies within the organizational scope
         value localNetworkPlusTwo(3)."
    DEFVAL { 96 }
    ::= { pnniScopeMappingEntry 3 }

pnniScopeSiteMinusOne OBJECT-TYPE
    SYNTAX PnniLevel
--    Rsyntax Integer32(0..104)
    ACCESS read-write
    STATUS mandatory
    DESCRIPTION
        "The highest level of PNNI hierarchy  (i.e. smallest PNNI
         routing level) that lies within the organizational scope
         value siteMinusOne(4)."
    DEFVAL { 80 }
    ::= { pnniScopeMappingEntry 4 }

pnniScopeIntraSite OBJECT-TYPE
    SYNTAX PnniLevel
--    Rsyntax Integer32(0..104)
    ACCESS read-write
    STATUS mandatory
    DESCRIPTION
        "The highest level of PNNI hierarchy (i.e. smallest PNNI
         routing level) that lies within the organizational scope
         value intraSite(5)."
    DEFVAL { 80 }
    ::= { pnniScopeMappingEntry 5 }

pnniScopeSitePlusOne OBJECT-TYPE
    SYNTAX PnniLevel
--    Rsyntax Integer32(0..104)
    ACCESS read-write
    STATUS mandatory
    DESCRIPTION
        "The highest level of PNNI hierarchy (i.e. smallest PNNI
         routing level) that lies within the organizational scope
         value sitePlusOne(6)."
    DEFVAL { 72 }
    ::= { pnniScopeMappingEntry 6 }

pnniScopeOrganizationMinusOne OBJECT-TYPE
    SYNTAX PnniLevel
--    Rsyntax Integer32(0..104)
    ACCESS read-write
    STATUS mandatory
    DESCRIPTION
        "The highest level of PNNI hierarchy (i.e. smallest PNNI
         routing level) that lies within the organizational scope
         value organizationMinusOne(7)."
    DEFVAL { 72 }
    ::= { pnniScopeMappingEntry 7 }

pnniScopeIntraOrganization OBJECT-TYPE
    SYNTAX PnniLevel
--    Rsyntax Integer32(0..104)
    ACCESS read-write
    STATUS mandatory
    DESCRIPTION
        "The highest level of PNNI hierarchy (i.e. smallest PNNI
         routing level) that lies within the organizational scope
         value intraOrganization(8)."
    DEFVAL { 64 }
    ::= { pnniScopeMappingEntry 8 }

pnniScopeOrganizationPlusOne OBJECT-TYPE
    SYNTAX PnniLevel
--    Rsyntax Integer32(0..104)
    ACCESS read-write
    STATUS mandatory
    DESCRIPTION
        "The highest level of PNNI hierarchy (i.e. smallest PNNI
         routing level) that lies within the organizational scope
         value organizationPlusOne(9)."
    DEFVAL { 64 }
    ::= { pnniScopeMappingEntry 9 }

pnniScopeCommunityMinusOne OBJECT-TYPE
    SYNTAX PnniLevel
--    Rsyntax Integer32(0..104)
    ACCESS read-write
    STATUS mandatory
    DESCRIPTION
        "The highest level of PNNI hierarchy (i.e. smallest PNNI
         routing level) that lies within the organizational scope
         value communityMinusOne(10)."
    DEFVAL { 64 }
    ::= { pnniScopeMappingEntry 10 }

pnniScopeIntraCommunity OBJECT-TYPE
    SYNTAX PnniLevel
--    Rsyntax Integer32(0..104)
    ACCESS read-write
    STATUS mandatory
    DESCRIPTION
        "The highest level of PNNI hierarchy (i.e. smallest PNNI
         routing level) that lies within the organizational scope
         value intraCommunity(11)."
    DEFVAL { 48 }
    ::= { pnniScopeMappingEntry 11 }

pnniScopeCommunityPlusOne OBJECT-TYPE
    SYNTAX PnniLevel
--    Rsyntax Integer32(0..104)
    ACCESS read-write
    STATUS mandatory
    DESCRIPTION
        "The highest level of PNNI hierarchy (i.e. smallest PNNI
         routing level) that lies within the organizational scope
         value communityPlusOne(12)."
    DEFVAL { 48 }
    ::= { pnniScopeMappingEntry 12 }

pnniScopeRegional OBJECT-TYPE
    SYNTAX PnniLevel
--    Rsyntax Integer32(0..104)
    ACCESS read-write
    STATUS mandatory
    DESCRIPTION
        "The highest level of PNNI hierarchy (i.e. smallest PNNI
         routing level) that lies within the organizational scope
         value regional(13)."
    DEFVAL { 32 }
    ::= { pnniScopeMappingEntry 13 }

pnniScopeInterRegional OBJECT-TYPE
    SYNTAX PnniLevel
--    Rsyntax Integer32(0..104)
    ACCESS read-write
    STATUS mandatory
    DESCRIPTION
        "The highest level of PNNI hierarchy (i.e. smallest PNNI
         routing level) that lies within the organizational scope
         value interRegional(14)."
    DEFVAL { 32 }
    ::= { pnniScopeMappingEntry 14 }

pnniScopeGlobal OBJECT-TYPE
    SYNTAX PnniLevel
--    Rsyntax Integer32(0..104)
    ACCESS read-write
    STATUS mandatory
    DESCRIPTION
        "The highest level of PNNI hierarchy (i.e. smallest PNNI
         routing level) that lies within the organizational scope
         value global(15)."
    DEFVAL { 0 }
    ::= { pnniScopeMappingEntry 15 }

pnniSummaryTable OBJECT-TYPE
    SYNTAX SEQUENCE OF PnniSummaryEntry
    ACCESS not-accessible
    STATUS deprecated
    DESCRIPTION
        "A list of the summary address prefixes that may be
         advertised by the specified logical PNNI entity."
    REFERENCE
        "ATM Forum PNNI 1.0 Section 5.9.2"
    ::= { pnniMIBObjects 7 }

pnniSummaryEntry OBJECT-TYPE
    SYNTAX PnniSummaryEntry
    ACCESS not-accessible
    STATUS deprecated
    DESCRIPTION
        "An entry in the table, containing summary address prefix
         information in this switching system."
    REFERENCE
        "ATM Forum PNNI 1.0 Section 5.9.2"
    INDEX { pnniNodeIndex, pnniSummaryAddress, pnniSummaryPrefixLength }
    ::= { pnniSummaryTable 1 }

PnniSummaryEntry ::= SEQUENCE {
    pnniSummaryAddress AtmAddrPrefix,
    pnniSummaryPrefixLength PnniPrefixLength,
    pnniSummaryType INTEGER,
    pnniSummarySuppress TruthValue,
    pnniSummaryState INTEGER,
    pnniSummaryRowStatus RowStatus
    }

pnniSummaryAddress OBJECT-TYPE
    SYNTAX AtmAddrPrefix
--    Rsyntax OCTET STRING(SIZE(19))
    ACCESS read-only 
    STATUS deprecated
    DESCRIPTION
        "The ATM End System Address prefix for the summary."
    ::= { pnniSummaryEntry 1 }

pnniSummaryPrefixLength OBJECT-TYPE
    SYNTAX PnniPrefixLength
--    Rsyntax Integer32(0..152)
    ACCESS read-only
    STATUS deprecated
    DESCRIPTION
        "The prefix length for the summary."
    ::= { pnniSummaryEntry 2 }

pnniSummaryType OBJECT-TYPE
    SYNTAX INTEGER {
        internal(1),
        exterior(2)
        }
    ACCESS read-write
    STATUS deprecated
    DESCRIPTION
        "The type (e.g. internal or exterior) of summary being
                    described."
    DEFVAL { internal }
    ::= { pnniSummaryEntry 3 }

pnniSummarySuppress OBJECT-TYPE
    SYNTAX TruthValue
--    Rsyntax INTEGER {
--        true(1),
--        false(2)
--        }
    ACCESS read-write
    STATUS deprecated
    DESCRIPTION
        "Determines what is done with addresses that are being
         summarized by the instance. The default value (e.g. false)
         will indicate that the summary should propagate into the
         peer group. Network Management will be able to set the
         value of this attribute to `suppress' (e.g. true), which
         suppresses the summary and any reachable addresses it
         summarizes from being advertised into the peer group."
    DEFVAL { false }
    ::= { pnniSummaryEntry 4 }

pnniSummaryState OBJECT-TYPE
    SYNTAX INTEGER {
        advertising(1),
        suppressing(2),
        inactive(3)
        }
    ACCESS read-only
    STATUS deprecated
    DESCRIPTION
        "Indicates whether the summary is currently being advertised
         by the node within the local switching system into its peer
         group."
    ::= { pnniSummaryEntry 5 }

pnniSummaryRowStatus OBJECT-TYPE
    SYNTAX RowStatus
--    Rsyntax INTEGER {
--        active(1),
--        notInService(2),
--        notReady(3),
--        createAndGo(4),
--        createAndWait(5),
--        destroy(6)
--        }
    ACCESS read-write
    STATUS deprecated
    DESCRIPTION
        "To create, delete, activate and de-activate a summary."
    ::= { pnniSummaryEntry 6 }

pnniSummaryAddressTable OBJECT-TYPE
    SYNTAX SEQUENCE OF PnniSummaryAddressEntry
    ACCESS not-accessible
    STATUS mandatory
    DESCRIPTION
        "A list of the summary address prefixes that may be 
         advertised by the specified logical PNNI entity."
    REFERENCE
        "ATM Forum PNNI 1.0 Section 5.9.2"
    ::= { pnniMIBObjects 20 }

pnniSummaryAddressEntry OBJECT-TYPE
    SYNTAX PnniSummaryAddressEntry
    ACCESS not-accessible
    STATUS mandatory
    DESCRIPTION
        "An entry in the table, containing summary address prefix
         information in this switching system."
    REFERENCE
        "ATM Forum PNNI 1.0 Section 5.9.2"
    INDEX { pnniNodeIndex, pnniSummaryAddressType, pnniSummaryAddressAddress, pnniSummaryAddressPrefixLength }
    ::= { pnniSummaryAddressTable 1 }

PnniSummaryAddressEntry ::= SEQUENCE {
    pnniSummaryAddressType INTEGER,
    pnniSummaryAddressAddress AtmAddrPrefix,
    pnniSummaryAddressPrefixLength PnniPrefixLength,
    pnniSummaryAddressSuppress TruthValue,
    pnniSummaryAddressState INTEGER,
    pnniSummaryAddressRowStatus RowStatus
    }

pnniSummaryAddressType OBJECT-TYPE
    SYNTAX INTEGER {
        internal(1),
        exterior(2)
        }
    ACCESS read-only 
    STATUS mandatory
    DESCRIPTION
        "The type (e.g. internal or exterior) of summary being
                    described."
    ::= { pnniSummaryAddressEntry 1 }

pnniSummaryAddressAddress OBJECT-TYPE
    SYNTAX AtmAddrPrefix
--    Rsyntax OCTET STRING(SIZE(19))
    ACCESS read-only 
    STATUS mandatory
    DESCRIPTION
        "The ATM End System Address prefix for the summary."
    ::= { pnniSummaryAddressEntry 2 }

pnniSummaryAddressPrefixLength OBJECT-TYPE
    SYNTAX PnniPrefixLength
--    Rsyntax Integer32(0..152)
    ACCESS read-only 
    STATUS mandatory
    DESCRIPTION
        "The prefix length for the summary."
    ::= { pnniSummaryAddressEntry 3 }

pnniSummaryAddressSuppress OBJECT-TYPE
    SYNTAX TruthValue
--    Rsyntax INTEGER {
--        true(1),
--        false(2)
--        }
    ACCESS read-write
    STATUS mandatory
    DESCRIPTION
        "Determines what is done with addresses that are being
         summarized by the instance. The default value (e.g. false)
         will indicate that the summary should propagate into the
         peer group. Network Management will be able to set the
         value of this attribute to `suppress' (e.g. true), which
         suppresses the summary and any reachable addresses it
         summarizes from being advertised into the peer group."
    DEFVAL { false }
    ::= { pnniSummaryAddressEntry 4 }

pnniSummaryAddressState OBJECT-TYPE
    SYNTAX INTEGER {
        advertising(1),
        suppressing(2),
        inactive(3)
        }
    ACCESS read-only
    STATUS mandatory
    DESCRIPTION
        "Indicates whether the summary is currently being advertised
         by the node within the local switching system into its peer
         group."
    ::= { pnniSummaryAddressEntry 5 }

pnniSummaryAddressRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "To create, delete, activate and de-activate a summary."
    ::= { pnniSummaryAddressEntry 6 }

pnniIfTable OBJECT-TYPE
    SYNTAX SEQUENCE OF PnniIfEntry
    ACCESS not-accessible
    STATUS mandatory
    DESCRIPTION
        "The pnniIfTable contains the attributes necessary to
         configure a physical interface on a switching system which
         is capable of being used for PNNI routing.  Interfaces may
         represent physical connection points (i.e. copper/fiber
         connection points) or VPCs which have been configured for
         PNNI's use.  Each interface is attached to a specific
         lowest-level node within the switching system.
        
         An ifIndex is used as the instance ID to uniquely identify
         the interface on the local switching system. This index has
         the same value as the ifIndex object defined in RFC 1573
         for the same interface, since this table correlates with
         the ifTable in RFC 1573.
        
         One row in this table is created by the managed system for
         each row in the ifTable that has an ifType of atm(37) or
         atmLogical(80)."
    ::= { pnniMIBObjects 8 }

pnniIfEntry OBJECT-TYPE
    SYNTAX PnniIfEntry
    ACCESS not-accessible
    STATUS mandatory
    DESCRIPTION
        "An entry in the table, containing PNNI specific interface
         information in this switching system."
    INDEX { ifIndex }
    ::= { pnniIfTable 1 }

PnniIfEntry ::= SEQUENCE {
    pnniIfNodeIndex PnniNodeIndex,
    pnniIfPortId PnniPortId,
    pnniIfAggrToken PnniAggrToken,
    pnniIfVPCapability TruthValue,
    pnniIfAdmWeightCbr INTEGER,
    pnniIfAdmWeightRtVbr INTEGER,
    pnniIfAdmWeightNrtVbr INTEGER,
    pnniIfAdmWeightAbr INTEGER,
    pnniIfAdmWeightUbr INTEGER,
    pnniIfRccServiceCategory ServiceCategory,
    pnniIfRccTrafficDescrIndex AtmTrafficDescrParamIndex
    }

pnniIfNodeIndex OBJECT-TYPE
    SYNTAX PnniNodeIndex
--    Rsyntax Integer32(1..65535)
    ACCESS read-write
    STATUS mandatory
    DESCRIPTION
        "Identifies the node within the switching system that the
         interface is directly attached to.  The value zero is not 
         a valid value."
    DEFVAL { 1 }
    ::= { pnniIfEntry 1 }

pnniIfPortId OBJECT-TYPE
    SYNTAX PnniPortId
--    Rsyntax Gauge32
    ACCESS read-only
    STATUS mandatory
    DESCRIPTION
        "The Port Identifier of the port as selected by the PNNI
         protocol entity for the given interface.  This value has
         meaning only within the context of the node to which the
         port is attached.  The distinguished value zero indicates
         that no PNNI Port Identifier has been assigned for this
         interface (for example, this value may be used when the
         interface is not running PNNI)."
    REFERENCE
        "ATM Forum PNNI 1.0 Section 5.3.4"
    ::= { pnniIfEntry 2 }

pnniIfAggrToken OBJECT-TYPE
    SYNTAX PnniAggrToken
--    Rsyntax Gauge32
    ACCESS read-write
    STATUS mandatory
    DESCRIPTION
        "The configured aggregation token for this interface.  The
         aggregation token controls what other links the link
         associated with this interface will be aggregated together
         with."
    REFERENCE
        "ATM Forum PNNI 1.0 Sections 5.3.5, 5.10.3.1"
    DEFVAL { 0 }
    ::= { pnniIfEntry 3 }

pnniIfVPCapability OBJECT-TYPE
    SYNTAX TruthValue
--    Rsyntax INTEGER {
--        true(1),
--        false(2)
--        }
    ACCESS read-write
    STATUS mandatory
    DESCRIPTION
        "Indicates whether the interface is capable of having VPCs
         established within it or not.
        
         This object may only have the value `true' for physical ATM
         interfaces, i.e. those with an ifType of atm(37)."
    REFERENCE
        "ATM Forum PNNI 1.0 Section 5.14.9.1 Table 5-34"
    ::= { pnniIfEntry 4 }

pnniIfAdmWeightCbr OBJECT-TYPE
    SYNTAX INTEGER(1..16777215)
--    SYNTAX Unsigned32
--    Rsyntax Gauge32(1..16777215)
    ACCESS read-write
    STATUS mandatory
    DESCRIPTION
        "The administrative weight of this interface for the
         constant bit rate service category."
    REFERENCE
        "ATM Forum PNNI 1.0 Section 5.8.1.1.3.4"
    DEFVAL { 5040 }
    ::= { pnniIfEntry 5 }

pnniIfAdmWeightRtVbr OBJECT-TYPE
    SYNTAX INTEGER(1..16777215)
--    SYNTAX Unsigned32
--    Rsyntax Gauge32(1..16777215)
    ACCESS read-write
    STATUS mandatory
    DESCRIPTION
        "The administrative weight of this interface for the
         real-time variable bit rate service category."
    REFERENCE
        "ATM Forum PNNI 1.0 Section 5.8.1.1.3.4"
    DEFVAL { 5040 }
    ::= { pnniIfEntry 6 }

pnniIfAdmWeightNrtVbr OBJECT-TYPE
    SYNTAX INTEGER(1..16777215)
--    SYNTAX Unsigned32
--    Rsyntax Gauge32(1..16777215)
    ACCESS read-write
    STATUS mandatory
    DESCRIPTION
        "The administrative weight of this interface for the
         non-real-time variable bit rate service category."
    REFERENCE
        "ATM Forum PNNI 1.0 Section 5.8.1.1.3.4"
    DEFVAL { 5040 }
    ::= { pnniIfEntry 7 }

pnniIfAdmWeightAbr OBJECT-TYPE
    SYNTAX INTEGER(1..16777215)
--    SYNTAX Unsigned32
--    Rsyntax Gauge32(1..16777215)
    ACCESS read-write
    STATUS mandatory
    DESCRIPTION
        "The administrative weight of this interface for the
         available bit rate service category."
    REFERENCE
        "ATM Forum PNNI 1.0 Section 5.8.1.1.3.4"
    DEFVAL { 5040 }
    ::= { pnniIfEntry 8 }

pnniIfAdmWeightUbr OBJECT-TYPE
    SYNTAX INTEGER(1..16777215)
--    SYNTAX Unsigned32
--    Rsyntax Gauge32(1..16777215)
    ACCESS read-write
    STATUS mandatory
    DESCRIPTION
        "The administrative weight of this interface for the
         unspecified bit rate service category."
    REFERENCE
        "ATM Forum PNNI 1.0 Section 5.8.1.1.3.4"
    DEFVAL { 5040 }
    ::= { pnniIfEntry 9 }

pnniIfRccServiceCategory OBJECT-TYPE
    SYNTAX ServiceCategory
--    Rsyntax INTEGER {
--        other(1),
--        cbr(2),
--        rtVbr(3),
--        nrtVbr(4),
--        abr(5),
--        ubr(6)
--        }
    ACCESS read-write
    STATUS mandatory
    DESCRIPTION
        "The service category used for the PNNI routing control
         channel (VCI=18) on this interface."
    REFERENCE
        "ATM Forum PNNI 1.0 Sections 5.5.2, 5.5.3"
    ::= { pnniIfEntry 10 }

pnniIfRccTrafficDescrIndex OBJECT-TYPE
    SYNTAX AtmTrafficDescrParamIndex
--    Rsyntax INTEGER(0..2147483647)
    ACCESS read-write
    STATUS mandatory
    DESCRIPTION
        "The traffic descriptor index referring to the entry in the
         atmTrafficDescrParamTable defined in RFC 1695 that
         specifies the traffic allocation for the PNNI routing
         control channel (VCI=18) on this interface."
    REFERENCE
        "ATM Forum PNNI 1.0 Sections 5.5.2, 5.5.3, Annex G
         RCCMaximumBurstSize, RCCPeakCellRate,
         RCCSustainableCellRate"
    ::= { pnniIfEntry 11 }

pnniLinkTable OBJECT-TYPE
    SYNTAX SEQUENCE OF PnniLinkEntry
    ACCESS not-accessible
    STATUS mandatory
    DESCRIPTION
        "This table contains the attributes necessary to describe
         the operation of logical links attached to the local
         switching system and the relationship with the neighbor
         nodes on the other end of the links.  Links are attached to
         a specific node within the switching system.  A
         concatenation of the Node Index of the node within the
         local switching system and the port ID are used as the
         instance ID to uniquely identify the link.  Links may
         represent horizontal links between lowest level neighboring
         peers, outside links, uplinks, or horizontal links to/from
         LGNs.
        
         The entire pnniLink object is read-only, reflecting the
         fact that this information is discovered dynamically by the
         PNNI protocol rather than configured."
    REFERENCE
        "ATM Forum PNNI 1.0 Section 5.6"
    ::= { pnniMIBObjects 9 }

pnniLinkEntry OBJECT-TYPE
    SYNTAX PnniLinkEntry
    ACCESS not-accessible
    STATUS mandatory
    DESCRIPTION
        "An entry in the table, containing information about a link
         attached to a PNNI logical node in this switching system."
    REFERENCE
        "ATM Forum PNNI 1.0 Section 5.6"
    INDEX { pnniNodeIndex, pnniLinkPortId }
    ::= { pnniLinkTable 1 }

PnniLinkEntry ::= SEQUENCE {
    pnniLinkPortId PnniPortId,
    pnniLinkType INTEGER,
    pnniLinkVersion PnniVersion,
    pnniLinkHelloState PnniHelloState,
    pnniLinkRemoteNodeId PnniNodeId,
    pnniLinkRemotePortId PnniPortId,
    pnniLinkDerivedAggrToken PnniAggrToken,
    pnniLinkUpnodeId PnniNodeId,
    pnniLinkUpnodeAtmAddress PnniAtmAddr,
    pnniLinkCommonPeerGroupId PnniPeerGroupId,
    pnniLinkIfIndex InterfaceIndex,
    pnniLinkSvccRccIndex PnniSvccRccIndex,
    pnniLinkRcvHellos Counter32,
    pnniLinkXmtHellos Counter32
    }

pnniLinkPortId OBJECT-TYPE
    SYNTAX PnniPortId
--    Rsyntax Gauge32
    ACCESS read-only
    STATUS mandatory
    DESCRIPTION
        "The Port Identifier of the link as selected by the local
         node.  This value has meaning only within the context of
         the node to which the port is attached."
    ::= { pnniLinkEntry 1 }

pnniLinkType OBJECT-TYPE
    SYNTAX INTEGER {
        unknown(1),
        lowestLevelHorizontalLink(2),
        horizontalLinkToFromLgn(3),
        lowestLevelOutsideLink(4),
        uplink(5),
        outsideLinkAndUplink(6)
        }
    ACCESS read-only
    STATUS mandatory
    DESCRIPTION
        "Indicates the type of link being described."
    ::= { pnniLinkEntry 2 }

pnniLinkVersion OBJECT-TYPE
    SYNTAX PnniVersion
--    Rsyntax INTEGER {
--        unsupported(1),
--        version1point0(2)
--        }
    ACCESS read-only
    STATUS mandatory
    DESCRIPTION
        "For horizontal and outside links between lowest-level nodes
         and for links of unknown type, this attribute indicates the
         version of PNNI routing protocol used to exchange
         information over this link.  If communication with the
         neighbor node has not yet been established, then the
         Version is set to `unknown'.  For uplinks (where the
         port ID is not also used for the underlying outside link)
         or links to/from LGNs, the Version is set to `unknown'."
    ::= { pnniLinkEntry 3 }

pnniLinkHelloState OBJECT-TYPE
    SYNTAX PnniHelloState
--    Rsyntax INTEGER {
--        notApplicable(1),
--        down(2),
--        attempt(3),
--        oneWayInside(4),
--        twoWayInside(5),
--        oneWayOutside(6),
--        twoWayOutside(7),
--        commonOutside(8)
--        }
    ACCESS read-only
    STATUS mandatory
    DESCRIPTION
        "For horizontal and outside links between lowest-level nodes
         and for links of unknown type, this attribute indicates the
         state of the Hello protocol exchange over this link.  For
         links to/from LGNs, this attribute indicates the state of
         the corresponding LGN Horizontal Link Hello State Machine.
         For uplinks (where the port ID is not also used for the
         underlying outside link), this attribute is set to
         notApplicable."
    REFERENCE
        "ATM Forum PNNI 1.0 Section 5.6.2.1.2"
    ::= { pnniLinkEntry 4 }

pnniLinkRemoteNodeId OBJECT-TYPE
    SYNTAX PnniNodeId
--    Rsyntax OCTET STRING(SIZE(22))
    ACCESS read-only
    STATUS mandatory
    DESCRIPTION
        "Indicates the node identifier of the remote (neighboring)
         node on the other end of the link.  If the pnniLinkType is
         `outside link and uplink', this is the node identifier of
         the lowest-level neighbor node on the other end of the
         outside link.  If the remote node ID is unknown or if the
         pnniLinkType is `uplink', this attribute is set to all
         zeros."
    ::= { pnniLinkEntry 5 }

pnniLinkRemotePortId OBJECT-TYPE
    SYNTAX PnniPortId
--    Rsyntax Gauge32
    ACCESS read-only
    STATUS mandatory
    DESCRIPTION
        "Indicates the port identifier of the port at the remote end
         of the link as assigned by the remote node.  If the
         pnniLinkType is `outside link and uplink', this is the port
         identifier assigned by the lowest-level neighbor node to
         identify the outside link.  If the remote port ID is
         unknown or if the pnniLinkType is `uplink', this attribute
         is set to zero."
    ::= { pnniLinkEntry 6 }

pnniLinkDerivedAggrToken OBJECT-TYPE
    SYNTAX PnniAggrToken
--    Rsyntax Gauge32
    ACCESS read-only
    STATUS mandatory
    DESCRIPTION
        "Indicates the derived aggregation token value used on this
         link.  For horizontal links between lowest-level nodes and
         when the link type is not yet known, this attribute takes
         the value of zero."
    REFERENCE
        "ATM Forum PNNI 1.0 Section 5.10.3.1"
    ::= { pnniLinkEntry 7 }

pnniLinkUpnodeId OBJECT-TYPE
    SYNTAX PnniNodeId
--    Rsyntax OCTET STRING(SIZE(22))
    ACCESS read-only
    STATUS mandatory
    DESCRIPTION
        "For outside links and uplinks, this attribute contains the
         Node Identifier of the upnode (the neighbor node's identity
         at the level of the common peer group).  When the upnode
         has not yet been identified, this attribute is set to zero.
         For horizontal links or when the link type is not yet
         known, this attribute is set to zero."
    ::= { pnniLinkEntry 8 }

pnniLinkUpnodeAtmAddress OBJECT-TYPE
    SYNTAX PnniAtmAddr
--    Rsyntax OCTET STRING(SIZE(0 | 20))
    ACCESS read-only
    STATUS mandatory
    DESCRIPTION
        "For outside links and uplinks, this attribute contains the
         ATM End System Address used to establish connections to the
         upnode.  When the upnode has not yet been identified, this
         attribute is set to zero.  For horizontal links or when the
         link type is not yet known, this attribute is set to zero."
    ::= { pnniLinkEntry 9 }

pnniLinkCommonPeerGroupId OBJECT-TYPE
    SYNTAX PnniPeerGroupId
--    Rsyntax OCTET STRING(SIZE(14))
    ACCESS read-only
    STATUS mandatory
    DESCRIPTION
        "For outside links and uplinks, this attribute contains the
         peer group identifier of the lowest level common Peer Group
         in the ancestry of the neighboring node and the node within
         the local switching system.  The value of this attribute
         takes on a value determined by the Hello exchange of
         hierarchical information that occurs between the two
         lowest-level border nodes.  When the common peer group has
         not yet been identified, this attribute is set to zero.
         For horizontal links or when the link type is not yet
         known, this attribute is set to all zeros."
    ::= { pnniLinkEntry 10 }

pnniLinkIfIndex OBJECT-TYPE
    SYNTAX InterfaceIndex
--    Rsyntax Integer32
    ACCESS read-only
    STATUS mandatory
    DESCRIPTION
        "For horizontal and outside links between lowest-level nodes
         and for links of unknown type, this attribute identifies
         the interface to which the logical link corresponds.
        
         For all other cases, the value of this object is zero."
    ::= { pnniLinkEntry 11 }

pnniLinkSvccRccIndex OBJECT-TYPE
    SYNTAX PnniSvccRccIndex
--    Rsyntax Integer32
    ACCESS read-only
    STATUS mandatory
    DESCRIPTION
        "For horizontal links to/from LGNs, this attribute
         identifies the SVCC-based RCC used to exchange information
         with the neighboring peer logical group node.  If the
         pnniLinkType is not `horizontal link to/from LGN', this
         attribute shall take the value of zero."
    ::= { pnniLinkEntry 12 }

pnniLinkRcvHellos OBJECT-TYPE
    SYNTAX Counter32
    ACCESS read-only
    STATUS mandatory
    DESCRIPTION
        "For horizontal and outside links between lowest-level nodes
         and for links of unknown type, this attribute contains a
         count of the number of Hello Packets received over this
         link.  If the pnniLinkType is `horizontal link to/from LGN'
         or `uplink', this attribute is set to zero."
    ::= { pnniLinkEntry 13 }

pnniLinkXmtHellos OBJECT-TYPE
    SYNTAX Counter32
    ACCESS read-only
    STATUS mandatory
    DESCRIPTION
        "For horizontal and outside links between lowest-level nodes
         and for links of unknown type, this attribute contains a
         count of the number of Hello Packets transmitted over this
         link.  If the pnniLinkType is `horizontal link to/from LGN'
         or `uplink', this attribute is set to zero."
    ::= { pnniLinkEntry 14 }

pnniNbrPeerTable OBJECT-TYPE
    SYNTAX SEQUENCE OF PnniNbrPeerEntry
    ACCESS not-accessible
    STATUS mandatory
    DESCRIPTION
        "The pnniNbrPeer Object contains all the attributes
         necessary to describe the relationship a node in this
         switching system has with a neighboring node within the
         same peer group.  A concatenation of the Node Identifier of
         the node within the local switching system and the
         neighboring peer's Node Identifier is used to form the
         instance ID for this object.
        
         The entire pnniNbrPeer object is read-only, reflecting the
         fact that neighboring peers are discovered dynamically by
         the PNNI protocol rather than configured."
    REFERENCE
        "ATM Forum PNNI 1.0 Sections 5.7, 5.8"
    ::= { pnniMIBObjects 10 }

pnniNbrPeerEntry OBJECT-TYPE
    SYNTAX PnniNbrPeerEntry
    ACCESS not-accessible
    STATUS mandatory
    DESCRIPTION
        "An entry in the table, containing information about this
         node's relationship with a neighboring peer node."
    REFERENCE
        "ATM Forum PNNI 1.0 Sections 5.7, 5.8"
    INDEX { pnniNodeIndex, pnniNbrPeerRemoteNodeId }
    ::= { pnniNbrPeerTable 1 }

PnniNbrPeerEntry ::= SEQUENCE {
    pnniNbrPeerRemoteNodeId PnniNodeId,
    pnniNbrPeerState INTEGER,
    pnniNbrPeerSvccRccIndex PnniSvccRccIndex,
    pnniNbrPeerPortCount Gauge32,
    pnniNbrPeerRcvDbSums Counter32,
    pnniNbrPeerXmtDbSums Counter32,
    pnniNbrPeerRcvPtsps Counter32,
    pnniNbrPeerXmtPtsps Counter32,
    pnniNbrPeerRcvPtseReqs Counter32,
    pnniNbrPeerXmtPtseReqs Counter32,
    pnniNbrPeerRcvPtseAcks Counter32,
    pnniNbrPeerXmtPtseAcks Counter32
    }

pnniNbrPeerRemoteNodeId OBJECT-TYPE
    SYNTAX PnniNodeId
--    Rsyntax OCTET STRING(SIZE(22))
    ACCESS read-only 
    STATUS mandatory
    DESCRIPTION
        "The Node Identifier of the neighboring peer node."
    ::= { pnniNbrPeerEntry 1 }

pnniNbrPeerState OBJECT-TYPE
    SYNTAX INTEGER {
        npdown(1),
        negotiating(2),
        exchanging(3),
        loading(4),
        full(5)
        }
    ACCESS read-only
    STATUS mandatory
    DESCRIPTION
        "Indicates the state of this node's Neighboring Peer State
         Machine associated with pnniNbrPeerRemoteNodeId."
    REFERENCE
        "ATM Forum PNNI 1.0 Section 5.7.2"
    ::= { pnniNbrPeerEntry 2 }

pnniNbrPeerSvccRccIndex OBJECT-TYPE
    SYNTAX PnniSvccRccIndex
--    Rsyntax Integer32
    ACCESS read-only
    STATUS mandatory
    DESCRIPTION
        "Identifies the SVCC-based RCC being used to communicate
         with the neighboring peer if one exists.  If both the local
         node and the neighboring peer node are lowest-level nodes,
         this attribute is set to zero."
    ::= { pnniNbrPeerEntry 3 }

pnniNbrPeerPortCount OBJECT-TYPE
    SYNTAX Gauge32
    ACCESS read-only
    STATUS mandatory
    DESCRIPTION
        "A count of the total number of ports that connect to the
         neighboring peer.  If the neighboring peer only
         communicates via an SVCC-based RCC, the value of this
         attribute is set to zero.  Otherwise it is set to the total
         number of ports to the neighboring peer in the Hello state
         2-WayInside."
    ::= { pnniNbrPeerEntry 4 }

pnniNbrPeerRcvDbSums OBJECT-TYPE
    SYNTAX Counter32
    ACCESS read-only
    STATUS mandatory
    DESCRIPTION
        "A count of the number of Database Summary Packets received
         from the neighboring peer."
    ::= { pnniNbrPeerEntry 5 }

pnniNbrPeerXmtDbSums OBJECT-TYPE
    SYNTAX Counter32
    ACCESS read-only
    STATUS mandatory
    DESCRIPTION
        "A count of the number of Database Summary Packets
         transmitted to the neighboring peer."
    ::= { pnniNbrPeerEntry 6 }

pnniNbrPeerRcvPtsps OBJECT-TYPE
    SYNTAX Counter32
    ACCESS read-only
    STATUS mandatory
    DESCRIPTION
        "A count of the number of PTSPs received from the
         neighboring peer."
    ::= { pnniNbrPeerEntry 7 }

pnniNbrPeerXmtPtsps OBJECT-TYPE
    SYNTAX Counter32
    ACCESS read-only
    STATUS mandatory
    DESCRIPTION
        "A count of the number of PTSPs (re)transmitted to the
         neighboring peer."
    ::= { pnniNbrPeerEntry 8 }

pnniNbrPeerRcvPtseReqs OBJECT-TYPE
    SYNTAX Counter32
    ACCESS read-only
    STATUS mandatory
    DESCRIPTION
        "A count of the number of PTSE Request packets received from
         the neighboring peer."
    ::= { pnniNbrPeerEntry 9 }

pnniNbrPeerXmtPtseReqs OBJECT-TYPE
    SYNTAX Counter32
    ACCESS read-only
    STATUS mandatory
    DESCRIPTION
        "A count of the number of PTSE Request packets transmitted
         to the neighboring peer."
    ::= { pnniNbrPeerEntry 10 }

pnniNbrPeerRcvPtseAcks OBJECT-TYPE
    SYNTAX Counter32
    ACCESS read-only
    STATUS mandatory
    DESCRIPTION
        "A count of the number of PTSE Ack packets received from the
         neighboring peer."
    ::= { pnniNbrPeerEntry 11 }

pnniNbrPeerXmtPtseAcks OBJECT-TYPE
    SYNTAX Counter32
    ACCESS read-only
    STATUS mandatory
    DESCRIPTION
        "A count of the number of PTSE Ack packets transmitted to
         the neighboring peer."
    ::= { pnniNbrPeerEntry 12 }

pnniNbrPeerPortTable OBJECT-TYPE
    SYNTAX SEQUENCE OF PnniNbrPeerPortEntry
    ACCESS not-accessible
    STATUS mandatory
    DESCRIPTION
        "A table of all ports in Hello state 2-Way Inside to a given
         neighboring peer node.  A concatenation of the Node Index
         of the node within the local switching system, the
         neighbor's Node Identifier and the Interface Index of the
         port being described forms the instance ID for this object.
         This object is only used for lowest-level nodes."
    REFERENCE
        "ATM Forum PNNI 1.0 Section 5.7.1 Port ID List"
    ::= { pnniMIBObjects 11 }

pnniNbrPeerPortEntry OBJECT-TYPE
    SYNTAX PnniNbrPeerPortEntry
    ACCESS not-accessible
    STATUS mandatory
    DESCRIPTION
        "An entry in the table, containing information about a port
         in the Hello state 2-Way Inside from a PNNI logical node in
         this switching system to a neighboring peer node."
    INDEX { pnniNodeIndex, pnniNbrPeerRemoteNodeId, pnniNbrPeerPortId }
    ::= { pnniNbrPeerPortTable 1 }

PnniNbrPeerPortEntry ::= SEQUENCE {
    pnniNbrPeerPortId PnniPortId,
    pnniNbrPeerPortFloodStatus TruthValue
    }

pnniNbrPeerPortId OBJECT-TYPE
    SYNTAX PnniPortId
--    Rsyntax Gauge32
    ACCESS read-only 
    STATUS mandatory
    DESCRIPTION
        "The port ID of a port to the neighboring peer that is in
         the Hello state 2-Way Inside."
    ::= { pnniNbrPeerPortEntry 1 }

pnniNbrPeerPortFloodStatus OBJECT-TYPE
    SYNTAX TruthValue
--    Rsyntax INTEGER {
--        true(1),
--        false(2)
--        }
    ACCESS read-only
    STATUS mandatory
    DESCRIPTION
        "Indicates whether the port is being used for transmission
         of flooding and database synchronization information to the
         neighboring peer."
    ::= { pnniNbrPeerPortEntry 2 }

pnniSvccRccTable OBJECT-TYPE
    SYNTAX SEQUENCE OF PnniSvccRccEntry
    ACCESS not-accessible
    STATUS mandatory
    DESCRIPTION
        "A table containing the attributes necessary to analyze the
         operation of the PNNI protocol on SVCC-based Routing
         Control Channels. This entire object is read-only,
         reflecting the fact that SVCC-based RCCs are established
         dynamically during operation of the PNNI protocol rather
         than configured."
    REFERENCE
        "ATM Forum PNNI 1.0 Sections 5.5.6, 5.6.3.1"
    ::= { pnniMIBObjects 12 }

pnniSvccRccEntry OBJECT-TYPE
    SYNTAX PnniSvccRccEntry
    ACCESS not-accessible
    STATUS mandatory
    DESCRIPTION
        "An entry in the table, containing information about an
         SVCC-based RCC from a PNNI logical node in this switching
         system."
    REFERENCE
        "ATM Forum PNNI 1.0 Sections 5.5.6, 5.6.3.1"
    INDEX { pnniNodeIndex, pnniSvccRccIndex }
    ::= { pnniSvccRccTable 1 }

PnniSvccRccEntry ::= SEQUENCE {
    pnniSvccRccIndex PnniSvccRccIndex,
    pnniSvccRccVersion PnniVersion,
    pnniSvccRccHelloState PnniHelloState,
    pnniSvccRccRemoteNodeId PnniNodeId,
    pnniSvccRccRemoteAtmAddress PnniAtmAddr,
    pnniSvccRccRcvHellos Counter32,
    pnniSvccRccXmtHellos Counter32,
    pnniSvccRccIfIndex InterfaceIndex,
    pnniSvccRccVpi INTEGER,
    pnniSvccRccVci INTEGER
    }

pnniSvccRccIndex OBJECT-TYPE
    SYNTAX PnniSvccRccIndex
--    Rsyntax Integer32
    ACCESS read-only 
    STATUS mandatory
    DESCRIPTION
        "An index into the node's tables of SVCC-based RCCs."
    ::= { pnniSvccRccEntry 1 }

pnniSvccRccVersion OBJECT-TYPE
    SYNTAX PnniVersion
--    Rsyntax INTEGER {
--        unsupported(1),
--        version1point0(2)
--        }
    ACCESS read-only
    STATUS mandatory
    DESCRIPTION
        "The version of the PNNI routing protocol used to exchange
         information with the neighbor node."
    ::= { pnniSvccRccEntry 2 }

pnniSvccRccHelloState OBJECT-TYPE
    SYNTAX PnniHelloState
--    Rsyntax INTEGER {
--        notApplicable(1),
--        down(2),
--        attempt(3),
--        oneWayInside(4),
--        twoWayInside(5),
--        oneWayOutside(6),
--        twoWayOutside(7),
--        commonOutside(8)
--        }
    ACCESS read-only
    STATUS mandatory
    DESCRIPTION
        "The state of the Hello protocol exchange over the
         SVCC-based RCC.
        
         Note: the Down state indicates that the SVCC
         establishment is in progress."
    ::= { pnniSvccRccEntry 3 }

pnniSvccRccRemoteNodeId OBJECT-TYPE
    SYNTAX PnniNodeId
--    Rsyntax OCTET STRING(SIZE(22))
    ACCESS read-only
    STATUS mandatory
    DESCRIPTION
        "The remote node at which the SVCC-based RCC terminates."
    ::= { pnniSvccRccEntry 4 }

pnniSvccRccRemoteAtmAddress OBJECT-TYPE
    SYNTAX PnniAtmAddr
--    Rsyntax OCTET STRING(SIZE(0 | 20))
    ACCESS read-only
    STATUS mandatory
    DESCRIPTION
        "The ATM End System Address to which SVCC establishment is
         attempted."
    ::= { pnniSvccRccEntry 5 }

pnniSvccRccRcvHellos OBJECT-TYPE
    SYNTAX Counter32
    ACCESS read-only
    STATUS mandatory
    DESCRIPTION
        "A count of the number of Hello Packets received over this
         SVCC-based RCC."
    ::= { pnniSvccRccEntry 6 }

pnniSvccRccXmtHellos OBJECT-TYPE
    SYNTAX Counter32
    ACCESS read-only
    STATUS mandatory
    DESCRIPTION
        "A count of the number of Hello Packets transmitted over
         this SVCC-based RCC."
    ::= { pnniSvccRccEntry 7 }

pnniSvccRccIfIndex OBJECT-TYPE
    SYNTAX InterfaceIndex
--    Rsyntax Integer32
    ACCESS read-only
    STATUS mandatory
    DESCRIPTION
        "The interface from which the SVCC-based RCC leaves the
         switching system.  If the SVCC-based RCC has not yet been
         established, then this attribute takes the value of zero."
    ::= { pnniSvccRccEntry 8 }

pnniSvccRccVpi OBJECT-TYPE
    SYNTAX INTEGER(0..4095)
    ACCESS read-only
    STATUS mandatory
    DESCRIPTION
        "The VPI used at the interface from which the SVCC-based RCC
         leaves the switching system.  If the SVCC-based RCC has not
         yet been established, then this attribute takes the value
         of zero "
    ::= { pnniSvccRccEntry 9 }

pnniSvccRccVci OBJECT-TYPE
    SYNTAX INTEGER(0..65535)
    ACCESS read-only
    STATUS mandatory
    DESCRIPTION
        "The VCI used at the interface from which the SVCC-based RCC
         leaves the switching system.  If the SVCC-based RCC has not
         yet been established, then this attribute takes the value
         of zero "
    ::= { pnniSvccRccEntry 10 }

pnniPtseTable OBJECT-TYPE
    SYNTAX SEQUENCE OF PnniPtseEntry
    ACCESS not-accessible
    STATUS mandatory
    DESCRIPTION
        "The pnniPtse object contains the attributes that describe
         the most recent instances of PTSEs in a node's topology
         database.  A concatenation of the Node Identifier of the
         local node that received the PTSE, the originating Node's
         Node Identifier and the PTSE Identifier are used to form
         the instance ID for an instance of this object."
    REFERENCE
        "ATM Forum PNNI 1.0 Section 5.8.2"
    ::= { pnniMIBObjects 13 }

pnniPtseEntry OBJECT-TYPE
    SYNTAX PnniPtseEntry
    ACCESS not-accessible
    STATUS mandatory
    DESCRIPTION
        "An entry in the table, containing information about a PTSE
         in the topology database of a PNNI logical node in this
         switching system."
    REFERENCE
        "ATM Forum PNNI 1.0 Section 5.8.2"
    INDEX { pnniNodeIndex, pnniPtseOriginatingNodeId, pnniPtseId }
    ::= { pnniPtseTable 1 }

PnniPtseEntry ::= SEQUENCE {
    pnniPtseOriginatingNodeId PnniNodeId,
    pnniPtseId INTEGER,
    pnniPtseType INTEGER,
    pnniPtseSequenceNum INTEGER,
    pnniPtseChecksum INTEGER,
    pnniPtseLifeTime INTEGER,
    pnniPtseInfo OCTET STRING
    }

pnniPtseOriginatingNodeId OBJECT-TYPE
    SYNTAX PnniNodeId
--    Rsyntax OCTET STRING(SIZE(22))
    ACCESS read-only 
    STATUS mandatory
    DESCRIPTION
        "The Node Identifier of the node that originated the PTSE."
    ::= { pnniPtseEntry 1 }

pnniPtseId OBJECT-TYPE
    SYNTAX INTEGER
--    Rsyntax Gauge32
    ACCESS read-only 
    STATUS mandatory
    DESCRIPTION
        "The value of the PTSE Identifier assigned to the PTSE by
         its originator."
    ::= { pnniPtseEntry 2 }

pnniPtseType OBJECT-TYPE
    SYNTAX INTEGER {
        other(1),
        nodalStateParameters(96),
        nodalInformation(97),
        internalReachableAddresses(224),
        exteriorReachableAddresses(256),
        horizontalLinks(288),
        uplinks(289)
        }
    ACCESS read-only
    STATUS mandatory
    DESCRIPTION
        "The type of information contained in the PTSE."
    ::= { pnniPtseEntry 3 }

pnniPtseSequenceNum OBJECT-TYPE
    SYNTAX INTEGER
--    Rsyntax Gauge32
    ACCESS read-only
    STATUS mandatory
    DESCRIPTION
        "The sequence number of the instance of the PTSE as it
         appears in the local topology database."
    ::= { pnniPtseEntry 4 }

pnniPtseChecksum OBJECT-TYPE
    SYNTAX INTEGER(0..65535)
--    Rsyntax Gauge32(0..65535)
    ACCESS read-only
    STATUS mandatory
    DESCRIPTION
        "The value of the PTSE checksum as it appears in the local
         topology database."
    ::= { pnniPtseEntry 5 }

pnniPtseLifeTime OBJECT-TYPE
    SYNTAX INTEGER(0..65535)
--    Rsyntax Gauge32(0..65535)
--  Units
--    seconds
    ACCESS read-only
    STATUS mandatory
    DESCRIPTION
        "The value of the remaining lifetime for the given PTSE as
         it appears in the local topology database."
    ::= { pnniPtseEntry 6 }

pnniPtseInfo OBJECT-TYPE
    SYNTAX OCTET STRING(SIZE(0..65535))
    ACCESS read-only
    STATUS mandatory
    DESCRIPTION
        "An unformatted hexadecimal dump of the PTSE contents in
         full.
        
         Note: If the size of the PTSE contents is larger than the
         maximum size of SNMP packets then this is truncated."
    ::= { pnniPtseEntry 7 }

pnniMapTable OBJECT-TYPE
    SYNTAX SEQUENCE OF PnniMapEntry
    ACCESS not-accessible
    STATUS mandatory
    DESCRIPTION
        "A table containing attributes necessary to find and analyze
         the operation of all links and nodes within the PNNI
         hierarchy, as seen from the perspective of a local node.
         An instance of a pnniMap Object describes a link in terms
         of a node at one end of the link.  Normally there will be
         two instances of the pnniMap object in the MIB for each
         horizontal link. The two instances provide information for
         Network management to map port identifiers from the nodes
         at both ends to the link between them.  A concatenation of
         the Local Node Index, Originating Node Identifier and
         Originating Port Identifier are used to form the instance
         ID for this object.
        
         This entire object is read-only, reflecting the fact that
         the map is discovered dynamically during operation of the
         PNNI protocol rather than configured."
    ::= { pnniMIBObjects 14 }

pnniMapEntry OBJECT-TYPE
    SYNTAX PnniMapEntry
    ACCESS not-accessible
    STATUS mandatory
    DESCRIPTION
        "An entry in the table, containing connectivity information
         about a node or link in the PNNI routing domain, as seen
         from the perspective of a PNNI logical node in this
         switching system."
    INDEX { pnniNodeIndex, pnniMapOriginatingNodeId, pnniMapOriginatingPortId, pnniMapIndex }
    ::= { pnniMapTable 1 }

PnniMapEntry ::= SEQUENCE {
    pnniMapOriginatingNodeId PnniNodeId,
    pnniMapOriginatingPortId PnniPortId,
    pnniMapIndex INTEGER,
    pnniMapType INTEGER,
    pnniMapPeerGroupId PnniPeerGroupId,
    pnniMapAggrToken PnniAggrToken,
    pnniMapRemoteNodeId PnniNodeId,
    pnniMapRemotePortId PnniPortId,
    pnniMapVPCapability TruthValue,
    pnniMapPtseId INTEGER,
    pnniMapMetricsTag PnniMetricsTag
    }

pnniMapOriginatingNodeId OBJECT-TYPE
    SYNTAX PnniNodeId
--    Rsyntax OCTET STRING(SIZE(22))
    ACCESS read-only 
    STATUS mandatory
    DESCRIPTION
        "The node identifier of the node whose connectivity within
         itself or to other nodes is being described."
    ::= { pnniMapEntry 1 }

pnniMapOriginatingPortId OBJECT-TYPE
    SYNTAX PnniPortId
--    Rsyntax Gauge32
    ACCESS read-only 
    STATUS mandatory
    DESCRIPTION
        "The port identifier of the port as assigned by the
         originating node, to which the port is attached."
    ::= { pnniMapEntry 2 }

pnniMapIndex OBJECT-TYPE
    SYNTAX INTEGER(0..65535)
    ACCESS read-only 
    STATUS mandatory
    DESCRIPTION
        "An index into the set of link and nodal connectivity
         associated with the originating node and port.  This index
         is needed since there may be multiple entries for nodal
         connectivity from a specific node and port pair, in
         addition to any entry for a horizontal link or uplink."
    ::= { pnniMapEntry 3 }

pnniMapType OBJECT-TYPE
    SYNTAX INTEGER {
        horizontalLink(1),
        uplink(2),
        node(3)
        }
    ACCESS read-only
    STATUS mandatory
    DESCRIPTION
        "The type of PNNI entity being described by this entry in
         the table."
    ::= { pnniMapEntry 4 }

pnniMapPeerGroupId OBJECT-TYPE
    SYNTAX PnniPeerGroupId
--    Rsyntax OCTET STRING(SIZE(14))
    ACCESS read-only
    STATUS mandatory
    DESCRIPTION
        "Identifies the peer group of the originating node."
    ::= { pnniMapEntry 5 }

pnniMapAggrToken OBJECT-TYPE
    SYNTAX PnniAggrToken
--    Rsyntax Gauge32
    ACCESS read-only
    STATUS mandatory
    DESCRIPTION
        "For horizontal links to/from LGNs and for uplinks, this
         attribute contains the derived aggregation token value for
         this link.  For nodes and for horizontal links between
         lowest-level nodes, this attribute is set to zero."
    ::= { pnniMapEntry 6 }

pnniMapRemoteNodeId OBJECT-TYPE
    SYNTAX PnniNodeId
--    Rsyntax OCTET STRING(SIZE(22))
    ACCESS read-only
    STATUS mandatory
    DESCRIPTION
        "For horizontal links and uplinks, this attribute contains
         the node identifier of the node at the other end of the
         link from the originating node.  If unknown, the PNNI
         protocol entity sets this attribute's value to (all)
         zero(s).  For nodes, this attribute's value is set to (all)
         zero(s)."
    ::= { pnniMapEntry 7 }

pnniMapRemotePortId OBJECT-TYPE
    SYNTAX PnniPortId
--    Rsyntax Gauge32
    ACCESS read-only
    STATUS mandatory
    DESCRIPTION
        "For horizontal links and uplinks, this attribute contains
         the port identifier of the port at the remote end of the
         link as assigned by the remote node.  If unknown, the PNNI
         protocol entity sets this attribute's value to zero.
        
         For nodes, this attribute contains the port identifier of
         the port at the other end of the spoke or bypass from the
         originating port.  When the originating port ID is zero, a
         value of zero indicates the default radius.  When the
         originating port ID is non-zero, a value of zero indicates
         the nodal nucleus."
    ::= { pnniMapEntry 8 }

pnniMapVPCapability OBJECT-TYPE
    SYNTAX TruthValue
--    Rsyntax INTEGER {
--        true(1),
--        false(2)
--        }
    ACCESS read-only
    STATUS mandatory
    DESCRIPTION
        "Indicates whether VPCs
         can be established across the PNNI entity being described
         by this entry in the pnniMapTable."
    ::= { pnniMapEntry 9 }

pnniMapPtseId OBJECT-TYPE
    SYNTAX INTEGER
--    Rsyntax Gauge32
    ACCESS read-only
    STATUS mandatory
    DESCRIPTION
        "The value of the PTSE Identifier for the PTSE being
         originated by the originating node which contains the
         information group(s) describing the PNNI entity."
    ::= { pnniMapEntry 10 }

pnniMapMetricsTag OBJECT-TYPE
    SYNTAX PnniMetricsTag
--    Rsyntax Integer32(0..2147483647)
    ACCESS read-only
    STATUS mandatory
    DESCRIPTION
        "An arbitrary integer that is used to associate a set of
         traffic parameters that are always advertised together.
         Within this set, the parameters are distinguished by the
         service categories and direction to which a set of
         parameters apply.  This value is used as an index into
         the pnniMetricsTable.  The distinguished value zero
         indicates that no metrics are associated with the link or
         nodal connectivity."
    ::= { pnniMapEntry 11 }

pnniMapNodeTable OBJECT-TYPE
    SYNTAX SEQUENCE OF PnniMapNodeEntry
    ACCESS not-accessible
    STATUS mandatory
    DESCRIPTION
        "A list of nodes as seen from the perspective of a local
         node.  The pnniMapNodeTable contains all information
         learned by the local node from nodal information PTSEs.
         This entire object is read-only, reflecting the fact that
         the map is discovered dynamically during operation of the
         PNNI protocol rather than configured."
    ::= { pnniMIBObjects 15 }

pnniMapNodeEntry OBJECT-TYPE
    SYNTAX PnniMapNodeEntry
    ACCESS not-accessible
    STATUS mandatory
    DESCRIPTION
        "An entry in the table, containing information about a node
         in the PNNI routing domain, as seen from the perspective of
         a logical node in this switching system."
    INDEX { pnniNodeIndex, pnniMapNodeId }
    ::= { pnniMapNodeTable 1 }

PnniMapNodeEntry ::= SEQUENCE {
    pnniMapNodeId PnniNodeId,
    pnniMapNodePeerGroupId PnniPeerGroupId,
    pnniMapNodeAtmAddress PnniAtmAddr,
    pnniMapNodeRestrictedTransit TruthValue,
    pnniMapNodeComplexRep TruthValue,
    pnniMapNodeRestrictedBranching TruthValue,
    pnniMapNodeDatabaseOverload TruthValue,
    pnniMapNodeIAmLeader TruthValue,
    pnniMapNodeLeadershipPriority INTEGER,
    pnniMapNodePreferredPgl PnniNodeId,
    pnniMapNodeParentNodeId PnniNodeId,
    pnniMapNodeParentAtmAddress PnniAtmAddr,
    pnniMapNodeParentPeerGroupId PnniPeerGroupId,
    pnniMapNodeParentPglNodeId PnniNodeId
    }

pnniMapNodeId OBJECT-TYPE
    SYNTAX PnniNodeId
--    Rsyntax OCTET STRING(SIZE(22))
    ACCESS read-only 
    STATUS mandatory
    DESCRIPTION
        "Identifies the node whose nodal information is being
         described."
    ::= { pnniMapNodeEntry 1 }

pnniMapNodePeerGroupId OBJECT-TYPE
    SYNTAX PnniPeerGroupId
--    Rsyntax OCTET STRING(SIZE(14))
    ACCESS read-only
    STATUS mandatory
    DESCRIPTION
        "Identifies the peer group of the originating node."
    ::= { pnniMapNodeEntry 2 }

pnniMapNodeAtmAddress OBJECT-TYPE
    SYNTAX PnniAtmAddr
--    Rsyntax OCTET STRING(SIZE(0 | 20))
    ACCESS read-only
    STATUS mandatory
    DESCRIPTION
        "The ATM End System Address of the originating node."
    ::= { pnniMapNodeEntry 3 }

pnniMapNodeRestrictedTransit OBJECT-TYPE
    SYNTAX TruthValue
--    Rsyntax INTEGER {
--        true(1),
--        false(2)
--        }
    ACCESS read-only
    STATUS mandatory
    DESCRIPTION
        "Indicates whether the originating node is restricted to
         only allow support of SVCs originating or terminating at
         this node.  A value of `true' indicates that the transit
         capabilities are restricted, i.e., transit connections are
         not allowed, whereas a value of `false' indicates that
         transit connections are allowed.  This attribute reflects
         the setting of the restricted transit bit received in the
         nodal information PTSE of the originating node."
    ::= { pnniMapNodeEntry 4 }

pnniMapNodeComplexRep OBJECT-TYPE
    SYNTAX TruthValue
--    Rsyntax INTEGER {
--        true(1),
--        false(2)
--        }
    ACCESS read-only
    STATUS mandatory
    DESCRIPTION
        "Indicates whether the originating node uses the complex
         node representation.  If the value is `true', the spokes
         and bypasses that make up the complex node representation
         should be found in the pnniMapTable.  This attribute
         reflects the setting of the nodal representation bit
         received in the nodal information PTSE of the originating
         node."
    ::= { pnniMapNodeEntry 5 }

pnniMapNodeRestrictedBranching OBJECT-TYPE
    SYNTAX TruthValue
--    Rsyntax INTEGER {
--        true(1),
--        false(2)
--        }
    ACCESS read-only
    STATUS mandatory
    DESCRIPTION
        "Indicates whether the originating node is able to support
         additional branches.  If the value is 'false', then it can
         support additional branches.  This attribute reflects the
         setting of the restricted branching bit received in the
         nodal information PTSE of the originating node."
    ::= { pnniMapNodeEntry 6 }

pnniMapNodeDatabaseOverload OBJECT-TYPE
    SYNTAX TruthValue
--    Rsyntax INTEGER {
--        true(1),
--        false(2)
--        }
    ACCESS read-only
    STATUS mandatory
    DESCRIPTION
        "Indicates whether the originating node is currently
         operating in topology database overload state.  This
         attribute has the same value as the Non-transit for PGL
         Election bit in the nodal information group originated by
         this node."
    ::= { pnniMapNodeEntry 7 }

pnniMapNodeIAmLeader OBJECT-TYPE
    SYNTAX TruthValue
--    Rsyntax INTEGER {
--        true(1),
--        false(2)
--        }
    ACCESS read-only
    STATUS mandatory
    DESCRIPTION
        "Indicates whether the originating node claims to be peer
         group leader of its peer group.  This attribute reflects
         the setting of the 'I am Leader' bit received in the nodal
         information PTSE of the originating node."
    ::= { pnniMapNodeEntry 8 }

pnniMapNodeLeadershipPriority OBJECT-TYPE
    SYNTAX INTEGER(0..255)
    ACCESS read-only
    STATUS mandatory
    DESCRIPTION
        "The Leadership priority value advertised by the originating
         node."
    ::= { pnniMapNodeEntry 9 }

pnniMapNodePreferredPgl OBJECT-TYPE
    SYNTAX PnniNodeId
--    Rsyntax OCTET STRING(SIZE(22))
    ACCESS read-only
    STATUS mandatory
    DESCRIPTION
        "Identifies the node which the originating node believes
         should be or is peer group leader of its peer group.  If
         the originating node has not chosen a Preferred PGL, this
         attribute's value is set to (all) zero(s)."
    ::= { pnniMapNodeEntry 10 }

pnniMapNodeParentNodeId OBJECT-TYPE
    SYNTAX PnniNodeId
--    Rsyntax OCTET STRING(SIZE(22))
    ACCESS read-only
    STATUS mandatory
    DESCRIPTION
        "When the originating node is a peer group leader, indicates
         the node ID of the parent LGN.  If the originating node is
         not peer group leader of its peer group, this attribute's
         value is set to (all) zero(s)."
    ::= { pnniMapNodeEntry 11 }

pnniMapNodeParentAtmAddress OBJECT-TYPE
    SYNTAX PnniAtmAddr
--    Rsyntax OCTET STRING(SIZE(0 | 20))
    ACCESS read-only
    STATUS mandatory
    DESCRIPTION
        "When the originating node is a peer group leader, indicates
         the ATM address of the parent LGN.  If the originating node
         is not peer group leader of its peer group, this
         attribute's value is set to (all) zero(s)."
    ::= { pnniMapNodeEntry 12 }

pnniMapNodeParentPeerGroupId OBJECT-TYPE
    SYNTAX PnniPeerGroupId
--    Rsyntax OCTET STRING(SIZE(14))
    ACCESS read-only
    STATUS mandatory
    DESCRIPTION
        "When the originating node is a peer group leader, indicates
         the node's parent peer group ID.  If the originating node
         is not peer group leader of its peer group, this
         attribute's value is set to (all) zero(s)."
    ::= { pnniMapNodeEntry 13 }

pnniMapNodeParentPglNodeId OBJECT-TYPE
    SYNTAX PnniNodeId
--    Rsyntax OCTET STRING(SIZE(22))
    ACCESS read-only
    STATUS mandatory
    DESCRIPTION
        "When the originating node is a peer group leader,
         identifies the node elected as peer group leader of the
         parent peer group.  If the originating node is not peer
         group leader of its peer group, this attribute's value is
         set to (all) zero(s)."
    ::= { pnniMapNodeEntry 14 }

pnniMapAddrTable OBJECT-TYPE
    SYNTAX SEQUENCE OF PnniMapAddrEntry
    ACCESS not-accessible
    STATUS mandatory
    DESCRIPTION
        "The pnniMapAddr MIB Object contains a list of all reachable
         addresses from each node visible to the local node.  The
         Local Node Index, Advertising Node ID, Advertised Port ID,
         Reachable Address, and Address prefix length are combined
         to form an instance ID for this object.  The entire object
         is read-only, reflecting the fact that reachable addresses
         are discovered during dynamic operation of the PNNI
         protocol rather than configured."
    ::= { pnniMIBObjects 16 }

pnniMapAddrEntry OBJECT-TYPE
    SYNTAX PnniMapAddrEntry
    ACCESS not-accessible
    STATUS mandatory
    DESCRIPTION
        "An entry in the table, containing information about an
         address prefix reachable from a node in the PNNI routing
         domain, as seen from the perspective of a PNNI logical node
         in this switching system."
    INDEX { pnniNodeIndex, pnniMapAddrAdvertisingNodeId, pnniMapAddrAdvertisedPortId, pnniMapAddrIndex }
    ::= { pnniMapAddrTable 1 }

PnniMapAddrEntry ::= SEQUENCE {
    pnniMapAddrAdvertisingNodeId PnniNodeId,
    pnniMapAddrAdvertisedPortId PnniPortId,
    pnniMapAddrIndex INTEGER,
    pnniMapAddrAddress AtmAddrPrefix,
    pnniMapAddrPrefixLength PnniPrefixLength
    }

pnniMapAddrAdvertisingNodeId OBJECT-TYPE
    SYNTAX PnniNodeId
--    Rsyntax OCTET STRING(SIZE(22))
    ACCESS read-only 
    STATUS mandatory
    DESCRIPTION
        "The node ID of a node advertising reachability to the
         address prefix."
    ::= { pnniMapAddrEntry 1 }

pnniMapAddrAdvertisedPortId OBJECT-TYPE
    SYNTAX PnniPortId
--    Rsyntax Gauge32
    ACCESS read-only 
    STATUS mandatory
    DESCRIPTION
        "The port identifier used from the advertising node to reach
         the given address prefix."
    ::= { pnniMapAddrEntry 2 }

pnniMapAddrIndex OBJECT-TYPE
    SYNTAX INTEGER(1..2147483647)
    ACCESS read-only 
    STATUS mandatory
    DESCRIPTION
        "An arbitrary index that is used to enumerate all of the
         addresses advertised by the specified node."
    ::= { pnniMapAddrEntry 3 }

pnniMapAddrAddress OBJECT-TYPE
    SYNTAX AtmAddrPrefix
--    Rsyntax OCTET STRING(SIZE(19))
    ACCESS read-only
    STATUS mandatory
    DESCRIPTION
        "The value of the ATM End System Address prefix."
    ::= { pnniMapAddrEntry 4 }

pnniMapAddrPrefixLength OBJECT-TYPE
    SYNTAX PnniPrefixLength
--    Rsyntax Integer32(0..152)
    ACCESS read-only
    STATUS mandatory
    DESCRIPTION
        "The Prefix length to be applied to the ATM End System
         Address prefix."
    ::= { pnniMapAddrEntry 5 }

pnniMapTnsTable OBJECT-TYPE
    SYNTAX SEQUENCE OF PnniMapTnsEntry
    ACCESS not-accessible
    STATUS mandatory
    DESCRIPTION
        "A list of all reachable transit networks from each node
         visible to the local node.  The Local Node Index,
         Advertising Node ID, Advertised Port ID, Transit Network
         Type, Transit Network Plan, and Transit Network ID are
         combined to form an instance ID for this object. The entire
         object is read-only, reflecting the fact that reachable
         transit networks are discovered during dynamic operation of
         the PNNI protocol rather than configured."
    ::= { pnniMIBObjects 17 }

pnniMapTnsEntry OBJECT-TYPE
    SYNTAX PnniMapTnsEntry
    ACCESS not-accessible
    STATUS mandatory
    DESCRIPTION
        "An entry in the table, containing information about a
         transit network reachable from a node in the PNNI routing
         domain, as seen from the perspective of a PNNI logical node
         in this switching system."
    INDEX { pnniNodeIndex, pnniMapTnsAdvertisingNodeId, pnniMapTnsAdvertisedPortId, pnniMapTnsType, pnniMapTnsPlan, pnniMapTnsId }
    ::= { pnniMapTnsTable 1 }

PnniMapTnsEntry ::= SEQUENCE {
    pnniMapTnsAdvertisingNodeId PnniNodeId,
    pnniMapTnsAdvertisedPortId PnniPortId,
    pnniMapTnsType TnsType,
    pnniMapTnsPlan TnsPlan,
    pnniMapTnsId DisplayString
    }

pnniMapTnsAdvertisingNodeId OBJECT-TYPE
    SYNTAX PnniNodeId
--    Rsyntax OCTET STRING(SIZE(22))
    ACCESS read-only 
    STATUS mandatory
    DESCRIPTION
        "The node ID of a node advertising reachability to the
         transit network."
    ::= { pnniMapTnsEntry 1 }

pnniMapTnsAdvertisedPortId OBJECT-TYPE
    SYNTAX PnniPortId
--    Rsyntax Gauge32
    ACCESS read-only 
    STATUS mandatory
    DESCRIPTION
        "The port identifier used from the advertising node to reach
         the given transit network."
    ::= { pnniMapTnsEntry 2 }

pnniMapTnsType OBJECT-TYPE
    SYNTAX TnsType
--    Rsyntax INTEGER {
--        nationalNetworkIdentification(2),
--        other(8)
--        }
    ACCESS read-only 
    STATUS mandatory
    DESCRIPTION
        "The type of network identification used for this transit
         network."
    ::= { pnniMapTnsEntry 3 }

pnniMapTnsPlan OBJECT-TYPE
    SYNTAX TnsPlan
--    Rsyntax INTEGER {
--        carrierIdentificationCode(1),
--        other(16)
--        }
    ACCESS read-only 
    STATUS mandatory
    DESCRIPTION
        "The network identification plan according to which network
         identification has been assigned."
    ::= { pnniMapTnsEntry 4 }

pnniMapTnsId OBJECT-TYPE
    SYNTAX DisplayString
--    Rsyntax OCTET STRING(SIZE(0..255))
    ACCESS read-only
    STATUS mandatory
    DESCRIPTION
        "The value of the transit network identifier."
    ::= { pnniMapTnsEntry 5 }

pnniMetricsTable OBJECT-TYPE
    SYNTAX SEQUENCE OF PnniMetricsEntry
    ACCESS not-accessible
    STATUS mandatory
    DESCRIPTION
        "This entity's table of PNNI parameters either associated
         with a PNNI entity or for the connectivity between a PNNI
         node and a reachable address or transit network."
    REFERENCE
        "ATM Forum PNNI 1.0 Section 5.8.1.1.3"
    ::= { pnniMIBObjects 18 }

pnniMetricsEntry OBJECT-TYPE
    SYNTAX PnniMetricsEntry
    ACCESS not-accessible
    STATUS mandatory
    DESCRIPTION
        "A set of parameters that applies to the connectivity from a
         certain node and port to another node or port or to one or
         more reachable address prefixes and/or transit networks,
         for one (or more) particular service category(s).  Note
         that there can be multiple sets of parameters with the same
         tag, in which case all sets apply to the specified
         connectivity."
    REFERENCE
        "ATM Forum PNNI 1.0 Section 5.8.1.1.3"
    INDEX { pnniNodeIndex, pnniMetricsTag, pnniMetricsDirection, pnniMetricsIndex }
    ::= { pnniMetricsTable 1 }

PnniMetricsEntry ::= SEQUENCE {
    pnniMetricsTag PnniMetricsTag,
    pnniMetricsDirection INTEGER,
    pnniMetricsIndex Integer32,
    pnniMetricsClasses INTEGER,
    pnniMetricsGcacClp ClpType,
    pnniMetricsAdminWeight INTEGER,
    pnniMetrics1 INTEGER,
    pnniMetrics2 INTEGER,
    pnniMetrics3 INTEGER,
    pnniMetrics4 INTEGER,
    pnniMetrics5 INTEGER,
    pnniMetrics6 INTEGER,
    pnniMetrics7 INTEGER,
    pnniMetrics8 INTEGER,
    pnniMetricsRowStatus RowStatus
    }

pnniMetricsTag OBJECT-TYPE
    SYNTAX PnniMetricsTag
--    Rsyntax Integer32(1..2147483647)
    ACCESS read-only
    STATUS mandatory
    DESCRIPTION
        "An arbitrary integer that is used to associate a set of
         traffic parameters that are always advertised together.
         Within this set, the parameters are distinguished by the
         service categories and direction to which a set of
         parameters apply."
    ::= { pnniMetricsEntry 1 }

pnniMetricsDirection OBJECT-TYPE
    SYNTAX INTEGER {
        incoming(1),
        outgoing(2)
        }
    ACCESS read-only 
    STATUS mandatory
    DESCRIPTION
        "The direction, with respect to the advertising node, in
         which the parameters in this entry apply."
    ::= { pnniMetricsEntry 2 }

pnniMetricsIndex OBJECT-TYPE
    SYNTAX Integer32(1..2147483647)
    ACCESS read-only 
    STATUS mandatory
    DESCRIPTION
        "An index into the set of parameters associated with the
         given tag and direction."
    ::= { pnniMetricsEntry 3 }

pnniMetricsClasses OBJECT-TYPE
    SYNTAX INTEGER(0..31)
    ACCESS read-write
    STATUS mandatory
    DESCRIPTION
        "The service categories to which this set of parameters
         applies.  This is an integer used as a bit mask with each
         bit that is set representing a single service category for
         which the resources indicated are available.  Bit 5
         represents CBR, bit 4 represents real-time VBR, bit 3
         represents non-real-time VBR, bit 2 represents ABR, and
         bit 1 (LSB) represents UBR."
    REFERENCE
        "ATM Forum Traffic Management 4.0 Section 2,
         ATM Forum PNNI 1.0 Section 5.8.1.1.3.1"
    ::= { pnniMetricsEntry 4 }

pnniMetricsGcacClp OBJECT-TYPE
    SYNTAX ClpType
--    Rsyntax INTEGER {
--        clpEqual0(1),
--        clpEqual0Or1(2)
--        }
    ACCESS read-write
    STATUS mandatory
    DESCRIPTION
        "Indicates whether the advertised GCAC parameters apply for
         CLP=0 traffic or for CLP=0+1 traffic."
    REFERENCE
        "ATM Forum PNNI 1.0 Sections 5.8.1.1.3.1, 5.13.4.1"
    ::= { pnniMetricsEntry 5 }

pnniMetricsAdminWeight OBJECT-TYPE
    SYNTAX INTEGER(1..16777215)
--    SYNTAX Unsigned32
--    Rsyntax Gauge32(1..16777215)
    ACCESS read-write
    STATUS mandatory
    DESCRIPTION
        "The administrative weight from the advertising node to the
         remote end of the PNNI entity or to the reachable address
         or transit network, for the specified service categories."
    REFERENCE
        "ATM Forum PNNI 1.0 Section 5.8.1.1.3.4"
    DEFVAL { 5040 }
    ::= { pnniMetricsEntry 6 }

pnniMetrics1 OBJECT-TYPE
    SYNTAX INTEGER(1..4294967295)
--    SYNTAX Unsigned32
--    Rsyntax Gauge32
    ACCESS read-write
    STATUS mandatory
    DESCRIPTION
        "An alternate routing parameter from the advertising node to
         the remote end of the PNNI entity or to the reachable
         address or transit network, for the specified service
         categories.
        
         For information learned from PNNI nodes, this is the
         maximum cell rate in cells per second for the specified
         service categories.
        
         If this parameter is not used, its value should be set to
         0xFFFFFFFF."
    REFERENCE
        "ATM Forum PNNI 1.0 Section 5.8.1.1.3.7"
    DEFVAL { 'FFFFFFFF'h }
    ::= { pnniMetricsEntry 7 }

pnniMetrics2 OBJECT-TYPE
    SYNTAX INTEGER(1..4294967295)
--    SYNTAX Unsigned32
--    Rsyntax Gauge32
    ACCESS read-write
    STATUS mandatory
    DESCRIPTION
        "An alternate routing parameter from the advertising node to
         the remote end of the PNNI entity or to the reachable
         address or transit network, for the specified service
         categories.
        
         For information learned from PNNI nodes, this is the
         available cell rate in cells per second for the specified
         service categories.
        
         If this parameter is not used, its value should be set to
         0xFFFFFFFF."
    REFERENCE
        "ATM Forum PNNI 1.0 Section 5.8.1.1.3.8"
    DEFVAL { 'FFFFFFFF'h }
    ::= { pnniMetricsEntry 8 }

pnniMetrics3 OBJECT-TYPE
    SYNTAX INTEGER(1..4294967295)
--    SYNTAX Unsigned32
--    Rsyntax Gauge32
    ACCESS read-write
    STATUS mandatory
    DESCRIPTION
        "An alternate routing parameter from the advertising node to
         the remote end of the PNNI entity or to the reachable
         address or transit network, for the specified service
         categories.
        
         For information learned from PNNI nodes, this is the
         maximum cell transfer delay in microseconds for the
         specified service categories.
        
         If this parameter is not used, its value should be set to
         0xFFFFFFFF."
    REFERENCE
        "ATM Forum PNNI 1.0 Section 5.8.1.1.3.3"
    DEFVAL { 'FFFFFFFF'h }
    ::= { pnniMetricsEntry 9 }

pnniMetrics4 OBJECT-TYPE
    SYNTAX INTEGER(1..4294967295)
--    SYNTAX Unsigned32
--    Rsyntax Gauge32
    ACCESS read-write
    STATUS mandatory
    DESCRIPTION
        "An alternate routing parameter from the advertising node to
         the remote end of the PNNI entity or to the reachable
         address or transit network, for the specified service
         categories.
        
         For information learned from PNNI nodes, this is the cell
         delay variation in microseconds for the specified service
         categories.
        
         If this parameter is not used, its value should be set to
         0xFFFFFFFF."
    REFERENCE
        "ATM Forum PNNI 1.0 Section 5.8.1.1.3.2"
    DEFVAL { 'FFFFFFFF'h }
    ::= { pnniMetricsEntry 10 }

pnniMetrics5 OBJECT-TYPE
    SYNTAX INTEGER(1..4294967295)
--    SYNTAX Unsigned32
--    Rsyntax Gauge32
    ACCESS read-write
    STATUS mandatory
    DESCRIPTION
        "An alternate routing parameter from the advertising node to
         the remote end of the PNNI entity or to the reachable
         address or transit network, for the specified service
         categories.
        
         For PNNI, this is the cell loss ratio for CLP=0 traffic for
         the specified service categories.  The cell loss ratio
         value is computed as 10**(-n) where 'n' is the value
         returned in this variable.
        
         If this parameter is not used, its value should be set to
         0xFFFFFFFF."
    REFERENCE
        "ATM Forum PNNI 1.0 Section 5.8.1.1.3.5"
    DEFVAL { 'FFFFFFFF'h }
    ::= { pnniMetricsEntry 11 }

pnniMetrics6 OBJECT-TYPE
    SYNTAX INTEGER(1..4294967295)
--    SYNTAX Unsigned32
--    Rsyntax Gauge32
    ACCESS read-write
    STATUS mandatory
    DESCRIPTION
        "An alternate routing parameter from the advertising node to
         the remote end of the PNNI entity or to the reachable
         address or transit network, for the specified service
         categories.
        
         For PNNI, this is the cell loss ratio for CLP=0+1 traffic
         for the specified service categories.  The cell loss ratio
         value is computed as 10**(-n) where 'n' is the value
         returned in this variable.
        
         If this parameter is not used, its value should be set to
         0xFFFFFFFF."
    REFERENCE
        "ATM Forum PNNI 1.0 Section 5.8.1.1.3.6"
    DEFVAL { 'FFFFFFFF'h }
    ::= { pnniMetricsEntry 12 }

pnniMetrics7 OBJECT-TYPE
    SYNTAX INTEGER(1..4294967295)
--    SYNTAX Unsigned32
--    Rsyntax Gauge32
    ACCESS read-write
    STATUS mandatory
    DESCRIPTION
        "An alternate routing parameter from the advertising node to
         the remote end of the PNNI entity or to the reachable
         address or transit network, for the specified service
         categories.
        
         For information learned from PNNI nodes, this is the cell
         rate margin in cells per second for the specified service
         categories.
        
         If this parameter is not used, its value should be set to
         0xFFFFFFFF."
    REFERENCE
        "ATM Forum PNNI 1.0 Section 5.8.1.1.3.9"
    DEFVAL { 'FFFFFFFF'h }
    ::= { pnniMetricsEntry 13 }

pnniMetrics8 OBJECT-TYPE
    SYNTAX INTEGER(1..4294967295)
--    SYNTAX Unsigned32
--    Rsyntax Gauge32
    ACCESS read-write
    STATUS mandatory
    DESCRIPTION
        "An alternate routing parameter from the advertising node to
         the remote end of the PNNI entity or to the reachable
         address or transit network, for the specified service
         categories.
        
         For information learned from PNNI nodes, this is the
         variance factor in units of 2**(-8) for the specified
         service categories.
        
         If this parameter is not used, its value should be set to
         0xFFFFFFFF."
    REFERENCE
        "ATM Forum PNNI 1.0 Section 5.8.1.1.3.10"
    DEFVAL { 'FFFFFFFF'h }
    ::= { pnniMetricsEntry 14 }

pnniMetricsRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "To create, delete, activate and de-activate a set of
         metrics."
    ::= { pnniMetricsEntry 15 }

pnniRouteNodeNumber OBJECT-TYPE
    SYNTAX Gauge32
    ACCESS read-only
    STATUS mandatory
    DESCRIPTION
        "The number of current precalculated PNNI routes to PNNI
         nodes that are not invalid."
    ::= { pnniRouteBaseGroup 1 }

pnniRouteAddrNumber OBJECT-TYPE
    SYNTAX Gauge32
    ACCESS read-only
    STATUS mandatory
    DESCRIPTION
        "The number of current PNNI routes from nodes in the PNNI
         routing domain to addresses and transit networks that are
         not invalid."
    ::= { pnniRouteBaseGroup 2 }

pnniRouteNodeTable OBJECT-TYPE
    SYNTAX SEQUENCE OF PnniRouteNodeEntry
    ACCESS not-accessible
    STATUS mandatory
    DESCRIPTION
        "This entity's PNNI Routing table (of routes to other
         nodes)."
    ::= { pnniRoutingGroup 2 }

pnniRouteNodeEntry OBJECT-TYPE
    SYNTAX PnniRouteNodeEntry
    ACCESS not-accessible
    STATUS mandatory
    DESCRIPTION
        "A particular route to a particular destination node, under
         a particular policy."
    INDEX { pnniNodeIndex, pnniRouteNodeClass, pnniRouteNodeDestNodeId, pnniRouteNodeDTL }
    ::= { pnniRouteNodeTable 1 }

PnniRouteNodeEntry ::= SEQUENCE {
    pnniRouteNodeClass ServiceCategory,
    pnniRouteNodeDestNodeId PnniNodeId,
    pnniRouteNodeDTL Integer32,
    pnniRouteNodeDestPortId PnniPortId,
    pnniRouteNodeProto INTEGER,
    pnniRouteNodeTimeStamp TimeStamp,
    pnniRouteNodeInfo OBJECT IDENTIFIER,
    pnniRouteNodeGcacClp ClpType,
    pnniRouteNodeFwdMetricAW INTEGER,
    pnniRouteNodeFwdMetric1 INTEGER,
    pnniRouteNodeFwdMetric2 INTEGER,
    pnniRouteNodeFwdMetric3 INTEGER,
    pnniRouteNodeFwdMetric4 INTEGER,
    pnniRouteNodeFwdMetric5 INTEGER,
    pnniRouteNodeFwdMetric6 INTEGER,
    pnniRouteNodeFwdMetric7 INTEGER,
    pnniRouteNodeFwdMetric8 INTEGER,
    pnniRouteNodeBwdMetricAW INTEGER,
    pnniRouteNodeBwdMetric1 INTEGER,
    pnniRouteNodeBwdMetric2 INTEGER,
    pnniRouteNodeBwdMetric3 INTEGER,
    pnniRouteNodeBwdMetric4 INTEGER,
    pnniRouteNodeBwdMetric5 INTEGER,
    pnniRouteNodeBwdMetric6 INTEGER,
    pnniRouteNodeBwdMetric7 INTEGER,
    pnniRouteNodeBwdMetric8 INTEGER,
    pnniRouteNodeVPCapability TruthValue,
    pnniRouteNodeStatus RowStatus
    }

pnniRouteNodeClass OBJECT-TYPE
    SYNTAX ServiceCategory
--    Rsyntax INTEGER {
--        other(1),
--        cbr(2),
--        rtVbr(3),
--        nrtVbr(4),
--        abr(5),
--        ubr(6)
--        }
    ACCESS read-only 
    STATUS mandatory
    DESCRIPTION
        "Indicates the service category with which this forwarding
         table entry is associated."
    ::= { pnniRouteNodeEntry 1 }

pnniRouteNodeDestNodeId OBJECT-TYPE
    SYNTAX PnniNodeId
--    Rsyntax OCTET STRING(SIZE(22))
    ACCESS read-only 
    STATUS mandatory
    DESCRIPTION
        "The node ID of the destination node to which this route
         proceeds, and at which the DTL stack for this route
         terminates."
    ::= { pnniRouteNodeEntry 2 }

pnniRouteNodeDTL OBJECT-TYPE
    SYNTAX Integer32(1..2147483647)
    ACCESS read-only 
    STATUS mandatory
    DESCRIPTION
        "The index into the owning PNNI node's DTL table of the DTL
         stack that goes with this route."
    ::= { pnniRouteNodeEntry 3 }

pnniRouteNodeDestPortId OBJECT-TYPE
    SYNTAX PnniPortId
--    Rsyntax Gauge32
    ACCESS read-write
    STATUS mandatory
    DESCRIPTION
        "The port ID of the destination node at which the route
         terminates.  A port ID of zero indicates the node nucleus.
         When the destination node is represented by the simple node
         representation, this value should be set to zero."
    DEFVAL { 0 }
    ::= { pnniRouteNodeEntry 4 }

pnniRouteNodeProto OBJECT-TYPE
    SYNTAX INTEGER {
        other(1),
        local(2),
        mgmt(3),
        pnni(4)
        }
    ACCESS read-only
    STATUS mandatory
    DESCRIPTION
        "The routing mechanism via which this route was learned."
    ::= { pnniRouteNodeEntry 5 }

pnniRouteNodeTimeStamp OBJECT-TYPE
    SYNTAX TimeStamp
--    Rsyntax TimeTicks
    ACCESS read-only
    STATUS mandatory
    DESCRIPTION
        "The time at which this  route  was last  updated  or
         otherwise  determined  to be correct.  Note that no
         semantics of  `too  old' can  be implied except through
         knowledge of the routing  protocol  by  which  the route
         was learned."
    ::= { pnniRouteNodeEntry 6 }

pnniRouteNodeInfo OBJECT-TYPE
    SYNTAX OBJECT IDENTIFIER
    ACCESS read-write
    STATUS mandatory
    DESCRIPTION
        "A reference to MIB definitions specific to the particular
         routing protocol which is responsible for this route, as
         determined by the value specified in the route's
         pnniRouteNodeProto value.  If this information is not
         present, its value should be set to the OBJECT IDENTIFIER
         null."
    DEFVAL { null }
    ::= { pnniRouteNodeEntry 7 }

pnniRouteNodeGcacClp OBJECT-TYPE
    SYNTAX ClpType
--    Rsyntax INTEGER {
--        clpEqual0(1),
--        clpEqual0Or1(2)
--        }
    ACCESS read-write
    STATUS mandatory
    DESCRIPTION
        "For PNNI, indicates whether any advertised GCAC parameters
         apply for CLP=0 traffic or for CLP=0+1 traffic."
    ::= { pnniRouteNodeEntry 8 }

pnniRouteNodeFwdMetricAW OBJECT-TYPE
    SYNTAX INTEGER (0..4294967295)
--    SYNTAX Unsigned32
--    Rsyntax Gauge32
    ACCESS read-write
    STATUS mandatory
    DESCRIPTION
        "The cumulative administrative weight calculated for the
         forward direction of this route.  If this metric is not
         used, its value should be set to 0xFFFFFFFF."
    REFERENCE
        "ATM Forum PNNI 1.0 Section 5.8.1.1.3.4"
    DEFVAL { 'FFFFFFFF'h }
    ::= { pnniRouteNodeEntry 9 }

pnniRouteNodeFwdMetric1 OBJECT-TYPE
    SYNTAX INTEGER (0..4294967295)
--    SYNTAX Unsigned32
--    Rsyntax Gauge32
    ACCESS read-write
    STATUS mandatory
    DESCRIPTION
        "An alternate routing parameter for the forward direction of
         this route.
        
         For information learned from PNNI nodes, this is the
         maximum possible cell rate (in cells per second) for the
         forward direction of the route.
        
         If this parameter is not used, its value should be set to
         0xFFFFFFFF."
    REFERENCE
        "ATM Forum PNNI 1.0 Section 5.8.1.1.3.7"
    DEFVAL { 'FFFFFFFF'h }
    ::= { pnniRouteNodeEntry 10 }

pnniRouteNodeFwdMetric2 OBJECT-TYPE
    SYNTAX INTEGER (0..4294967295)
--    SYNTAX Unsigned32
--    Rsyntax Gauge32
    ACCESS read-write
    STATUS mandatory
    DESCRIPTION
        "An alternate routing parameter for the forward direction of
         this route.
        
         For information learned from PNNI nodes, this is the
         Available cell rate (in cells per second) for the forward
         direction of the route.  Further information on available
         bandwidth may be obtainable by reference to the nodal
         advertisements of the nodes in the path.
        
         If this parameter is not used, its value should be set to
         0xFFFFFFFF."
    REFERENCE
        "ATM Forum PNNI 1.0 Section 5.8.1.1.3.8"
    DEFVAL { 'FFFFFFFF'h }
    ::= { pnniRouteNodeEntry 11 }

pnniRouteNodeFwdMetric3 OBJECT-TYPE
    SYNTAX INTEGER (0..4294967295)
--    SYNTAX Unsigned32
--    Rsyntax Gauge32
    ACCESS read-write
    STATUS mandatory
    DESCRIPTION
        "An alternate routing parameter for the forward direction of
         this route.
        
         For information learned from PNNI nodes, this is the
         cumulative Maximum Cell Transfer Delay (in microseconds)
         for the forward direction of the route.
        
         If this parameter is not used, its value should be set to
         0xFFFFFFFF."
    REFERENCE
        "ATM Forum PNNI 1.0 Section 5.8.1.1.3.3"
    DEFVAL { 'FFFFFFFF'h }
    ::= { pnniRouteNodeEntry 12 }

pnniRouteNodeFwdMetric4 OBJECT-TYPE
    SYNTAX INTEGER (0..4294967295)
--    SYNTAX Unsigned32
--    Rsyntax Gauge32
    ACCESS read-write
    STATUS mandatory
    DESCRIPTION
        "An alternate routing parameter for the forward direction of
         this route.
        
         For information learned from PNNI nodes, this is the
         cumulative Cell Delay Variation (in microseconds) for the
         forward direction of the route.
        
         If this parameter is not used, its value should be set to
         0xFFFFFFFF."
    REFERENCE
        "ATM Forum PNNI 1.0 Section 5.8.1.1.3.2"
    DEFVAL { 'FFFFFFFF'h }
    ::= { pnniRouteNodeEntry 13 }

pnniRouteNodeFwdMetric5 OBJECT-TYPE
    SYNTAX INTEGER (0..4294967295)
--    SYNTAX Unsigned32
--    Rsyntax Gauge32
    ACCESS read-write
    STATUS mandatory
    DESCRIPTION
        "An alternate routing parameter for the forward direction of
         this route.
        
         For information learned from PNNI nodes, this is the
         cumulative Cell Loss Ratio for CLP=0 traffic for the
         forward direction of the route. The cell loss ratio value
         is computed as 10**(-n) where 'n' is the value returned in
         this variable.
        
         If this parameter is not used, its value should be set to
         0xFFFFFFFF."
    REFERENCE
        "ATM Forum PNNI 1.0 Section 5.8.1.1.3.5"
    DEFVAL { 'FFFFFFFF'h }
    ::= { pnniRouteNodeEntry 14 }

pnniRouteNodeFwdMetric6 OBJECT-TYPE
    SYNTAX INTEGER (0..4294967295)
--    SYNTAX Unsigned32
--    Rsyntax Gauge32
    ACCESS read-write
    STATUS mandatory
    DESCRIPTION
        "An alternate routing parameter for the forward direction of
         this route.
        
         For information learned from PNNI nodes, this is the
         cumulative Cell Loss Ratio for CLP=0+1 traffic for the
         forward direction of the route. The cell loss ratio value
         is computed as 10**(-n) where 'n' is the value returned in
         this variable.
        
         If this parameter is not used, its value should be set to
         0xFFFFFFFF."
    REFERENCE
        "ATM Forum PNNI 1.0 Section 5.8.1.1.3.6"
    DEFVAL { 'FFFFFFFF'h }
    ::= { pnniRouteNodeEntry 15 }

pnniRouteNodeFwdMetric7 OBJECT-TYPE
    SYNTAX INTEGER (0..4294967295)
--    SYNTAX Unsigned32
--    Rsyntax Gauge32
    ACCESS read-write
    STATUS mandatory
    DESCRIPTION
        "An alternate routing parameter for the forward direction of
         this route.
        
         For information learned from PNNI nodes, this is the Cell
         Rate Margin (in cells per second) for the forward direction
         of the route.
        
         If this parameter is not used, its value should be set to
         0xFFFFFFFF."
    REFERENCE
        "ATM Forum PNNI 1.0 Section 5.8.1.1.3.9"
    DEFVAL { 'FFFFFFFF'h }
    ::= { pnniRouteNodeEntry 16 }

pnniRouteNodeFwdMetric8 OBJECT-TYPE
    SYNTAX INTEGER (0..4294967295)
--    SYNTAX Unsigned32
--    Rsyntax Gauge32
    ACCESS read-write
    STATUS mandatory
    DESCRIPTION
        "An alternate routing parameter for the forward direction of
         this route.
        
         For information learned from PNNI nodes, this is the
         Variance Factor (in units of 2**(-8)) for the forward
         direction of the route.
        
         If this parameter is not used, its value should be set to
         0xFFFFFFFF."
    REFERENCE
        "ATM Forum PNNI 1.0 Section 5.8.1.1.3.10"
    DEFVAL { 'FFFFFFFF'h }
    ::= { pnniRouteNodeEntry 17 }

pnniRouteNodeBwdMetricAW OBJECT-TYPE
    SYNTAX INTEGER (0..4294967295)
--    SYNTAX Unsigned32
--    Rsyntax Gauge32
    ACCESS read-write
    STATUS mandatory
    DESCRIPTION
        "The administrative weight calculated for the backward
         direction of this route.  If this metric is not used, its
         value should be set to 0xFFFFFFFF."
    REFERENCE
        "ATM Forum PNNI 1.0 Section 5.8.1.1.3.4"
    DEFVAL { 'FFFFFFFF'h }
    ::= { pnniRouteNodeEntry 18 }

pnniRouteNodeBwdMetric1 OBJECT-TYPE
    SYNTAX INTEGER (0..4294967295)
--    SYNTAX Unsigned32
--    Rsyntax Gauge32
    ACCESS read-write
    STATUS mandatory
    DESCRIPTION
        "An alternate routing parameter for the backward direction
         of this route.
        
         For information learned from PNNI nodes, this is the
         maximum possible cell rate (in cells per second) for the
         backward direction of the route.
        
         If this parameter is not used, its value should be set to
         0xFFFFFFFF."
    REFERENCE
        "ATM Forum PNNI 1.0 Section 5.8.1.1.3.7"
    DEFVAL { 'FFFFFFFF'h }
    ::= { pnniRouteNodeEntry 19 }

pnniRouteNodeBwdMetric2 OBJECT-TYPE
    SYNTAX INTEGER (0..4294967295)
--    SYNTAX Unsigned32
--    Rsyntax Gauge32
    ACCESS read-write
    STATUS mandatory
    DESCRIPTION
        "An alternate routing parameter for the backward direction
         of this route.
        
         For information learned from PNNI nodes, this is the
         Available cell rate (in cells per second) for the backward
         direction of the route.  Further information on available
         bandwidth may be obtainable by reference to the nodal
         advertisements of the nodes in the path.
        
         If this parameter is not used, its value should be set to
         0xFFFFFFFF."
    REFERENCE
        "ATM Forum PNNI 1.0 Section 5.8.1.1.3.8"
    DEFVAL { 'FFFFFFFF'h }
    ::= { pnniRouteNodeEntry 20 }

pnniRouteNodeBwdMetric3 OBJECT-TYPE
    SYNTAX INTEGER (0..4294967295)
--    SYNTAX Unsigned32
--    Rsyntax Gauge32
    ACCESS read-write
    STATUS mandatory
    DESCRIPTION
        "An alternate routing parameter for the backward direction
         of this route.
        
         For information learned from PNNI nodes, this is the
         cumulative Maximum Cell Transfer Delay (in microseconds)
         for the backward direction of the route.
        
         If this parameter is not used, its value should be set to
         0xFFFFFFFF."
    REFERENCE
        "ATM Forum PNNI 1.0 Section 5.8.1.1.3.3"
    DEFVAL { 'FFFFFFFF'h }
    ::= { pnniRouteNodeEntry 21 }

pnniRouteNodeBwdMetric4 OBJECT-TYPE
    SYNTAX INTEGER (0..4294967295)
--    SYNTAX Unsigned32
--    Rsyntax Gauge32
    ACCESS read-write
    STATUS mandatory
    DESCRIPTION
        "An alternate routing parameter for the backward direction
         of this route.
        
         For information learned from PNNI nodes, this is the
         cumulative Cell Delay Variation (in microseconds) for the
         backward direction of the route.
        
         If this parameter is not used, its value should be set to
         0xFFFFFFFF."
    REFERENCE
        "ATM Forum PNNI 1.0 Section 5.8.1.1.3.2"
    DEFVAL { 'FFFFFFFF'h }
    ::= { pnniRouteNodeEntry 22 }

pnniRouteNodeBwdMetric5 OBJECT-TYPE
    SYNTAX INTEGER (0..4294967295)
--    SYNTAX Unsigned32
--    Rsyntax Gauge32
    ACCESS read-write
    STATUS mandatory
    DESCRIPTION
        "An alternate routing parameter for the backward direction
         of this route.
        
         For information learned from PNNI nodes, this is the
         cumulative Cell Loss Ratio for CLP=0 traffic for the
         backward direction of the route. The cell loss ratio value
         is computed as 10**(-n) where 'n' is the value returned in
         this variable.
        
         If  this parameter is not used, its value should be set to
         0xFFFFFFFF."
    REFERENCE
        "ATM Forum PNNI 1.0 Section 5.8.1.1.3.5"
    DEFVAL { 'FFFFFFFF'h }
    ::= { pnniRouteNodeEntry 23 }

pnniRouteNodeBwdMetric6 OBJECT-TYPE
    SYNTAX INTEGER (0..4294967295)
--    SYNTAX Unsigned32
--    Rsyntax Gauge32
    ACCESS read-write
    STATUS mandatory
    DESCRIPTION
        "An alternate routing parameter for the backward direction
         of this route.
        
         For information learned from PNNI nodes, this is the
         cumulative Cell Loss Ratio for CLP=0+1 traffic for the
         backward direction of the route. The cell loss ratio value
         is computed as 10**(-n) where 'n' is the value returned in
         this variable.
        
         If  this parameter is not used, its value should be set to
         0xFFFFFFFF."
    REFERENCE
        "ATM Forum PNNI 1.0 Section 5.8.1.1.3.6"
    DEFVAL { 'FFFFFFFF'h }
    ::= { pnniRouteNodeEntry 24 }

pnniRouteNodeBwdMetric7 OBJECT-TYPE
    SYNTAX INTEGER (0..4294967295)
--    SYNTAX Unsigned32
--    Rsyntax Gauge32
    ACCESS read-write
    STATUS mandatory
    DESCRIPTION
        "An alternate routing parameter for the backward direction
         of this route.
        
         For information learned from PNNI nodes, this is the Cell
         Rate Margin (in cells per second) for the backward
         direction of the route.
        
         If this parameter is not used, its value should be set to
         0xFFFFFFFF."
    REFERENCE
        "ATM Forum PNNI 1.0 Section 5.8.1.1.3.9"
    DEFVAL { 'FFFFFFFF'h }
    ::= { pnniRouteNodeEntry 25 }

pnniRouteNodeBwdMetric8 OBJECT-TYPE
    SYNTAX INTEGER (0..4294967295)
--    SYNTAX Unsigned32
--    Rsyntax Gauge32
    ACCESS read-write
    STATUS mandatory
    DESCRIPTION
        "An alternate routing parameter for the backward direction
         of this route.
        
         For information learned from PNNI nodes, this is the
         Variance Factor (in units of 2**(-8)) for the backward
         direction of the route.
        
         If this parameter is not used, its value should be set to
         0xFFFFFFFF."
    REFERENCE
        "ATM Forum PNNI 1.0 Section 5.8.1.1.3.10"
    DEFVAL { 'FFFFFFFF'h }
    ::= { pnniRouteNodeEntry 26 }

pnniRouteNodeVPCapability OBJECT-TYPE
    SYNTAX TruthValue
--    Rsyntax INTEGER {
--        true(1),
--        false(2)
--        }
    ACCESS read-write
    STATUS mandatory
    DESCRIPTION
        "This attribute indicates whether a VPC setup on this route
         is possible."
    ::= { pnniRouteNodeEntry 27 }

pnniRouteNodeStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The row status variable, used according to row installation
         and removal conventions."
    ::= { pnniRouteNodeEntry 28 }

pnniDTLTable OBJECT-TYPE
    SYNTAX SEQUENCE OF PnniDTLEntry
    ACCESS not-accessible
    STATUS mandatory
    DESCRIPTION
        "The set of all DTL stacks used for the pre-computed routes
         maintained by this managed entity."
    ::= { pnniRoutingGroup 3 }

pnniDTLEntry OBJECT-TYPE
    SYNTAX PnniDTLEntry
    ACCESS not-accessible
    STATUS mandatory
    DESCRIPTION
        "A segment of a DTL stack.  The complete DTL stack is formed
         by traversing the rows of the table for which the
         pnniDTLIndex is the same.  Level transitions are indicated
         using the pnniDLTLinkType column."
    INDEX { pnniNodeIndex, pnniDTLIndex, pnniDTLEntryIndex }
    ::= { pnniDTLTable 1 }

PnniDTLEntry ::= SEQUENCE {
    pnniDTLIndex Integer32,
    pnniDTLEntryIndex Integer32,
    pnniDTLNodeId PnniNodeId,
    pnniDTLPortId PnniPortId,
    pnniDTLLinkType INTEGER,
    pnniDTLStatus RowStatus
    }

pnniDTLIndex OBJECT-TYPE
    SYNTAX Integer32(1..2147483647)
    ACCESS read-only 
    STATUS mandatory
    DESCRIPTION
        "The index in the node's DTL table of this DTL stack."
    ::= { pnniDTLEntry 1 }

pnniDTLEntryIndex OBJECT-TYPE
    SYNTAX Integer32(1..200)
    ACCESS read-only 
    STATUS mandatory
    DESCRIPTION
        "The index in the current DTL stack of this entry."
    ::= { pnniDTLEntry 2 }

pnniDTLNodeId OBJECT-TYPE
    SYNTAX PnniNodeId
--    Rsyntax OCTET STRING(SIZE(22))
    ACCESS read-write
    STATUS mandatory
    DESCRIPTION
        "The node which is this hop in the DTL stack."
    ::= { pnniDTLEntry 3 }

pnniDTLPortId OBJECT-TYPE
    SYNTAX PnniPortId
--    Rsyntax Gauge32
    ACCESS read-write
    STATUS mandatory
    DESCRIPTION
        "The port from the pnniDTLNodeId to use as the exit.  If the
         DTL stack does not care, this is coded as zero."
    ::= { pnniDTLEntry 4 }

pnniDTLLinkType OBJECT-TYPE
    SYNTAX INTEGER {
        invalid(1),
        horizontal(2),
        uplink(3),
        last(4)
        }
    ACCESS read-write
    STATUS mandatory
    DESCRIPTION
        "The type of link out from this node (pnniDTLNodeId).  This
         is well defined even if the specific port is not
         specified."
    ::= { pnniDTLEntry 5 }

pnniDTLStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The row status variable, used according to row installation
         and removal conventions."
    ::= { pnniDTLEntry 6 }

pnniRouteAddrTable OBJECT-TYPE
    SYNTAX SEQUENCE OF PnniRouteAddrEntry
    ACCESS not-accessible
    STATUS mandatory
    DESCRIPTION
        "A table containing all the attributes necessary to
         determine what the PNNI entity believes is reachable in
         terms of ATM End System Addresses and to determine which
         nodes are advertising this reachability.  This table is
         also used to configure static routes to reachable address
         prefixes.  The local node index that received the
         reachability information, reachable address, address prefix
         length, and an index that distinguishes between multiple
         listings of connectivity to a given address prefix from a
         given local node are combined to form an instance ID for
         this object."
    REFERENCE
        "ATM Forum PNNI 1.0 Section 5.8.1.3"
    ::= { pnniRoutingGroup 4 }

pnniRouteAddrEntry OBJECT-TYPE
    SYNTAX PnniRouteAddrEntry
    ACCESS not-accessible
    STATUS mandatory
    DESCRIPTION
        "An entry in the table, containing information about a
         reachable address prefix."
    REFERENCE
        "ATM Forum PNNI 1.0 Section 5.8.1.3"
    INDEX { pnniNodeIndex, pnniRouteAddrAddress, pnniRouteAddrPrefixLength, pnniRouteAddrIndex }
    ::= { pnniRouteAddrTable 1 }

PnniRouteAddrEntry ::= SEQUENCE {
    pnniRouteAddrAddress AtmAddrPrefix,
    pnniRouteAddrPrefixLength PnniPrefixLength,
    pnniRouteAddrIndex Integer32,
    pnniRouteAddrIfIndex InterfaceIndex,
    pnniRouteAddrAdvertisingNodeId PnniNodeId,
    pnniRouteAddrAdvertisedPortId PnniPortId,
    pnniRouteAddrType INTEGER,
    pnniRouteAddrProto INTEGER,
    pnniRouteAddrPnniScope PnniLevel,
    pnniRouteAddrVPCapability TruthValue,
    pnniRouteAddrMetricsTag PnniMetricsTag,
    pnniRouteAddrPtseId INTEGER,
    pnniRouteAddrOriginateAdvertisement TruthValue,
    pnniRouteAddrInfo OBJECT IDENTIFIER,
    pnniRouteAddrOperStatus INTEGER,
    pnniRouteAddrTimeStamp TimeStamp,
    pnniRouteAddrRowStatus RowStatus
    }

pnniRouteAddrAddress OBJECT-TYPE
    SYNTAX AtmAddrPrefix
--    Rsyntax OCTET STRING(SIZE(19))
    ACCESS read-only 
    STATUS mandatory
    DESCRIPTION
        "The value of the ATM End System Address prefix."
    ::= { pnniRouteAddrEntry 1 }

pnniRouteAddrPrefixLength OBJECT-TYPE
    SYNTAX PnniPrefixLength
--    Rsyntax Integer32(0..152)
    ACCESS read-only 
    STATUS mandatory
    DESCRIPTION
        "The prefix length to be applied to the ATM End System
         Address prefix."
    ::= { pnniRouteAddrEntry 2 }

pnniRouteAddrIndex OBJECT-TYPE
    SYNTAX Integer32(1..65535)
    ACCESS read-only 
    STATUS mandatory
    DESCRIPTION
        "An index into the set of listings of connectivity to a
         given address prefix from a given local node."
    ::= { pnniRouteAddrEntry 3 }

pnniRouteAddrIfIndex OBJECT-TYPE
    SYNTAX InterfaceIndex
--    Rsyntax Integer32
    ACCESS read-write
    STATUS mandatory
    DESCRIPTION
        "The local interface over which the reachable address can be
         reached.  The value zero indicates an unknown interface or
         reachability through a remote node.
        
         This object may only have a non-zero value if the value of
         the corresponding instance of pnniRouteAddrProto is other
         than 'pnni', pnniRouteAddrType is other than 'reject', and
         the node identified by pnniRouteAddrAdvertisingNodeId is
         instantiated within this switching system."
    ::= { pnniRouteAddrEntry 4 }

pnniRouteAddrAdvertisingNodeId OBJECT-TYPE
    SYNTAX PnniNodeId
--    Rsyntax OCTET STRING(SIZE(22))
    ACCESS read-write
    STATUS mandatory
    DESCRIPTION
        "The node ID of a node advertising reachability to the
         address prefix.  If the local node index is zero, then the
         advertising node ID must be set to all zeros."
    ::= { pnniRouteAddrEntry 5 }

pnniRouteAddrAdvertisedPortId OBJECT-TYPE
    SYNTAX PnniPortId
--    Rsyntax Gauge32
    ACCESS read-write
    STATUS mandatory
    DESCRIPTION
        "The port identifier used from the advertising node to reach
         the given address prefix."
    DEFVAL { 0 }
    ::= { pnniRouteAddrEntry 6 }

pnniRouteAddrType OBJECT-TYPE
    SYNTAX INTEGER {
        other(1),
        reject(2),
        internal(3),
        exterior(4)
        }
    ACCESS read-write
    STATUS mandatory
    DESCRIPTION
        "The type (e.g. internal or exterior) of reachability from
         the advertising node to the address prefix.
        
         Reject(2) refers to an address prefix which, if matched,
         indicates that the message should be discarded as
         unreachable. This is used in some protocols as a means of
         correctly aggregating routes."
    REFERENCE
        "ATM Forum PNNI 1.0 Section 5.8.1.3"
    DEFVAL { exterior }
    ::= { pnniRouteAddrEntry 7 }

pnniRouteAddrProto OBJECT-TYPE
    SYNTAX INTEGER {
        other(1),
        local(2),
        mgmt(3),
        pnni(4)
        }
    ACCESS read-only
    STATUS mandatory
    DESCRIPTION
        "The routing mechanism via which the connectivity from the
         advertising node to the reachable address prefix was
         learned."
    ::= { pnniRouteAddrEntry 8 }

pnniRouteAddrPnniScope OBJECT-TYPE
    SYNTAX PnniLevel
--    Rsyntax Integer32(0..104)
    ACCESS read-write
    STATUS mandatory
    DESCRIPTION
        "The PNNI scope of advertisement (i.e. level of PNNI
         hierarchy) of the reachability from the advertising node to
         the address prefix."
    REFERENCE
        "ATM Forum PNNI 1.0 Sections 5.3.6, 5.9.1"
    ::= { pnniRouteAddrEntry 9 }

pnniRouteAddrVPCapability OBJECT-TYPE
    SYNTAX TruthValue
--    Rsyntax INTEGER {
--        true(1),
--        false(2)
--        }
    ACCESS read-write
    STATUS mandatory
    DESCRIPTION
        "Indicates whether VPCs can be established from the
         advertising node to the reachable address prefix."
    REFERENCE
        "ATM Forum PNNI 1.0 Section 5.14.9.1 Table 5-34"
    ::= { pnniRouteAddrEntry 10 }

pnniRouteAddrMetricsTag OBJECT-TYPE
    SYNTAX PnniMetricsTag
--    Rsyntax Integer32(0..2147483647)
    ACCESS read-write
    STATUS mandatory
    DESCRIPTION
        "The index into the pnniMetricsTable for the traffic
         parameter values that apply for the connectivity from the
         advertising node to the reachable address prefix.  There
         will be one or more entries in the pnniMetricsTable whose
         first instance identifier matches the value of this
         variable.
        
         If there are no parameters associated with this reachable
         address prefix then the distinguished value zero is used."
    DEFVAL { 0 }
    ::= { pnniRouteAddrEntry 11 }

pnniRouteAddrPtseId OBJECT-TYPE
    SYNTAX INTEGER(0..4294967295)
--    Rsyntax Gauge32
    ACCESS read-only
    STATUS mandatory
    DESCRIPTION
        "For reachable addresses learned via PNNI, this attribute
         contains the value of the PTSE Identifier for the PTSE
         being originated by the originating node which contains the
         information group(s) describing the reachable address.  For
         reachable addresses learned by means other than PNNI, this
         attribute is set to zero."
    REFERENCE
        "ATM Forum PNNI 1.0 Section 5.8.2"
    ::= { pnniRouteAddrEntry 12 }

pnniRouteAddrOriginateAdvertisement OBJECT-TYPE
    SYNTAX TruthValue
--    Rsyntax INTEGER {
--        true(1),
--        false(2)
--        }
    ACCESS read-write
    STATUS mandatory
    DESCRIPTION
        "Whether or not the reachable address specified by this
         entry is to be advertised by the local node into its PNNI
         routing domain.
        
         This object may only take on the value 'true' when the
         value of the corresponding instance of pnniRouteAddrProto
         is other than 'pnni'."
    DEFVAL { true }
    ::= { pnniRouteAddrEntry 13 }

pnniRouteAddrInfo OBJECT-TYPE
    SYNTAX OBJECT IDENTIFIER
    ACCESS read-write
    STATUS mandatory
    DESCRIPTION
        "A reference to MIB definitions specific to the particular
         routing protocol which is responsible for this reachable
         address prefix, as determined by the value specified in the
         route's pnniRouteAddrProto value.  If this information is
         not present, its value should be set to the OBJECT
         IDENTIFIER null = zeroDotZero."
    DEFVAL { null }
    ::= { pnniRouteAddrEntry 14 }

pnniRouteAddrOperStatus OBJECT-TYPE
    SYNTAX INTEGER {
        inactive(1),
        active(2),
        advertised(3)
        }
    ACCESS read-only
    STATUS mandatory
    DESCRIPTION
        "Indicates whether the reachable address prefix is
         operationally valid and whether it is being advertised by
         this node."
    ::= { pnniRouteAddrEntry 15 }

pnniRouteAddrTimeStamp OBJECT-TYPE
    SYNTAX TimeStamp
--    Rsyntax TimeTicks
    ACCESS read-only
    STATUS mandatory
    DESCRIPTION
        "Indicates when the connectivity from the advertising node
         to the reachable address prefix became known to the local
         node."
    ::= { pnniRouteAddrEntry 16 }

pnniRouteAddrRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "To create, delete, activate and de-activate a reachable
         address prefix."
    ::= { pnniRouteAddrEntry 17 }

pnniRouteTnsTable OBJECT-TYPE
    SYNTAX SEQUENCE OF PnniRouteTnsEntry
    ACCESS not-accessible
    STATUS mandatory
    DESCRIPTION
        "A table containing all the attributes necessary to
         determine what transit networks the PNNI entity believes
         are reachable and to determine which nodes are advertising
         this reachability.  This table is also used to add static
         routes to reachable transit networks.  The local node index
         which received the reachability information, type of
         network identification, network identification plan,
         transit network identifier, and an index that distinguishes
         between multiple listings of connectivity to a given
         transit network from a given local node are combined to
         form an instance ID for this object."
    REFERENCE
        "ATM Forum PNNI 1.0 Section 5.8.1.3.2"
    ::= { pnniRoutingGroup 5 }

pnniRouteTnsEntry OBJECT-TYPE
    SYNTAX PnniRouteTnsEntry
    ACCESS not-accessible
    STATUS mandatory
    DESCRIPTION
        "An entry in the table, containing information about a
         reachable transit network."
    REFERENCE
        "ATM Forum PNNI 1.0 Section 5.8.1.3.2"
    INDEX { pnniNodeIndex, pnniRouteTnsType, pnniRouteTnsPlan, pnniRouteTnsId, pnniRouteTnsIndex }
    ::= { pnniRouteTnsTable 1 }

PnniRouteTnsEntry ::= SEQUENCE {
    pnniRouteTnsType TnsType,
    pnniRouteTnsPlan TnsPlan,
    pnniRouteTnsId DisplayString,
    pnniRouteTnsIndex Integer32,
    pnniRouteTnsIfIndex InterfaceIndex,
    pnniRouteTnsAdvertisingNodeId PnniNodeId,
    pnniRouteTnsAdvertisedPortId PnniPortId,
    pnniRouteTnsRouteType INTEGER,
    pnniRouteTnsProto INTEGER,
    pnniRouteTnsPnniScope PnniLevel,
    pnniRouteTnsVPCapability TruthValue,
    pnniRouteTnsMetricsTag PnniMetricsTag,
    pnniRouteTnsPtseId INTEGER,
    pnniRouteTnsOriginateAdvertisement TruthValue,
    pnniRouteTnsInfo OBJECT IDENTIFIER,
    pnniRouteTnsOperStatus INTEGER,
    pnniRouteTnsTimeStamp TimeStamp,
    pnniRouteTnsRowStatus RowStatus
    }

pnniRouteTnsType OBJECT-TYPE
    SYNTAX TnsType
--    Rsyntax INTEGER {
--        nationalNetworkIdentification(2),
--        other(8)
--        }
    ACCESS read-only 
    STATUS mandatory
    DESCRIPTION
        "The type of network identification used for this transit
         network."
    ::= { pnniRouteTnsEntry 1 }

pnniRouteTnsPlan OBJECT-TYPE
    SYNTAX TnsPlan
--    Rsyntax INTEGER {
--        carrierIdentificationCode(1),
--        other(16)
--        }
    ACCESS read-only 
    STATUS mandatory
    DESCRIPTION
        "The network identification plan according to which network
         identification has been assigned."
    ::= { pnniRouteTnsEntry 2 }

pnniRouteTnsId OBJECT-TYPE
    SYNTAX DisplayString
--    Rsyntax OCTET STRING(SIZE(0..255))
    ACCESS read-only 
    STATUS mandatory
    DESCRIPTION
        "The value of the transit network identifier."
    ::= { pnniRouteTnsEntry 3 }

pnniRouteTnsIndex OBJECT-TYPE
    SYNTAX Integer32(1..65535)
    ACCESS read-only
    STATUS mandatory
    DESCRIPTION
        "An index into the set of listings of connectivity to a
         given transit network from a given local node."
    ::= { pnniRouteTnsEntry 4 }

pnniRouteTnsIfIndex OBJECT-TYPE
    SYNTAX InterfaceIndex
--    Rsyntax Integer32
    ACCESS read-write
    STATUS mandatory
    DESCRIPTION
        "The local interface over which the transit network can be
         reached.  The value zero indicates an unknown interface or
         reachability through a remote node.
        
         This object may only have a non-zero value if the value of
         the corresponding instance of pnniRouteTnsProto is other
         than 'pnni' and the node identified by
         pnniRouteTnsAdvertisingNodeId is instantiated within this
         switching system."
    ::= { pnniRouteTnsEntry 5 }

pnniRouteTnsAdvertisingNodeId OBJECT-TYPE
    SYNTAX PnniNodeId
--    Rsyntax OCTET STRING(SIZE(22))
    ACCESS read-write
    STATUS mandatory
    DESCRIPTION
        "The node ID of a node advertising reachability to the
         transit network.  If the local node index is zero, then the
         advertising node ID must also be set to zero."
    ::= { pnniRouteTnsEntry 6 }

pnniRouteTnsAdvertisedPortId OBJECT-TYPE
    SYNTAX PnniPortId
--    Rsyntax Gauge32
    ACCESS read-write
    STATUS mandatory
    DESCRIPTION
        "The port identifier used from the advertising node to
         reach the given transit network."
    DEFVAL { 0 }
    ::= { pnniRouteTnsEntry 7 }

pnniRouteTnsRouteType OBJECT-TYPE
    SYNTAX INTEGER {
        other(1),
        exterior(4)
        }
    ACCESS read-write
    STATUS mandatory
    DESCRIPTION
        "The type (e.g. exterior or other) of reachability from the
         advertising node to the transit network."
    REFERENCE
        "ATM Forum PNNI 1.0 Section 5.8.1.3"
    DEFVAL { exterior }
    ::= { pnniRouteTnsEntry 8 }

pnniRouteTnsProto OBJECT-TYPE
    SYNTAX INTEGER {
        other(1),
        local(2),
        mgmt(3),
        pnni(4)
        }
    ACCESS read-only
    STATUS mandatory
    DESCRIPTION
        "The routing mechanism via which the connectivity from the
         advertising node to the transit network was learned."
    ::= { pnniRouteTnsEntry 9 }

pnniRouteTnsPnniScope OBJECT-TYPE
    SYNTAX PnniLevel
--    Rsyntax Integer32(0..104)
    ACCESS read-write
    STATUS mandatory
    DESCRIPTION
        "The PNNI scope of advertisement (i.e. level of PNNI
         hierarchy) of the reachability from the advertising node to
         the transit network."
    REFERENCE
        "ATM Forum PNNI 1.0 Section 5.3.6"
    ::= { pnniRouteTnsEntry 10 }

pnniRouteTnsVPCapability OBJECT-TYPE
    SYNTAX TruthValue
--    Rsyntax INTEGER {
--        true(1),
--        false(2)
--        }
    ACCESS read-write
    STATUS mandatory
    DESCRIPTION
        "Indicates whether VPCs can be established from the
         advertising node to the reachable transit network."
    REFERENCE
        "ATM Forum PNNI 1.0 Section 5.14.9.1 Table 5-34"
    ::= { pnniRouteTnsEntry 11 }

pnniRouteTnsMetricsTag OBJECT-TYPE
    SYNTAX PnniMetricsTag
--    Rsyntax Integer32(0..2147483647)
    ACCESS read-write
    STATUS mandatory
    DESCRIPTION
        "The index into the pnniMetricsTable for the traffic
         parameter values that apply for the connectivity from the
         advertising node to the transit network.  There will be one
         or more entries in the pnniMetricsTable whose first
         instance identifier matches the value of this variable.
        
         If there are no parameters associated with this transit
         network then the distinguished value zero is used."
    DEFVAL { 0 }
    ::= { pnniRouteTnsEntry 12 }

pnniRouteTnsPtseId OBJECT-TYPE
    SYNTAX INTEGER(0..4294967295)
--    Rsyntax Gauge32
    ACCESS read-only
    STATUS mandatory
    DESCRIPTION
        "For reachable transit networks learned via PNNI, this
         attribute contains the value of the PTSE Identifier for the
         PTSE being originated by the originating node which
         contains the information group(s) describing the transit
         network.  For reachable transit networks learned by means
         other than PNNI, this attribute is set to zero."
    REFERENCE
        "ATM Forum PNNI 1.0 Section 5.8.2"
    ::= { pnniRouteTnsEntry 13 }

pnniRouteTnsOriginateAdvertisement OBJECT-TYPE
    SYNTAX TruthValue
--    Rsyntax INTEGER {
--        true(1),
--        false(2)
--        }
    ACCESS read-write
    STATUS mandatory
    DESCRIPTION
        "Whether or not the transit network specified by this entry
         is to be advertised by the local node into its PNNI routing
         domain.
        
         This object may only take on the value 'true' when the
         value of the corresponding instance of pnniRouteNodeProto
         is other than 'pnni'."
    DEFVAL { true }
    ::= { pnniRouteTnsEntry 14 }

pnniRouteTnsInfo OBJECT-TYPE
    SYNTAX OBJECT IDENTIFIER
    ACCESS read-write
    STATUS mandatory
    DESCRIPTION
        "A reference to MIB definitions specific to the particular
         routing protocol which is responsible for this transit
         network, as determined by the value specified in the
         route's pnniRouteTnsProto value.  If this information is
         not present, its value should be set to the OBJECT
         IDENTIFIER null = zeroDotZero."
    DEFVAL { null }
    ::= { pnniRouteTnsEntry 15 }

pnniRouteTnsOperStatus OBJECT-TYPE
    SYNTAX INTEGER {
        inactive(1),
        active(2),
        advertised(3)
        }
    ACCESS read-only
    STATUS mandatory
    DESCRIPTION
        "Indicates whether the reachable transit network is
         operationally valid and whether it is being advertised by
         this node."
    ::= { pnniRouteTnsEntry 16 }

pnniRouteTnsTimeStamp OBJECT-TYPE
    SYNTAX TimeStamp
--    Rsyntax TimeTicks
    ACCESS read-only
    STATUS mandatory
    DESCRIPTION
        "Indicates how long the connectivity from the advertising
         node to the reachable transit network has been known to the
         local node."
    ::= { pnniRouteTnsEntry 17 }

pnniRouteTnsRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "To create, delete, activate and de-activate a reachable
         transit network."
    ::= { pnniRouteTnsEntry 18 }

pnniGeneralMinGroup OBJECT IDENTIFIER ::= { pnniMIBGroups 1 }
-- OBJECT-GROUP
--  Status
--    mandatory
--  Descr
--    A collection of general PNNI objects required for
--     management of a minimum function switching system.
--  objects
--    pnniHighestVersion, pnniLowestVersion, pnniDtlCountOriginator, 
--    pnniCrankbackCountOriginator, pnniAltRouteCountOriginator, 
--    pnniRouteFailCountOriginator, 
--    pnniRouteFailUnreachableOriginator

pnniGeneralBorderGroup OBJECT IDENTIFIER ::= { pnniMIBGroups 2 }
-- OBJECT-GROUP
--  Status
--    mandatory
--  Descr
--    A collection of general PNNI objects required for
--     management of a border node.
--  objects
--    pnniDtlCountBorder, pnniCrankbackCountBorder, 
--    pnniAltRouteCountBorder, pnniRouteFailCountBorder, 
--    pnniRouteFailUnreachableBorder

pnniNodeMinGroup OBJECT IDENTIFIER ::= { pnniMIBGroups 3 }
-- OBJECT-GROUP
--  Status
--    mandatory
--  Descr
--    A collection of per node PNNI objects required for
--     management of a minimum function switching system.
--  objects
--    pnniNodeLevel, pnniNodeId, pnniNodeLowest, 
--    pnniNodeAdminStatus, pnniNodeOperStatus, pnniNodeDomainName, 
--    pnniNodeAtmAddress, pnniNodePeerGroupId, 
--    pnniNodeRestrictedTransit, pnniNodeComplexRep, 
--    pnniNodeRestrictedBranching, pnniNodeDatabaseOverload, 
--    pnniNodePtses, pnniNodeRowStatus

pnniNodePglMinGroup OBJECT IDENTIFIER ::= { pnniMIBGroups 4 }
-- OBJECT-GROUP
--  Status
--    mandatory
--  Descr
--    A collection of per node PGL election related PNNI objects
--     required for management of a minimum function switching
--     system.
--  objects
--    pnniNodePglLeadershipPriority, pnniNodePglInitTime, 
--    pnniNodePglReelectTime, pnniNodePglState, 
--    pnniNodePreferredPgl, pnniNodePeerGroupLeader, 
--    pnniNodePglTimeStamp, pnniNodeActiveParentNodeId

pnniNodePglLgnGroup OBJECT IDENTIFIER ::= { pnniMIBGroups 5 }
-- OBJECT-GROUP
--  Status
--    mandatory
--  Descr
--    A collection of per node PGL election related PNNI objects
--     required for management of a PGL/LGN capable switching
--     system.
--  objects
--    pnniNodeCfgParentNodeIndex, pnniNodePglOverrideDelay

pnniNodeTimerMinGroup OBJECT IDENTIFIER ::= { pnniMIBGroups 6 }
-- OBJECT-GROUP
--  Status
--    mandatory
--  Descr
--    A collection of per node PNNI objects required for
--     management of timers and significant change thresholds in a
--     minimum function switching system.
--  objects
--    pnniNodePtseHolddown, pnniNodeHelloHolddown, 
--    pnniNodeHelloInterval, pnniNodeHelloInactivityFactor, 
--    pnniNodePtseRefreshInterval, pnniNodePtseLifetimeFactor, 
--    pnniNodeRxmtInterval, pnniNodePeerDelayedAckInterval, 
--    pnniNodeAvcrPm, pnniNodeAvcrMt, pnniNodeCdvPm, pnniNodeCtdPm

pnniNodeTimerLgnGroup OBJECT IDENTIFIER ::= { pnniMIBGroups 7 }
-- OBJECT-GROUP
--  Status
--    mandatory
--  Descr
--    A collection of per node PNNI objects required for
--     management of timers in a PGL/LGN capable switching
--     system.
--  objects
--    pnniNodeHlinkInact

pnniNodeSvccLgnGroup OBJECT IDENTIFIER ::= { pnniMIBGroups 8 }
-- OBJECT-GROUP
--  Status
--    mandatory
--  Descr
--    A collection of per node SVCC-based RCC related PNNI
--     objects required for management of a PGL/LGN capable
--     switching system.
--  objects
--    pnniNodeSvccInitTime, pnniNodeSvccRetryTime, 
--    pnniNodeSvccCallingIntegrityTime, 
--    pnniNodeSvccCalledIntegrityTime, 
--    pnniNodeSvccTrafficDescriptorIndex

pnniScopeMinGroup OBJECT IDENTIFIER ::= { pnniMIBGroups 9 }
-- OBJECT-GROUP
--  Status
--    mandatory
--  Descr
--    A collection of per node scope mapping related PNNI objects
--     required for management of a minimum function switching
--     system.
--  objects
--    pnniScopeLocalNetwork, pnniScopeLocalNetworkPlusOne, 
--    pnniScopeLocalNetworkPlusTwo, pnniScopeSiteMinusOne, 
--    pnniScopeIntraSite, pnniScopeSitePlusOne, 
--    pnniScopeOrganizationMinusOne, pnniScopeIntraOrganization, 
--    pnniScopeOrganizationPlusOne, pnniScopeCommunityMinusOne, 
--    pnniScopeIntraCommunity, pnniScopeCommunityPlusOne, 
--    pnniScopeRegional, pnniScopeInterRegional, pnniScopeGlobal

pnniSummaryLgnGroup OBJECT IDENTIFIER ::= { pnniMIBGroups 10 }
-- OBJECT-GROUP
--  Status
--    deprecated
--  Descr
--    A collection of PNNI objects required for controlling
--     address summarization.
--  objects
--    pnniSummaryType, pnniSummarySuppress, pnniSummaryState, 
--    pnniSummaryRowStatus

pnniSummaryAddressLgnGroup OBJECT IDENTIFIER ::= { pnniMIBGroups 31 }
-- OBJECT-GROUP
--  Status
--    mandatory
--  Descr
--    A collection of PNNI objects required for controlling address 
--    summarization.
--  objects
--    pnniSummaryAddressSuppress, pnniSummaryAddressState, 
--    pnniSummaryAddressRowStatus

pnniIfMinGroup OBJECT IDENTIFIER ::= { pnniMIBGroups 11 }
-- OBJECT-GROUP
--  Status
--    mandatory
--  Descr
--    A collection of per interface PNNI objects required for
--     management of a minimum function switching system.
--  objects
--    pnniIfNodeIndex, pnniIfPortId, pnniIfVPCapability, 
--    pnniIfAdmWeightCbr, pnniIfAdmWeightRtVbr, 
--    pnniIfAdmWeightNrtVbr, pnniIfAdmWeightAbr, pnniIfAdmWeightUbr, 
--    pnniIfRccServiceCategory, pnniIfRccTrafficDescrIndex

pnniIfBorderGroup OBJECT IDENTIFIER ::= { pnniMIBGroups 12 }
-- OBJECT-GROUP
--  Status
--    mandatory
--  Descr
--    A collection of per interface PNNI objects required for
--     management of a border node.
--  objects
--    pnniIfAggrToken

pnniLinkMinGroup OBJECT IDENTIFIER ::= { pnniMIBGroups 13 }
-- OBJECT-GROUP
--  Status
--    mandatory
--  Descr
--    A collection of per link PNNI objects required for
--     management of a minimum function switching system.
--  objects
--    pnniLinkType, pnniLinkVersion, pnniLinkHelloState, 
--    pnniLinkRemoteNodeId, pnniLinkRemotePortId, pnniLinkIfIndex, 
--    pnniLinkRcvHellos, pnniLinkXmtHellos

pnniLinkBorderOrLgnGroup OBJECT IDENTIFIER ::= { pnniMIBGroups 14 }
-- OBJECT-GROUP
--  Status
--    mandatory
--  Descr
--    A collection of per link PNNI objects required for
--     management of a border node or a PGL/LGN capable switching
--     system.
--  objects
--    pnniLinkDerivedAggrToken, pnniLinkUpnodeId, 
--    pnniLinkUpnodeAtmAddress, pnniLinkCommonPeerGroupId

pnniLinkLgnGroup OBJECT IDENTIFIER ::= { pnniMIBGroups 15 }
-- OBJECT-GROUP
--  Status
--    mandatory
--  Descr
--    A collection of per link PNNI objects required for
--     management of a PGL/LGN capable switching system.
--  objects
--    pnniLinkSvccRccIndex

pnniNbrPeerMinGroup OBJECT IDENTIFIER ::= { pnniMIBGroups 16 }
-- OBJECT-GROUP
--  Status
--    mandatory
--  Descr
--    A collection of per neighboring peer PNNI objects required
--     for management of a minimum function switching system.
--  objects
--    pnniNbrPeerState, pnniNbrPeerPortCount, pnniNbrPeerRcvDbSums, 
--    pnniNbrPeerXmtDbSums, pnniNbrPeerRcvPtsps, 
--    pnniNbrPeerXmtPtsps, pnniNbrPeerRcvPtseReqs, 
--    pnniNbrPeerXmtPtseReqs, pnniNbrPeerRcvPtseAcks, 
--    pnniNbrPeerXmtPtseAcks

pnniNbrPeerLgnGroup OBJECT IDENTIFIER ::= { pnniMIBGroups 17 }
-- OBJECT-GROUP
--  Status
--    mandatory
--  Descr
--    A collection of per neighboring peer PNNI objects required
--     for management of a PGL/LGN capable switching system.
--  objects
--    pnniNbrPeerSvccRccIndex

pnniNbrPeerPortMinGroup OBJECT IDENTIFIER ::= { pnniMIBGroups 18 }
-- OBJECT-GROUP
--  Status
--    mandatory
--  Descr
--    A collection of per port to neighboring peer PNNI objects
--     required for management of a minimum function switching
--     system.
--  objects
--    pnniNbrPeerPortFloodStatus

pnniSvccRccLgnGroup OBJECT IDENTIFIER ::= { pnniMIBGroups 19 }
-- OBJECT-GROUP
--  Status
--    mandatory
--  Descr
--    A collection of per SVCC-based RCC PNNI objects required
--     for management of a PGL/LGN capable switching system.
--  objects
--    pnniSvccRccVersion, pnniSvccRccHelloState, 
--    pnniSvccRccRemoteNodeId, pnniSvccRccRemoteAtmAddress, 
--    pnniSvccRccRcvHellos, pnniSvccRccXmtHellos, 
--    pnniSvccRccIfIndex, pnniSvccRccVpi, pnniSvccRccVci

pnniPtseOptionalGroup OBJECT IDENTIFIER ::= { pnniMIBGroups 20 }
-- OBJECT-GROUP
--  Status
--    mandatory
--  Descr
--    A collection of optional per PTSE PNNI objects.
--  objects
--    pnniPtseType, pnniPtseSequenceNum, pnniPtseChecksum, 
--    pnniPtseLifeTime, pnniPtseInfo

pnniMapOptionalGroup OBJECT IDENTIFIER ::= { pnniMIBGroups 21 }
-- OBJECT-GROUP
--  Status
--    mandatory
--  Descr
--    A collection of optional PNNI objects used to create a map
--     of nodes and links in the PNNI routing domain.
--  objects
--    pnniMapType, pnniMapPeerGroupId, pnniMapAggrToken, 
--    pnniMapRemoteNodeId, pnniMapRemotePortId, pnniMapVPCapability, 
--    pnniMapPtseId, pnniMapMetricsTag

pnniMapNodeOptionalGroup OBJECT IDENTIFIER ::= { pnniMIBGroups 22 }
-- OBJECT-GROUP
--  Status
--    mandatory
--  Descr
--    A collection of optional PNNI objects used to create a map
--     of nodes in the PNNI routing domain.
--  objects
--    pnniMapNodePeerGroupId, pnniMapNodeAtmAddress, 
--    pnniMapNodeRestrictedTransit, pnniMapNodeComplexRep, 
--    pnniMapNodeRestrictedBranching, pnniMapNodeDatabaseOverload, 
--    pnniMapNodeIAmLeader, pnniMapNodeLeadershipPriority, 
--    pnniMapNodePreferredPgl, pnniMapNodeParentNodeId, 
--    pnniMapNodeParentAtmAddress, pnniMapNodeParentPeerGroupId, 
--    pnniMapNodeParentPglNodeId

pnniMapAddrOptionalGroup OBJECT IDENTIFIER ::= { pnniMIBGroups 23 }
-- OBJECT-GROUP
--  Status
--    mandatory
--  Descr
--    A collection of optional PNNI objects used to create a map
--     of reachable addresses in the PNNI routing domain.
--  objects
--    pnniMapAddrAddress, pnniMapAddrPrefixLength

pnniMapTnsOptionalGroup OBJECT IDENTIFIER ::= { pnniMIBGroups 24 }
-- OBJECT-GROUP
--  Status
--    mandatory
--  Descr
--    A collection of optional PNNI objects used to create a map
--     of reachable transit networks in the PNNI routing domain.
--  objects
--    pnniMapTnsId

pnniMetricsOptionalGroup OBJECT IDENTIFIER ::= { pnniMIBGroups 25 }
-- OBJECT-GROUP
--  Status
--    mandatory
--  Descr
--    A collection of optional PNNI objects used to manage
--     metrics and attributes associated with PNNI entities.
--  objects
--    pnniMetricsClasses, pnniMetricsGcacClp, 
--    pnniMetricsAdminWeight, pnniMetrics1, pnniMetrics2, 
--    pnniMetrics3, pnniMetrics4, pnniMetrics5, pnniMetrics6, 
--    pnniMetrics7, pnniMetrics8, pnniMetricsRowStatus

pnniRouteGeneralOptionalGroup OBJECT IDENTIFIER ::= { pnniMIBGroups 26 }
-- OBJECT-GROUP
--  Status
--    mandatory
--  Descr
--    A collection of optional PNNI objects.
--  objects
--    pnniRouteNodeNumber, pnniRouteAddrNumber

pnniRouteNodeOptionalGroup OBJECT IDENTIFIER ::= { pnniMIBGroups 27 }
-- OBJECT-GROUP
--  Status
--    mandatory
--  Descr
--    A collection of optional PNNI objects used to manage
--     precalculated routes to nodes in the PNNI routing domain.
--  objects
--    pnniRouteNodeDestPortId, pnniRouteNodeProto, 
--    pnniRouteNodeTimeStamp, pnniRouteNodeInfo, 
--    pnniRouteNodeGcacClp, pnniRouteNodeFwdMetricAW, 
--    pnniRouteNodeFwdMetric1, pnniRouteNodeFwdMetric2, 
--    pnniRouteNodeFwdMetric3, pnniRouteNodeFwdMetric4, 
--    pnniRouteNodeFwdMetric5, pnniRouteNodeFwdMetric6, 
--    pnniRouteNodeFwdMetric7, pnniRouteNodeFwdMetric8, 
--    pnniRouteNodeBwdMetricAW, pnniRouteNodeBwdMetric1, 
--    pnniRouteNodeBwdMetric2, pnniRouteNodeBwdMetric3, 
--    pnniRouteNodeBwdMetric4, pnniRouteNodeBwdMetric5, 
--    pnniRouteNodeBwdMetric6, pnniRouteNodeBwdMetric7, 
--    pnniRouteNodeBwdMetric8, pnniRouteNodeVPCapability, 
--    pnniRouteNodeStatus

pnniDTLOptionalGroup OBJECT IDENTIFIER ::= { pnniMIBGroups 28 }
-- OBJECT-GROUP
--  Status
--    mandatory
--  Descr
--    A collection of optional PNNI objects used to manage
--     precalculated routes to nodes in the PNNI routing domain.
--  objects
--    pnniDTLNodeId, pnniDTLPortId, pnniDTLLinkType, pnniDTLStatus

pnniRouteAddrOptionalGroup OBJECT IDENTIFIER ::= { pnniMIBGroups 29 }
-- OBJECT-GROUP
--  Status
--    mandatory
--  Descr
--    A collection of optional PNNI objects used to manage routes
--     to reachable addresses in the PNNI routing domain.
--  objects
--    pnniRouteAddrIfIndex, pnniRouteAddrAdvertisingNodeId, 
--    pnniRouteAddrAdvertisedPortId, pnniRouteAddrType, 
--    pnniRouteAddrProto, pnniRouteAddrPnniScope, 
--    pnniRouteAddrVPCapability, pnniRouteAddrMetricsTag, 
--    pnniRouteAddrPtseId, pnniRouteAddrOriginateAdvertisement, 
--    pnniRouteAddrInfo, pnniRouteAddrOperStatus, 
--    pnniRouteAddrTimeStamp, pnniRouteAddrRowStatus

pnniRouteTnsOptionalGroup OBJECT IDENTIFIER ::= { pnniMIBGroups 30 }
-- OBJECT-GROUP
--  Status
--    mandatory
--  Descr
--    A collection of optional PNNI objects used to manage routes
--     to reachable transit networks in the PNNI routing domain.
--  objects
--    pnniRouteTnsIfIndex, pnniRouteTnsAdvertisingNodeId, 
--    pnniRouteTnsAdvertisedPortId, pnniRouteTnsRouteType, 
--    pnniRouteTnsProto, pnniRouteTnsPnniScope, 
--    pnniRouteTnsVPCapability, pnniRouteTnsMetricsTag, 
--    pnniRouteTnsPtseId, pnniRouteTnsOriginateAdvertisement, 
--    pnniRouteTnsInfo, pnniRouteTnsOperStatus, 
--    pnniRouteTnsTimeStamp, pnniRouteTnsRowStatus

pnniMIBCompliance OBJECT IDENTIFIER ::= { pnniMIBCompliances 1 }
-- MODULE-COMPLIANCE
--  Status
--    mandatory
--  Descr
--    The compliance statement for entities which implement
--     the PNNI MIB.
--    
--     Groups of PNNI objects required for management of a minimum
--     function node are identified by the suffix MinGroup.
--    
--     Groups of PNNI objects required for management of a border
--     node are identified by the suffix BorderGroup.
--    
--     Groups of PNNI objects required for management of a PGL/LGN
--     capable node are identified by the suffix LgnGroup.
--    
--     Groups of optional PNNI objects are identified by the
--     suffix OptionalGroup.
--  Module
--    >>current<<
--   MandGroup
--    pnniGeneralMinGroup
--   MandGroup
--    pnniNodeMinGroup
--   MandGroup
--    pnniNodePglMinGroup
--   MandGroup
--    pnniNodeTimerMinGroup
--   MandGroup
--    pnniScopeMinGroup
--   MandGroup
--    pnniIfMinGroup
--   MandGroup
--    pnniLinkMinGroup
--   MandGroup
--    pnniNbrPeerMinGroup
--   MandGroup
--    pnniNbrPeerPortMinGroup
--   ObjVar
--    pnniNodeId
--   ObjVar
--    pnniNodeLowest
--   ObjVar
--    pnniNodeRestrictedTransit
--   ObjVar
--    pnniNodeComplexRep
--   ObjVar
--    pnniNodeRowStatus
--   ObjVar
--    pnniNodePglLeadershipPriority
--   ObjVar
--    pnniIfNodeIndex
--   ObjVar
--    pnniIfVPCapability


END

MPOA-MIB DEFINITIONS ::= BEGIN

-- From file: "af-mpoa-0092_000.mi2"
-- Compile options "G P A"

IMPORTS
--  enterprises
--	    FROM RFC1155-SMI
    Counter32, Integer32, Counter64
            FROM SNMPv2-SMI-v1
    OBJECT-TYPE
            FROM RFC-1212
    MacAddress, TimeInterval, TimeStamp, TruthValue, RowStatus
            FROM SNMPv2-TC-v1
    lecIndex, atmForumNetworkManagement
            FROM LAN-EMULATION-CLIENT-MIB
    AtmAddr
            FROM ATM-TC-MIB;

-- mpoaMIB OBJECT IDENTIFIER ::= { atmfMpoa 1 }
-- MODULE-IDENTITY
--  LastUpdated
--    9805220000Z
--  OrgName
--    ATM Forum LANE/MPOA Working Group
--  ContactInfo
--    The ATM Forum
--    2570 West El Camino Real, Suite 304
--    Mountain View, CA  94040-1313
--    USA
--    
--    Tel: +1-650-949-6700
--    Fax: +1-650-949-6705
--    
--    Web: http://www.atmforum.com
--    E-mail: info@atmforum.com
--  Descr
--    This module defines a portion of the management
--    information base (MIB) for managing Multiprotocol Over
--    ATM clients and servers.
--  RevDate
--    9805220000Z
--  RevDescr
--    Final Ballot Version,  May 22, 1998
--    Version of the MIB module MPOA-MIB
--    that is in:  AF-MPOA-0092.000.
--  RevDate
--    9802250000Z
--  RevDescr
--    Straw Ballot Revision 1.0,  February 25, 1998
--    
--    
--    Version of the MIB module MPOA-MIB
--    that is in STR-MPOA-MIB-01.01.

--atmForum        OBJECT IDENTIFIER ::= { enterprises 353 }
--atmForumNetworkManagement OBJECT IDENTIFIER ::= { atmForum 5 }
atmfMpoa        OBJECT IDENTIFIER ::= { atmForumNetworkManagement 8 }
mpoaMIB OBJECT IDENTIFIER ::= { atmfMpoa 1 }
mpoaMIBObjects  OBJECT IDENTIFIER ::= { mpoaMIB 1 }
mpoaCommonObjects OBJECT IDENTIFIER ::= { mpoaMIBObjects 1 }
mpcObjects      OBJECT IDENTIFIER ::= { mpoaMIBObjects 2 }
mpsObjects      OBJECT IDENTIFIER ::= { mpoaMIBObjects 3 }
mpoaMIBConformance OBJECT IDENTIFIER ::= { mpoaMIB 2 }
mpoaMIBGroups   OBJECT IDENTIFIER ::= { mpoaMIBConformance 1 }
mpoaMIBCompliances OBJECT IDENTIFIER ::= { mpoaMIBConformance 2 }

LecIndex ::= INTEGER(1..2147483647)
-- TEXTUAL-CONVENTION
--  Status
--    mandatory
--  Descr
--    The value of this object identifies the LEC
--    for which the entry contains management
--    information.  The value of this object for
--    a particular LAN Emulation Client (LEC) has
--    the same value as the lecIndex object, defined
--    in the LAN-EMULATION-CLIENT MIB, for the same LEC.

AtmConfigAddr ::= OCTET STRING(SIZE(1..20))
-- TEXTUAL-CONVENTION
--  Status
--    mandatory
--  Descr
--    The ATM address used by the network entity.
--    The address types are: NSAP SEL Byte (1 octet)
--    E.164 (8 octets), and NSAP (20 octets).
--    Note: If the 1 octet NSAP SEL is given, the
--    other 19 octets of the NSAP are derived
--    from the system either through ILMI or another method.
--    Note: The E.164 address is encoded in BCD format.

InternetworkAddrType ::= INTEGER {
        other(0),
        ipV4(1),
        ipV6(2),
        nsap(3),
        hdlc(4),
        bbn1822(5),
        ieee802(6),
        e163(7),
        e164(8),
        f69(9),
        x121(10),
        ipx(11),
        appleTalk(12),
        decnetIV(13),
        banyanVines(14),
        e164WithNsap(15)
        }
-- TEXTUAL-CONVENTION
--  Status
--    mandatory
--  Descr
--    Internetwork Layer Address Types.
--    Values are defined in Assigned Numbers,
--    RFC1700. Note: not all of these values make sense in all
--    contexts where this type is used in this MIB, but they are
--    included for completeness.
--  Refer
--    Assigned Numbers, RFC1700, ADDRESS FAMILY NUMBERS

InternetworkAddr ::= OCTET STRING(SIZE(0..60))
-- TEXTUAL-CONVENTION
--  Status
--    mandatory
--  Descr
--    The value of an internetwork layer address.

MpcIndex ::= Integer32(1..2147483647)
-- TEXTUAL-CONVENTION
--  Status
--    mandatory
--  Descr
--    A unique value, for each MPOA client
--    which this SNMP agent manages.  It is recommended that
--    values
--    are assigned contiguously starting from 1.  The value for
--    each MPOA Client must remain constant, even if the MPOA
--    Client or SNMP agent is re-initialized.

MpsIndex ::= Integer32(1..2147483647)
-- TEXTUAL-CONVENTION
--  Status
--    mandatory
--  Descr
--    A unique value, for each MPOA Server
--    which this SNMP agent manages.  It is recommended that
--    values
--    
--    
--    are assigned contiguously starting from 1.  The value for
--    each MPOA Server must remain constant, even if the MPOA
--    Server or SNMP agent is re-initialized.

deviceTypeTable OBJECT-TYPE
    SYNTAX SEQUENCE OF DeviceTypeEntry
    ACCESS not-accessible
    STATUS mandatory
    DESCRIPTION
        "The device type table
        represents the mapping of the Lane Data ATM address
        to the MAC device capability.
        The unique key is the Lane data ATM address and Lec Index
        of the LEC associated with the MAC addresses.
        This table contains information which was
        gathered from its environment about neighboring
        machines.
        This Device type table represents the information of
        other/remote MPOA devices, discovered/gathered by each MPOA
        device. This MIB is not the device type of MPS/MPC
        itself; it is DISCOVERED information."
    REFERENCE
        "Sections:  5.2.3 Device Type TLV, and 4.2 Device Discovery,
        MPOA Version 1.0 (Letter Ballot) AF-MPOA-0087.000"
    ::= { mpoaCommonObjects 1 }

deviceTypeEntry OBJECT-TYPE
    SYNTAX DeviceTypeEntry
    ACCESS not-accessible
    STATUS mandatory
    DESCRIPTION
        "An entry in this table and corresponding entries in the
        deviceTypeMpsMacAddressTable represent a mapping of a MAC device
        capability (i.e. the set of MAC addresses from a device) to the
        LEC ATM Address."
    REFERENCE
        "Section 5.2.3 Device Type TLV
        MPOA Version 1.0 (Letter Ballot) AF-MPOA-0087.000"
    INDEX { deviceTypeIndex }
    ::= { deviceTypeTable 1 }

DeviceTypeEntry ::= SEQUENCE {
    deviceTypeIndex INTEGER,
    deviceTypeLecIndex LecIndex,
    deviceTypeRemoteLecAtmAddress AtmAddr,
    deviceTypeType INTEGER,
    deviceTypeMpsAtmAddress AtmAddr,
    deviceTypeMpcAtmAddress AtmAddr
    }

deviceTypeIndex OBJECT-TYPE
    SYNTAX INTEGER(1..2147483647)
--  ACCESS not-accessible
    ACCESS read-only
    STATUS mandatory
    DESCRIPTION
        "Index into this table and also used as one of the indices for
        the deviceTypeMpsMacAddressTable.  This index has local
        significance within the mpoaDeviceGroup.
        Entries in the `deviceTypeMpsMacAddressTable' which correspond
        to this index, and have the `deviceTypeType' value of `mps' or
        `mpsAndMps' are considered to be MPS MAC addresses."
    REFERENCE
        "Section 5.2.3 Device Type TLV
        MPOA Version 1.0 (Letter Ballot) AF-MPOA-0087.000"
    ::= { deviceTypeEntry 1 }

deviceTypeLecIndex OBJECT-TYPE
    SYNTAX LecIndex
--    Rsyntax INTEGER(1..2147483647)
    ACCESS read-only
    STATUS mandatory
    DESCRIPTION
        "LecIndex of LEC that supports this
        data ATM address"
    REFERENCE
        "Section 5.2.3 Device Type TLV
        MPOA Version 1.0 (Letter Ballot) AF-MPOA-0087.000"
    ::= { deviceTypeEntry 2 }

deviceTypeRemoteLecAtmAddress OBJECT-TYPE
    SYNTAX AtmAddr
--    Rsyntax OCTET STRING(SIZE(0..20))
    ACCESS read-only
    STATUS mandatory
    DESCRIPTION
        "The ATM address learned by LE ARP."
    REFERENCE
        "Section 5.2.3 Device Type TLV
        MPOA Version 1.0 (Letter Ballot) AF-MPOA-0087.000"
    ::= { deviceTypeEntry 3 }

deviceTypeType OBJECT-TYPE
    SYNTAX INTEGER {
        nonMpoa(1),
        mps(2),
        mpc(3),
        mpsAndMpc(4)
        }
    ACCESS read-only
    STATUS mandatory
    DESCRIPTION
        "same as the TLV"
    REFERENCE
        "Section 5.2.3 Device Type TLV
        MPOA Version 1.0 (Letter Ballot) AF-MPOA-0087.000"
    ::= { deviceTypeEntry 4 }

deviceTypeMpsAtmAddress OBJECT-TYPE
    SYNTAX AtmAddr
--    Rsyntax OCTET STRING(SIZE(0..20))
    ACCESS read-only
    STATUS mandatory
    DESCRIPTION
        "Associated MPS address, zeros for non-MPOA and mpc"
    REFERENCE
        "Section 5.2.3 Device Type TLV
        MPOA Version 1.0 (Letter Ballot) AF-MPOA-0087.000"
    ::= { deviceTypeEntry 5 }

deviceTypeMpcAtmAddress OBJECT-TYPE
    SYNTAX AtmAddr
--    Rsyntax OCTET STRING(SIZE(0..20))
    ACCESS read-only
    STATUS mandatory
    DESCRIPTION
        "Associated MPC address, zeros for non-MPOA & mps"
    REFERENCE
        "Section 5.2.3 Device Type TLV
        MPOA Version 1.0 (Letter Ballot) AF-MPOA-0087.000"
    ::= { deviceTypeEntry 6 }

deviceTypeMpsMacAddressTable OBJECT-TYPE
    SYNTAX SEQUENCE OF DeviceTypeMpsMacAddressEntry
    ACCESS not-accessible
    STATUS mandatory
    DESCRIPTION
        "This table contains MPS MAC Address information gathered from
        the MPOA DeviceTypeTLV."
    REFERENCE
        "Section 5.2.3 Device Type TLV
        MPOA Version 1.0 (Letter Ballot) AF-MPOA-0087.000"
    ::= { mpoaCommonObjects 2 }

deviceTypeMpsMacAddressEntry OBJECT-TYPE
    SYNTAX DeviceTypeMpsMacAddressEntry
    ACCESS not-accessible
    STATUS mandatory
    DESCRIPTION
        "Each entry represents an MPS MAC Address.  Each entry
        corresponds to a deviceTypeIndex value for which the
        deviceTypeType attribute is `mps' or `mpsAndMpc'."
    REFERENCE
        "Section 5.2.3 Device Type TLV
        MPOA Version 1.0 (Letter Ballot) AF-MPOA-0087.000"
    INDEX { deviceTypeIndex, deviceTypeMpsMacAddress }
    ::= { deviceTypeMpsMacAddressTable 1 }

DeviceTypeMpsMacAddressEntry ::= SEQUENCE {
    deviceTypeMpsMacAddress MacAddress
    }

deviceTypeMpsMacAddress OBJECT-TYPE
    SYNTAX MacAddress
--    Rsyntax OCTET STRING(SIZE(6))
    ACCESS read-only
    STATUS mandatory
    DESCRIPTION
        "MPS MAC address contained in the Device Type TLV which
        is identified by the deviceTypeIndex in the deviceTypeTable."
    REFERENCE
        "Section 5.2.3 Device Type TLV
        MPOA Version 1.0 (Letter Ballot) AF-MPOA-0087.000"
    ::= { deviceTypeMpsMacAddressEntry 1 }

mpcNextIndex OBJECT-TYPE
    SYNTAX Integer32(0..2147483647)
    ACCESS read-write
    STATUS mandatory
    DESCRIPTION
        "This object contains an appropriate value to
        be used for mpcIndex when creating entries in
        the mpcConfigTable.  The value 0 indicates that
        no new rows can be created.  Otherwise, it is
        recommended that values are assigned contiguously,
        starting from 1.
        
        MPC creation by a Manager:  To obtain the mpcIndex value
        for a new entry, the manager issues a management protocol
        retrieval operation to obtain the current value of this
        object.  If the value retrieved is 0 (zero), the manager
        cannot create a row.
        
        After each retrieval of a non-zero value, the manager
        should issue a management protocol SET operation using
        the value just retrieved.  If the SET is successful,
        the agent should update the value to the next unassigned
        index, or zero if appropriate.
        
        NOTE:  the manager may also issue a set on this object
        with a value of its own choosing.  If the set is successful,
        the manager may use this value for the mpcIndex. In this
        case, the agent would update the value to the next
        unassigned index, or zero if appropriate.
        The definition of `next unassigned index' is any
        mpcNextIndex value that has not yet been set by a manager,
        or reserved by the agent (see next paragraph), since this
        agent was last re-initialized.
        
        MPC creation by an Agent:  When a row in the
        mpcConfigTable is created by an agent, the agent should
        reserve the value of the index by updating the value of
        this object to the next unassigned index
        or zero if appropriate.  Thus, a manager will not
        be able to set an index reserved by an agent.
        
        In the situation of an agent re-initialization,  all currently
        used mpcIndexes must be preserved.
        In other words, the Agent should store in non-volatile memory
        all of the currently used mpcIndexes (along with all necessary
        configuration information from the mpcConfigTable).  When the
        agent is re-initialized, the mpcNextIndex value is
        any valid Integer32 value which is not being used
        as an mpcIndex, except 0 which maintains its original
        
        
        definition of indicating that a row cannot be created."
    ::= { mpcObjects 1 }

mpcConfigTable OBJECT-TYPE
    SYNTAX SEQUENCE OF MpcConfigEntry
    ACCESS not-accessible
    STATUS mandatory
    DESCRIPTION
        "The MPOA Client Configuration Table.
        This table contains configuration information
        for all MPOA Clients which this agent manages."
    ::= { mpcObjects 2 }

mpcConfigEntry OBJECT-TYPE
    SYNTAX MpcConfigEntry
    ACCESS not-accessible
    STATUS mandatory
    DESCRIPTION
        "MPOA Client Configuration Entry.
        Each entry contains configuration information
        for one MPOA Client.  The configuration information, including
        the mpcIndex, must be restored after a re-initialization of an
        MPC or a re-initialization of the SNMP agent."
    INDEX { mpcIndex }
    ::= { mpcConfigTable 1 }

MpcConfigEntry ::= SEQUENCE {
    mpcIndex MpcIndex,
    mpcRowStatus RowStatus,
    mpcConfigMode INTEGER,
    mpcCtrlAtmAddr AtmConfigAddr,
    mpcSCSetupFrameCount Integer32,
    mpcSCSetupFrameTime Integer32,
    mpcInitialRetryTime Integer32,
    mpcRetryTimeMaximum Integer32,
    mpcHoldDownTime Integer32
    }

mpcIndex OBJECT-TYPE
    SYNTAX MpcIndex
--    Rsyntax Integer32(1..2147483647)
--  ACCESS not-accessible
    ACCESS read-only
    STATUS mandatory
    DESCRIPTION
        "A value which uniquely identifies this conceptual
        row in the mpcConfigTable.  The `mpcNextIndex' object
        needs to be used to determine the value of this object.
        A row cannot be added, unless the mpcCtrlAtmAddress is unique.
        In the event of either an MPC re-initialization or an agent
        re-initialization, the value of this mpcIndex must remain the
        same.  In other words, the row needs to be saved and restored
        in the event of an MPC or SNMP Agent re-initialization."
    ::= { mpcConfigEntry 1 }

mpcRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows creation and deletion of
        MPOA Clients.
        
        Within each conceptual mpcConfigTable row, writable objects
        may be modified, regardless of the value of mpcRowStatus.
        It is not necessary to set a row's status to `notInService'
        first.
        
        A row cannot be created, unless the mpcAtmCtrlAddress
        in this table is unique.
        When an MPOA Client is created via this object,
        it will initially have
        `mpcActualState' = `initialState'"
    ::= { mpcConfigEntry 2 }

mpcConfigMode OBJECT-TYPE
    SYNTAX INTEGER {
        automatic(1),
        manual(2)
        }
    ACCESS read-write
    STATUS mandatory
    DESCRIPTION
        "Indicates whether this MPC should auto-configure
        the next time it is (re-)initialized.
        During the (re-)initialization of this MPC, if
        the mode is automatic(1), the LECS is contacted and
        
        
        requests are made for all MPC-p* parameters.
        Otherwise, if the mode is manual(2), the values of the
        configuration parameters are obtained from the
        mpcConfigTableand the mpcProtocolTable.  In other words, when
        the MPC is first initialized, it can use the default or
        configured values from the mpcConfigTable and
        mpcProtocolTable.  If the mode is manual (2), no further
        action is required.  If the mode is automatic (1), then
        the LECS should be contacted and all available MPC-p1
        to MPC-p6 parameters would be retrieved.
        These parameters would then overwrite the existing MPC-p1 to
        MPC-p6 parameters.  The actual values are reflected in the
        mpcActualTable."
    DEFVAL { automatic }
    ::= { mpcConfigEntry 3 }

mpcCtrlAtmAddr OBJECT-TYPE
    SYNTAX AtmConfigAddr
--    Rsyntax OCTET STRING(SIZE(1 | 8 | 20))
    ACCESS read-write
    STATUS mandatory
    DESCRIPTION
        "The MPC's Control ATM Address.  There exists one
        Control ATM Address per MPC, therefore, the value
        of this entry is unique within the table.  The control ATM
        Address is the address which is used by the MPC in its requests
        to the MPS.  The value of this object should not change, once
        created."
    ::= { mpcConfigEntry 4 }

mpcSCSetupFrameCount OBJECT-TYPE
    SYNTAX Integer32(1..65535)
    ACCESS read-write
    STATUS mandatory
    DESCRIPTION
        "This represents the MPC-p1 Short-cut setup frame count
        parameter.
        
        The MPC-p1 value is frames measured over mpcSCFrameTime seconds.
        Flow detection is protocol independent. i.e. all network layers
        mpcProtocolEntries for this MPC share the flow rate
        specification.
        A value of 1 causes all flows to initiate resolution/shortcut
        process."
    DEFVAL { 10 }
    ::= { mpcConfigEntry 5 }

mpcSCSetupFrameTime OBJECT-TYPE
    SYNTAX Integer32(1..60)
    ACCESS read-write
    STATUS mandatory
    DESCRIPTION
        "MPC-p2 Short-cut setup frame time, in seconds."
    DEFVAL { 1 }
    ::= { mpcConfigEntry 6 }

mpcInitialRetryTime OBJECT-TYPE
    SYNTAX Integer32(1..300)
    ACCESS read-write
    STATUS mandatory
    DESCRIPTION
        "MPC-p4 is the initial value for the retry time out
        period used for timing out MPOA Resolution Requests
        in seconds.  Retry time consists of this initial
        time-out (MPC-p4) and a retry multiplier (MPC-c1).
        If a response is not received, then another request
        is sent with a timeout of `retry time' * MPC-c1
        seconds, or until mpcRetryTimeMaximum."
    DEFVAL { 5 }
    ::= { mpcConfigEntry 7 }

mpcRetryTimeMaximum OBJECT-TYPE
    SYNTAX Integer32(10..300)
    ACCESS read-write
    STATUS mandatory
    DESCRIPTION
        "MPC-p5 cumulative max value for Retry Time (MPC-p4).
        Retries are attempted at intervals determined by the
        algorithm described in the definition of mpcIntialRetryTime."
    REFERENCE
        "Multiprotocol Over ATM.  AF-MPOA-0087.000.
        Section 4.3 MPOA Retry Mechanism"
    DEFVAL { 40 }
    ::= { mpcConfigEntry 8 }

mpcHoldDownTime OBJECT-TYPE
    SYNTAX Integer32(30..1200)
    ACCESS read-write
    STATUS mandatory
    DESCRIPTION
        "MPC-p6 Hold Down Time
        Minimum time to wait before reinitiating
        a failed resolution attempt.  Default is
        mpcRetryTimeMaximum * 4."
    REFERENCE
        "Multiprotocol Over ATM.  AF-MPOA-0087.000.
        Section 4.1.2.1 MPC Parameters"
    DEFVAL { 160 }
    ::= { mpcConfigEntry 9 }

mpcActualTable OBJECT-TYPE
    SYNTAX SEQUENCE OF MpcActualEntry
    ACCESS not-accessible
    STATUS mandatory
    DESCRIPTION
        "MPOA Client Actual Table.
        A read-only table which contains state
        information and reflects the actual values which
        these MPOA Clients are using.  The actual
        values may differ from the configured values.
        For example, the mpcConfigMode takes affect
        only during (re-)initialization of the MPC.
        The MPC-p1 to MPC-p6 parameters may differ
        from the configured values because, if the
        MPC was (re-)initialized and the mpcConfigMode
        was set to automatic (1) then some, perhaps all,
        of the MPC-p1 to MPC-p6 parameters were retrieved
        from the LECS and the values from the LECS may
        differ from the configured/default values of the
        mpcConfigTable.  NOTE:  after re-initialization
        a set to an object in the mpcConfigTable which
        changes the value of the object will be reflect
        in this Table, except for a set to the
        mpcConfigMode which takes effect only during
        re-initialization."
    ::= { mpcObjects 3 }

mpcActualEntry OBJECT-TYPE
    SYNTAX MpcActualEntry
    ACCESS not-accessible
    STATUS mandatory
    DESCRIPTION
        "An entry in the MPC Actual Table.
        An entry represents a specific MPOA Client's
        state information and the actual values
        which are being used by the MPOA Client.
        For example, the corresponding mpcConfigEntry contains
        default and/or configured parameters, if mpcConfigMode was
        
        
        set to manual, then these are the objects values' which are
        reflected for the mpcActualEntry.  However, if the
        mpcConfigMode is automatic, then the mpcActualEntry
        will be all the corresponding mpcConfigEntry's object,
        excluding any objects which were retrieved from the LECS.
        In other words, the objects retrieved from the LECS during
        the (re-)initialization of the MPC overwrite any of the default
        and/or configured values.
        NOTE:  any subsequent `set' to the configured values, e.g. an
        SNMP
        set operation, which is successful could result in a change to an
        mpcConfigTable value, and will be reflected in this table as
        well."
    INDEX { mpcIndex }
-- Augments mpcConfigEntry
    ::= { mpcActualTable 1 }

MpcActualEntry ::= SEQUENCE {
    mpcActualState INTEGER,
    mpcDiscontinuityTime TimeStamp,
    mpcActualConfigMode INTEGER,
    mpcActualSCSetupFrameCount Integer32,
    mpcActualSCSetupFrameTime Integer32,
    mpcActualInitialRetryTime Integer32,
    mpcActualRetryTimeMaximum Integer32,
    mpcActualHoldDownTime Integer32
    }

mpcActualState OBJECT-TYPE
    SYNTAX INTEGER {
        unknown(1),
        initialState(2),
        up(3),
        down(4)
        }
    ACCESS read-only
    STATUS mandatory
    DESCRIPTION
        "This object indicates the actual state
        of the MPOA Client."
    ::= { mpcActualEntry 1 }

mpcDiscontinuityTime OBJECT-TYPE
    SYNTAX TimeStamp
--    Rsyntax TimeTicks
    ACCESS read-only
    STATUS mandatory
    DESCRIPTION
        "The value of sysUpTime on the most recent occasion at
        which any one or more of this MPC's counters
        experienced a discontinuity.  The relevant counters
        are the specific instances associated with this
        MPC.  If discontinuities have not occurred since the
        last re-initialization of the local management subsystem,
        then this object contains a zero value."
    ::= { mpcActualEntry 2 }

mpcActualConfigMode OBJECT-TYPE
    SYNTAX INTEGER {
        automatic(1),
        manual(2)
        }
    ACCESS read-only
    STATUS mandatory
    DESCRIPTION
        "Indicates whether this MPC auto-configured
        when it was last (re-)initialized."
    ::= { mpcActualEntry 3 }

mpcActualSCSetupFrameCount OBJECT-TYPE
    SYNTAX Integer32(1..65535)
    ACCESS read-only
    STATUS mandatory
    DESCRIPTION
        "MPC-p1 Short-cut setup frame count.
        In frames measured over mpcShortcutFrameTime seconds.
        Flow detection is protocol independent. i.e. all
        network layers mpcProtocolEntry share the flow rate
        specification.
        A value of 1 implies that resolutions for short-cuts
        are attempted for all flows."
    ::= { mpcActualEntry 4 }

mpcActualSCSetupFrameTime OBJECT-TYPE
    SYNTAX Integer32(1..60)
    ACCESS read-only
    STATUS mandatory
    DESCRIPTION
        "Actual MPC-p2 Short-cut setup frame time, in seconds."
    ::= { mpcActualEntry 5 }

mpcActualInitialRetryTime OBJECT-TYPE
    SYNTAX Integer32(1..300)
    ACCESS read-only
    STATUS mandatory
    DESCRIPTION
        "Actual MPC-p4 is initial value for the
        retry time out."
    ::= { mpcActualEntry 6 }

mpcActualRetryTimeMaximum OBJECT-TYPE
    SYNTAX Integer32(30..300)
    ACCESS read-only
    STATUS mandatory
    DESCRIPTION
        "MPC-p5 cumulative maximum value for Retry Time (MPC-p4).
        Retries are attempted at intervals determined by the
        algorithm described in the definition of
        mpcActualInitialRetryTime."
    REFERENCE
        "Multiprotocol Over ATM.  AF-MPOA-0087.000.
        Section 4.3 MPOA Retry Mechanism"
    ::= { mpcActualEntry 7 }

mpcActualHoldDownTime OBJECT-TYPE
    SYNTAX Integer32(30..1200)
    ACCESS read-only
    STATUS mandatory
    DESCRIPTION
        "MPC-p6 Hold Down Time
        Minimum time to wait before reinitiating a failed
        resolution attempt.  The default value is
        mpcRetryTimeMaximum * 4."
    ::= { mpcActualEntry 8 }

mpcDataAtmAddressTable OBJECT-TYPE
    SYNTAX SEQUENCE OF MpcDataAtmAddressEntry
    ACCESS not-accessible
    STATUS mandatory
    DESCRIPTION
        "A table which shows all the data ATM addresses
        associated with  all MPOA Clients."
    ::= { mpcObjects 4 }

mpcDataAtmAddressEntry OBJECT-TYPE
    SYNTAX MpcDataAtmAddressEntry
    ACCESS not-accessible
    STATUS mandatory
    DESCRIPTION
        "Each row defines one data ATM address associated with
        an MPC.  NOTE:  if an MPC has more than one data ATM
        address then there will be another entry which contains
        the same mpcIndex subIdentifier, with a different
        mpcDataAtmAddress."
    INDEX { mpcIndex, mpcDataAtmAddress }
    ::= { mpcDataAtmAddressTable 1 }

MpcDataAtmAddressEntry ::= SEQUENCE {
    mpcDataAtmAddress AtmAddr,
    mpcDataAtmAddressRowStatus RowStatus
    }

mpcDataAtmAddress OBJECT-TYPE
    SYNTAX AtmAddr
--    Rsyntax OCTET STRING(SIZE(0..20))
--  ACCESS not-accessible
    ACCESS read-only
    STATUS mandatory
    DESCRIPTION
        "A data ATM Address which is associated with
        an MPOA Client specified by the mpcIndex."
    ::= { mpcDataAtmAddressEntry 1 }

mpcDataAtmAddressRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows creation and deletion of
        an MPOA Client's Data ATM Addresses.  The
        row can be created/deleted by either an NMS
        or by the SNMP agent."
    ::= { mpcDataAtmAddressEntry 2 }

mpcStatisticsTable OBJECT-TYPE
    SYNTAX SEQUENCE OF MpcStatisticsEntry
    ACCESS not-accessible
    STATUS mandatory
    DESCRIPTION
        "A read-only table which contains statistical
        information for all MPOA Clients that
        this agent manages."
    ::= { mpcObjects 5 }

mpcStatisticsEntry OBJECT-TYPE
    SYNTAX MpcStatisticsEntry
    ACCESS not-accessible
    STATUS mandatory
    DESCRIPTION
        "Each row in this table contains statistics
        for one MPOA Client."
    INDEX { mpcIndex }
-- Augments mpcConfigEntry
    ::= { mpcStatisticsTable 1 }

MpcStatisticsEntry ::= SEQUENCE {
    mpcStatTxMpoaResolveRequests Counter32,
    mpcStatRxMpoaResolveReplyAcks Counter32,
    mpcStatRxMpoaResolveReplyInsufECResources Counter32,
    mpcStatRxMpoaResolveReplyInsufSCResources Counter32,
    mpcStatRxMpoaResolveReplyInsufEitherResources Counter32,
    mpcStatRxMpoaResolveReplyUnsupportedInetProt Counter32,
    mpcStatRxMpoaResolveReplyUnsupportedMacEncaps Counter32,
    mpcStatRxMpoaResolveReplyUnspecifiedOther Counter32,
    mpcStatRxMpoaImpRequests Counter32,
    mpcStatTxMpoaImpReplyAcks Counter32,
    mpcStatTxMpoaImpReplyInsufECResources Counter32,
    mpcStatTxMpoaImpReplyInsufSCResources Counter32,
    mpcStatTxMpoaImpReplyInsufEitherResources Counter32,
    mpcStatTxMpoaImpReplyUnsupportedInetProt Counter32,
    mpcStatTxMpoaImpReplyUnsupportedMacEncaps Counter32,
    mpcStatTxMpoaImpReplyUnspecifiedOther Counter32,
    mpcStatTxMpoaEgressCachePurgeRequests Counter32,
    mpcStatRxMpoaEgressCachePurgeReplies Counter32,
    mpcStatRxMpoaKeepAlives Counter32,
    mpcStatRxMpoaTriggers Counter32,
    mpcStatRxMpoaDataPlanePurges Counter32,
    mpcStatTxMpoaDataPlanePurges Counter32,
    mpcStatRxNhrpPurgeRequests Counter32,
    mpcStatTxNhrpPurgeReplies Counter32,
    mpcStatRxErrUnrecognizedExtensions Counter32,
    mpcStatRxErrLoopDetecteds Counter32,
    mpcStatRxErrProtoAddrUnreachables Counter32,
    mpcStatRxErrProtoErrors Counter32,
    mpcStatRxErrSduSizeExceededs Counter32,
    mpcStatRxErrInvalidExtensions Counter32,
    mpcStatRxErrInvalidReplies Counter32,
    mpcStatRxErrAuthenticationFailures Counter32,
    mpcStatRxErrHopCountExceededs Counter32
    }

mpcStatTxMpoaResolveRequests OBJECT-TYPE
    SYNTAX Counter32
    ACCESS read-only
    STATUS mandatory
    DESCRIPTION
        "The number of MPOA Resolve Requests transmitted
        by this MPC.
        
        Discontinuities in the value of this counter can occur
        at re-initialization of the management system, and/or
        re-initialization of the MPC, and at other times,
        as indicated by the value of mpcDiscontinuityTime."
    ::= { mpcStatisticsEntry 1 }

mpcStatRxMpoaResolveReplyAcks OBJECT-TYPE
    SYNTAX Counter32
    ACCESS read-only
    STATUS mandatory
    DESCRIPTION
        "The number of positively acknowledged MPC
        Resolved Replies received by this MPC with an MPOA
        CIE Code of 0x00 (Success).
        Discontinuities in the value of this counter can occur at
        re-initialization of the management system, and/or re-
        initialization
        of the MPC, and at other times, as indicated by the value of
        mpcDiscontinuityTime."
    REFERENCE
        "Multiprotocol Over ATM.  AF-MPOA-0087.000.  Page 62."
    ::= { mpcStatisticsEntry 2 }

mpcStatRxMpoaResolveReplyInsufECResources OBJECT-TYPE
    SYNTAX Counter32
    ACCESS read-only
    STATUS mandatory
    DESCRIPTION
        "The number of MPOA Resolution Replies received with
        an MPOA CIE Code of 0x81, `Insufficient resources to
        accept egress cache entry'.
        Discontinuities in the value of this counter can occur
        at re-initialization of the management system, and/or
        re-initialization of the MPC, and at other times,
        as indicated by the value of mpcDiscontinuityTime."
    REFERENCE
        "Multiprotocol Over ATM.  AF-MPOA-0087.000.  Page 62."
    ::= { mpcStatisticsEntry 3 }

mpcStatRxMpoaResolveReplyInsufSCResources OBJECT-TYPE
    SYNTAX Counter32
    ACCESS read-only
    STATUS mandatory
    DESCRIPTION
        "The number of MPOA Resolution Replies received with
        an MPOA CIE Code of 0x82, `Insufficient resources to
        accept the shortcut'.
        Discontinuities in the value of this counter can occur
        at re-initialization of the management system, and/or
        re-initialization of the MPC, and at other times,
        as indicated by the value of mpcDiscontinuityTime."
    REFERENCE
        "Multiprotocol Over ATM.  AF-MPOA-0087.000.  Page 62."
    ::= { mpcStatisticsEntry 4 }

mpcStatRxMpoaResolveReplyInsufEitherResources OBJECT-TYPE
    SYNTAX Counter32
    ACCESS read-only
    STATUS mandatory
    DESCRIPTION
        "The number of MPOA Resolution Replies received with
        an MPOA CIE Code of 0x83, `Insufficient resources to
        accept either shortcut or egress cache entry'.
        Discontinuities in the value of this counter can occur
        at re-initialization of the management system, and/or
        re-initialization of the MPC, and at other times,
        as indicated by the value of mpcDiscontinuityTime."
    REFERENCE
        "Multiprotocol Over ATM.  AF-MPOA-0087.000.  Page 62."
    ::= { mpcStatisticsEntry 5 }

mpcStatRxMpoaResolveReplyUnsupportedInetProt OBJECT-TYPE
    SYNTAX Counter32
    ACCESS read-only
    STATUS mandatory
    DESCRIPTION
        "The number of MPOA Resolution Replies received with
        an MPOA CIE Code of 0x84, `Unsupported Internework
        Layer protocol'.
        Discontinuities in the value of this counter can occur
        at re-initialization of the management system, and/or
        re-initialization of the MPC, and at other times,
        as indicated by the value of mpcDiscontinuityTime."
    REFERENCE
        "Multiprotocol Over ATM.  AF-MPOA-0087.000.  Page 62."
    ::= { mpcStatisticsEntry 6 }

mpcStatRxMpoaResolveReplyUnsupportedMacEncaps OBJECT-TYPE
    SYNTAX Counter32
    ACCESS read-only
    STATUS mandatory
    DESCRIPTION
        "The number of MPOA Resolution Replies received with
        an MPOA CIE Code of 0x85, `Unsupported MAC layer encapsulation'.
        Discontinuities in the value of this counter can occur
        at re-initialization of the management system, and/or
        re-initialization of the MPC, and at other times,
        as indicated by the value of mpcDiscontinuityTime."
    REFERENCE
        "Multiprotocol Over ATM.  AF-MPOA-0087.000.  Page 62."
    ::= { mpcStatisticsEntry 7 }

mpcStatRxMpoaResolveReplyUnspecifiedOther OBJECT-TYPE
    SYNTAX Counter32
    ACCESS read-only
    STATUS mandatory
    DESCRIPTION
        "The number of MPOA Resolution Replies received with
        an MPOA CIE Code of 0x88, `Unspecified/Other'.
        Discontinuities in the value of this counter can occur
        at re-initialization of the management system, and/or
        re-initialization of the MPC, and at other times,
        as indicated by the value of mpcDiscontinuityTime."
    REFERENCE
        "Multiprotocol Over ATM.  AF-MPOA-0087.000.  Page 62."
    ::= { mpcStatisticsEntry 8 }

mpcStatRxMpoaImpRequests OBJECT-TYPE
    SYNTAX Counter32
    ACCESS read-only
    STATUS mandatory
    DESCRIPTION
        "The number of MPOA Cache Imposition Requests received
        by this MPC.
        Discontinuities in the value of this counter can occur at re-
        initialization
        of the management system, and/or re-initialization of the MPC,
        and at
        other times, as indicated by the value of mpcDiscontinuityTime."
    ::= { mpcStatisticsEntry 9 }

mpcStatTxMpoaImpReplyAcks OBJECT-TYPE
    SYNTAX Counter32
    ACCESS read-only
    STATUS mandatory
    DESCRIPTION
        "The number of successful MPOA Cache Imposition replies
        transmitted by this MPC with an MPOA CIE Code of 0x00
        `Success'.
        Discontinuities in the value of this counter can occur at re-
        initialization
        of the management system, and/or re-initialization of the MPC,
        and at
        other times, as indicated by the value of mpcDiscontinuityTime."
    REFERENCE
        "Multiprotocol Over ATM.  AF-MPOA-0087.000.  Page 62."
    ::= { mpcStatisticsEntry 10 }

mpcStatTxMpoaImpReplyInsufECResources OBJECT-TYPE
    SYNTAX Counter32
    ACCESS read-only
    STATUS mandatory
    DESCRIPTION
        "The number of MPOA Cache Imposition Replies transmitted with
        an MPOA CIE Code of 0x81, `Insufficient resources to
        accept egress cache entry'.
        Discontinuities in the value of this counter can occur
        at re-initialization of the management system, and/or
        re-initialization of the MPC, and at other times,
        as indicated by the value of mpcDiscontinuityTime."
    REFERENCE
        "Multiprotocol Over ATM.  AF-MPOA-0087.000.  Page 62."
    ::= { mpcStatisticsEntry 11 }

mpcStatTxMpoaImpReplyInsufSCResources OBJECT-TYPE
    SYNTAX Counter32
    ACCESS read-only
    STATUS mandatory
    DESCRIPTION
        "The number of MPOA Imposition Replies transmitted with
        an MPOA CIE Code of 0x82, `Insufficient resources to
        accept shortcut'.
        Discontinuities in the value of this counter can occur
        at re-initialization of the management system, and/or
        re-initialization of the MPC, and at other times,
        as indicated by the value of mpcDiscontinuityTime."
    REFERENCE
        "Multiprotocol Over ATM.  AF-MPOA-0087.000.  Page 62."
    ::= { mpcStatisticsEntry 12 }

mpcStatTxMpoaImpReplyInsufEitherResources OBJECT-TYPE
    SYNTAX Counter32
    ACCESS read-only
    STATUS mandatory
    DESCRIPTION
        "The number of MPOA Imposition Replies transmitted with
        an MPOA CIE Code of 0x83, `Insufficient resources to
        accept either shortcut or egress cache entry'.
        Discontinuities in the value of this counter can occur
        at re-initialization of the management system, and/or
        re-initialization of the MPC, and at other times,
        as indicated by the value of mpcDiscontinuityTime."
    REFERENCE
        "Multiprotocol Over ATM.  AF-MPOA-0087.000.  Page 62."
    ::= { mpcStatisticsEntry 13 }

mpcStatTxMpoaImpReplyUnsupportedInetProt OBJECT-TYPE
    SYNTAX Counter32
    ACCESS read-only
    STATUS mandatory
    DESCRIPTION
        "The number of MPOA Imposition Replies transmitted with
        an MPOA CIE Code of 0x84, `Unsupported Internetwork Layer
        protocol'.
        Discontinuities in the value of this counter can occur
        at re-initialization of the management system, and/or
        re-initialization of the MPC, and at other times,
        as indicated by the value of mpcDiscontinuityTime."
    REFERENCE
        "Multiprotocol Over ATM.  AF-MPOA-0087.000.  Page 62."
    ::= { mpcStatisticsEntry 14 }

mpcStatTxMpoaImpReplyUnsupportedMacEncaps OBJECT-TYPE
    SYNTAX Counter32
    ACCESS read-only
    STATUS mandatory
    DESCRIPTION
        "The number of MPOA Imposition Replies transmitted with
        an MPOA CIE Code of 0x85, `Unsupported MAC Layer
        encapsulation'.
        Discontinuities in the value of this counter can occur
        at re-initialization of the management system, and/or
        re-initialization of the MPC, and at other times,
        as indicated by the value of mpcDiscontinuityTime."
    REFERENCE
        "Multiprotocol Over ATM.  AF-MPOA-0087.000.  Page 62."
    ::= { mpcStatisticsEntry 15 }

mpcStatTxMpoaImpReplyUnspecifiedOther OBJECT-TYPE
    SYNTAX Counter32
    ACCESS read-only
    STATUS mandatory
    DESCRIPTION
        "The number of MPOA Imposition Replies transmitted with
        an MPOA CIE Code of 0x88, `Unspecified/Other'.
        Discontinuities in the value of this counter can occur
        at re-initialization of the management system, and/or
        re-initialization of the MPC, and at other times,
        as indicated by the value of mpcDiscontinuityTime."
    REFERENCE
        "Multiprotocol Over ATM.  AF-MPOA-0087.000.  Page 62."
    ::= { mpcStatisticsEntry 16 }

mpcStatTxMpoaEgressCachePurgeRequests OBJECT-TYPE
    SYNTAX Counter32
    ACCESS read-only
    STATUS mandatory
    DESCRIPTION
        "The number of MPOA Egress Cache Purge Requests transmitted
        by this MPC.
        Discontinuities in the value of this counter can occur
        at re-initialization of the management system, and/or
        re-initialization of the MPC, and at other times,
        as indicated by the value of mpcDiscontinuityTime."
    ::= { mpcStatisticsEntry 17 }

mpcStatRxMpoaEgressCachePurgeReplies OBJECT-TYPE
    SYNTAX Counter32
    ACCESS read-only
    STATUS mandatory
    DESCRIPTION
        "The number of MPOA Egress Cache Purge Replies received by
        this MPC.
        
        
        Discontinuities in the value of this counter can occur
        at re-initialization of the management system, and/or
        re-initialization of the MPC, and at other times,
        as indicated by the value of mpcDiscontinuityTime."
    ::= { mpcStatisticsEntry 18 }

mpcStatRxMpoaKeepAlives OBJECT-TYPE
    SYNTAX Counter32
    ACCESS read-only
    STATUS mandatory
    DESCRIPTION
        "The number of MPOA Keep Alive messages received by this MPC.
        Discontinuities in the value of this counter can occur
        at re-initialization of the management system, and/or
        re-initialization of the MPC, and at other times,
        as indicated by the value of mpcDiscontinuityTime."
    ::= { mpcStatisticsEntry 19 }

mpcStatRxMpoaTriggers OBJECT-TYPE
    SYNTAX Counter32
    ACCESS read-only
    STATUS mandatory
    DESCRIPTION
        "The number of MPOA Trigger messages received by this MPC.
        Discontinuities in the value of this counter can occur
        at re-initialization of the management system, and/or
        re-initialization of the MPC, and at other times,
        as indicated by the value of mpcDiscontinuityTime."
    ::= { mpcStatisticsEntry 20 }

mpcStatRxMpoaDataPlanePurges OBJECT-TYPE
    SYNTAX Counter32
    ACCESS read-only
    STATUS mandatory
    DESCRIPTION
        "The number of MPOA Data Plane Purge messages received
        by this MPC.
        Discontinuities in the value of this counter can occur
        at re-initialization of the management system, and/or
        re-initialization of the MPC, and at other times,
        as indicated by the value of mpcDiscontinuityTime."
    ::= { mpcStatisticsEntry 21 }

mpcStatTxMpoaDataPlanePurges OBJECT-TYPE
    SYNTAX Counter32
    ACCESS read-only
    STATUS mandatory
    DESCRIPTION
        "The number of MPOA Data Plane Purge messages transmitted
        by this MPC.
        Discontinuities in the value of this counter can occur
        at re-initialization of the management system, and/or
        re-initialization of the MPC, and at other times,
        as indicated by the value of mpcDiscontinuityTime."
    ::= { mpcStatisticsEntry 22 }

mpcStatRxNhrpPurgeRequests OBJECT-TYPE
    SYNTAX Counter32
    ACCESS read-only
    STATUS mandatory
    DESCRIPTION
        "The number of Purge Requests received by this MPC.
        Discontinuities in the value of this counter can occur
        at re-initialization of the management system, and/or
        re-initialization of the MPC, and at other times,
        as indicated by the value of mpcDiscontinuityTime."
    ::= { mpcStatisticsEntry 23 }

mpcStatTxNhrpPurgeReplies OBJECT-TYPE
    SYNTAX Counter32
    ACCESS read-only
    STATUS mandatory
    DESCRIPTION
        "The number of Purge Replies transmitted by this MPC.
        Discontinuities in the value of this counter can occur
        at re-initialization of the management system, and/or
        re-initialization of the MPC, and at other times,
        as indicated by the value of mpcDiscontinuityTime."
    ::= { mpcStatisticsEntry 24 }

mpcStatRxErrUnrecognizedExtensions OBJECT-TYPE
    SYNTAX Counter32
    ACCESS read-only
    STATUS mandatory
    DESCRIPTION
        "The number of Error Indication packets received by
        this MPC with the error code `Unrecognized Extension'.
        Discontinuities in the value of this counter can occur
        at re-initialization of the management system, and/or
        re-initialization of the MPC, and at other times,
        as indicated by the value of mpcDiscontinuityTime."
    ::= { mpcStatisticsEntry 25 }

mpcStatRxErrLoopDetecteds OBJECT-TYPE
    SYNTAX Counter32
    ACCESS read-only
    STATUS mandatory
    DESCRIPTION
        "The number of Error Indication packets received by
        this MPC with the error code `Loop Detected'.
        Discontinuities in the value of this counter can occur
        at re-initialization of the management system, and/or
        re-initialization of the MPC, and at other times,
        as indicated by the value of mpcDiscontinuityTime."
    ::= { mpcStatisticsEntry 26 }

mpcStatRxErrProtoAddrUnreachables OBJECT-TYPE
    SYNTAX Counter32
    ACCESS read-only
    STATUS mandatory
    DESCRIPTION
        "The number of Error Indication packets received by this
        MPC with the error code `Protocol Address Unreachable'.
        Discontinuities in the value of this counter can occur
        at re-initialization of the management system, and/or
        re-initialization of the MPC, and at other times,
        as indicated by the value of mpcDiscontinuityTime."
    ::= { mpcStatisticsEntry 27 }

mpcStatRxErrProtoErrors OBJECT-TYPE
    SYNTAX Counter32
    ACCESS read-only
    STATUS mandatory
    DESCRIPTION
        "The number of Error Indication packets received by
        this MPC with the error code `Protocol Errors'.
        Discontinuities in the value of this counter can occur
        at re-initialization of the management system, and/or
        re-initialization of the MPC, and at other times,
        as indicated by the value of mpcDiscontinuityTime."
    ::= { mpcStatisticsEntry 28 }

mpcStatRxErrSduSizeExceededs OBJECT-TYPE
    SYNTAX Counter32
    ACCESS read-only
    STATUS mandatory
    DESCRIPTION
        "The number of Error Indication packets received by
        this MPC with the error code `SDU Size Exceeded'.
        Discontinuities in the value of this counter can occur
        at re-initialization of the management system, and/or
        
        
        re-initialization of the MPC, and at other times,
        as indicated by the value of mpcDiscontinuityTime."
    ::= { mpcStatisticsEntry 29 }

mpcStatRxErrInvalidExtensions OBJECT-TYPE
    SYNTAX Counter32
    ACCESS read-only
    STATUS mandatory
    DESCRIPTION
        "The number of Error Indication packets received by
        this MPC with the error code `Invalid Extensions'.
        Discontinuities in the value of this counter can occur
        at re-initialization of the management system, and/or
        re-initialization of the MPC, and at other times,
        as indicated by the value of mpcDiscontinuityTime."
    ::= { mpcStatisticsEntry 30 }

mpcStatRxErrInvalidReplies OBJECT-TYPE
    SYNTAX Counter32
    ACCESS read-only
    STATUS mandatory
    DESCRIPTION
        "The number of Error Indication packets received by
        this MPC with the error code `Invalid Reply'.
        Discontinuities in the value of this counter can occur
        at re-initialization of the management system, and/or
        re-initialization of the MPC, and at other times,
        as indicated by the value of mpcDiscontinuityTime."
    ::= { mpcStatisticsEntry 31 }

mpcStatRxErrAuthenticationFailures OBJECT-TYPE
    SYNTAX Counter32
    ACCESS read-only
    STATUS mandatory
    DESCRIPTION
        "The number of Error Indication packets received by
        this MPC with the error code `Authentication Failure'.
        Discontinuities in the value of this counter can occur
        at re-initialization of the management system, and/or
        re-initialization of the MPC, and at other times,
        as indicated by the value of mpcDiscontinuityTime."
    ::= { mpcStatisticsEntry 32 }

mpcStatRxErrHopCountExceededs OBJECT-TYPE
    SYNTAX Counter32
    ACCESS read-only
    STATUS mandatory
    DESCRIPTION
        "The number of Error Indication packets received by
        this MPC with the error code `Hop Count Exceeded'.
        Discontinuities in the value of this counter can occur
        at re-initialization of the management system, and/or
        re-initialization of the MPC, and at other times,
        as indicated by the value of mpcDiscontinuityTime."
    ::= { mpcStatisticsEntry 33 }

mpcProtocolTable OBJECT-TYPE
    SYNTAX SEQUENCE OF MpcProtocolEntry
    ACCESS not-accessible
    STATUS mandatory
    DESCRIPTION
        "List of protocols, per MPC, for which flow
        detection is enabled"
    REFERENCE
        "Multiprotocol Over ATM Version 1.0 (Letter Ballot),
        Section 4.1.2.1 MPC Parameters"
    ::= { mpcObjects 6 }

mpcProtocolEntry OBJECT-TYPE
    SYNTAX MpcProtocolEntry
    ACCESS not-accessible
    STATUS mandatory
    DESCRIPTION
        "Each row indicates one protocol for which an MPC will
        do flow detection.  If the LECS was contacted for
        configuration information, and the Control Octet of
        the MPC-p3 has the value of 0x01, `Enable', then protocol
        values retrieved from the LECS are reflected in this
        table and the mpcLECSValue object will be (1) true.
        Also, the user or agent can create rows which
        appropriately correspond to the MPC denoted by mpcIndex,
        and the mpcLECSValue object will be set to (2) false.
        NOTE:  if the LECS does not return information for the
        MPC-p3 parameter, or if in manual mode, the user or
        agent should create at least one entry for the
        corresponding MPC.
        
        Both, LECS and user and/or agent created rows may
        exist in this Table."
    INDEX { mpcIndex, mpcFlowDetectProtocol }
    ::= { mpcProtocolTable 1 }

MpcProtocolEntry ::= SEQUENCE {
    mpcFlowDetectProtocol InternetworkAddrType,
    mpcLECSValue TruthValue,
    mpcProtocolRowStatus RowStatus
    }

mpcFlowDetectProtocol OBJECT-TYPE
    SYNTAX InternetworkAddrType
--    Rsyntax INTEGER {
--        other(0),
--        ipV4(1),
--        ipV6(2),
--        nsap(3),
--        hdlc(4),
--        bbn1822(5),
--        ieee802(6),
--        e163(7),
--        e164(8),
--        f69(9),
--        x121(10),
--        ipx(11),
--        appleTalk(12),
--        decnetIV(13),
--        banyanVines(14),
--        e164WithNsap(15)
--        }
--  ACCESS not-accessible
    ACCESS read-only
    STATUS mandatory
    DESCRIPTION
        "The protocol on which flow detection is performed.
        If this value was obtained from the LECS then this
        value is one of the collection of values returned
        in the MPC-p3 parameter."
    ::= { mpcProtocolEntry 1 }

mpcLECSValue OBJECT-TYPE
    SYNTAX TruthValue
--    Rsyntax INTEGER {
--        true(1),
--        false(2)
--        }
    ACCESS read-only
    STATUS mandatory
    DESCRIPTION
        "This object reflects if the current entry is due to
        a retrieval from the LECS or not.  If this entry is
        due to the LECS, then true(1) is the value for this
        object, otherwise, false (2)."
    ::= { mpcProtocolEntry 2 }

mpcProtocolRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used by an agent or manager to
        create, delete or modify a row in this table."
    ::= { mpcProtocolEntry 3 }

mpcMappingTable OBJECT-TYPE
    SYNTAX SEQUENCE OF MpcMappingEntry
    ACCESS not-accessible
    STATUS mandatory
    DESCRIPTION
        "A table mapping the `lecIndex' values of
        LANE Clients to the `mpcIndex' values of
        corresponding MPOA Clients."
    ::= { mpcObjects 7 }

mpcMappingEntry OBJECT-TYPE
    SYNTAX MpcMappingEntry
    ACCESS not-accessible
    STATUS mandatory
    DESCRIPTION
        "Each row defines one lecIndex --> mpcIndex mapping.
        The mpcIndex that a lecIndex maps to is not
        necessarily unique (an MPC can  serve many LECs, however,
        a LEC cannot be served by more than one MPC)."
    REFERENCE
        "Multiprotocol Over ATM Version 1.0 (Letter Ballot),
        Section 4.4."
    INDEX { lecIndex }
    ::= { mpcMappingTable 1 }

MpcMappingEntry ::= SEQUENCE {
    mpcMappingRowStatus RowStatus,
    mpcMappingIndex MpcIndex
    }

mpcMappingRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used by an agent or manager to create, delete
        or modify a row in this table."
    ::= { mpcMappingEntry 1 }

mpcMappingIndex OBJECT-TYPE
    SYNTAX MpcIndex
--    Rsyntax Integer32(1..2147483647)
    ACCESS read-write
    STATUS mandatory
    DESCRIPTION
        "The mpcIndex of the MPOA Client that is performing
        flow detection for the LANE Client represented by
        the lecIndex."
    ::= { mpcMappingEntry 2 }

mpcMpsTable OBJECT-TYPE
    SYNTAX SEQUENCE OF MpcMpsEntry
    ACCESS not-accessible
    STATUS mandatory
    DESCRIPTION
        "This is a read-only table which contains
        information about the MPSs that these MPCs
        know about."
    ::= { mpcObjects 8 }

mpcMpsEntry OBJECT-TYPE
    SYNTAX MpcMpsEntry
    ACCESS not-accessible
    STATUS mandatory
    DESCRIPTION
        "A row created by an MPC.  The MPC learns about
        an MPS and creates a row."
    INDEX { mpcMpsIndex }
    ::= { mpcMpsTable 1 }

MpcMpsEntry ::= SEQUENCE {
    mpcMpsIndex MpsIndex,
    mpcMpsAtmAddr AtmAddr
    }

mpcMpsIndex OBJECT-TYPE
    SYNTAX MpsIndex
--    Rsyntax Integer32(1..2147483647)
--  ACCESS not-accessible
    ACCESS read-only
    STATUS mandatory
    DESCRIPTION
        "The MPS's index which is used to identify
        a row in this table."
    ::= { mpcMpsEntry 1 }

mpcMpsAtmAddr OBJECT-TYPE
    SYNTAX AtmAddr
--    Rsyntax OCTET STRING(SIZE(0..20))
    ACCESS read-only
    STATUS mandatory
    DESCRIPTION
        "The Control ATM Address of the MPS"
    ::= { mpcMpsEntry 2 }

mpcMpsMacAddressTable OBJECT-TYPE
    SYNTAX SEQUENCE OF MpcMpsMacAddressEntry
    ACCESS not-accessible
    STATUS mandatory
    DESCRIPTION
        "This is a read-only table which contains
        information about all the MPSs' MAC Addresses
        that these MPCs know about."
    ::= { mpcObjects 9 }

mpcMpsMacAddressEntry OBJECT-TYPE
    SYNTAX MpcMpsMacAddressEntry
    ACCESS not-accessible
    STATUS mandatory
    DESCRIPTION
        "A row is created by an MPC.  The MPC learns about an
        MPS's MAC Address and creates a row."
    INDEX { mpcMpsIndex, mpcLecIndex }
    ::= { mpcMpsMacAddressTable 1 }

MpcMpsMacAddressEntry ::= SEQUENCE {
    mpcLecIndex LecIndex,
    mpcMpsMacAddress MacAddress
    }

mpcLecIndex OBJECT-TYPE
    SYNTAX LecIndex
--    Rsyntax INTEGER(1..2147483647)
--  ACCESS not-accessible
    ACCESS read-only
    STATUS mandatory
    DESCRIPTION
        "The lecIndex which represents the associated LEC."
    ::= { mpcMpsMacAddressEntry 1 }

mpcMpsMacAddress OBJECT-TYPE
    SYNTAX MacAddress
--    Rsyntax OCTET STRING(SIZE(6))
    ACCESS read-only
    STATUS mandatory
    DESCRIPTION
        "The MAC Address of the MPS."
    REFERENCE
        "Multiprotocol Over ATM Version 1.0 (Letter Ballot),
        Section 3.3.3.1"
    ::= { mpcMpsMacAddressEntry 2 }

mpcIngressCacheTxTotalPackets OBJECT-TYPE
    SYNTAX Counter32
    ACCESS read-only
    STATUS mandatory
    DESCRIPTION
        "The total number of packets transmitted over MPC Short Cuts."
    ::= { mpcObjects 10 }

mpcIngressCacheTxTotalOctets OBJECT-TYPE
    SYNTAX Counter64
    ACCESS read-only
    STATUS mandatory
    DESCRIPTION
        "The total number of octets transmitted over MPC Short Cuts."
    ::= { mpcObjects 11 }

mpcIngressCacheTable OBJECT-TYPE
    SYNTAX SEQUENCE OF MpcIngressCacheEntry
    ACCESS not-accessible
    STATUS mandatory
    DESCRIPTION
        "This table contains information for MPC Caches for
        the ingress MPC."
    ::= { mpcObjects 12 }

mpcIngressCacheEntry OBJECT-TYPE
    SYNTAX MpcIngressCacheEntry
    ACCESS not-accessible
    STATUS mandatory
    DESCRIPTION
        "An entry contains control information
        for a row in a MPC's Ingress Cache."
    INDEX { mpcIngressCacheDestInetworkAddrType, mpcIngressCacheDestAddr, mpcIndex, mpcMpsIndex }
    ::= { mpcIngressCacheTable 1 }

MpcIngressCacheEntry ::= SEQUENCE {
    mpcIngressCacheDestInetworkAddrType InternetworkAddrType,
    mpcIngressCacheDestAddr InternetworkAddr,
    mpcIngressCachePrefixLen Integer32,
    mpcIngressCacheDestAtmAddr AtmAddr,
    mpcIngressCacheSrcAtmAddr AtmAddr,
    mpcIngressCacheEntryState INTEGER,
    mpcIngressCacheEgressCacheTagValid TruthValue,
    mpcIngressCacheEgressCacheTag Integer32,
    mpcIngressCacheLastNhrpCieCode INTEGER,
    mpcIngressCacheSigErrCode Integer32,
    mpcIngressCacheRetries Counter32,
    mpcIngressCacheTimeUntilNextResolutionRequest TimeInterval,
    mpcIngressCacheHoldingTime TimeInterval,
    mpcIngressCacheServiceCategory INTEGER
    }

mpcIngressCacheDestInetworkAddrType OBJECT-TYPE
    SYNTAX InternetworkAddrType
--    Rsyntax INTEGER {
--        other(0),
--        ipV4(1),
--        ipV6(2),
--        nsap(3),
--        hdlc(4),
--        bbn1822(5),
--        ieee802(6),
--        e163(7),
--        e164(8),
--        f69(9),
--        x121(10),
--        ipx(11),
--        appleTalk(12),
--        decnetIV(13),
--        banyanVines(14),
--        e164WithNsap(15)
--        }
    ACCESS read-only
    STATUS mandatory
    DESCRIPTION
        "The type of the destination internetwork layer address."
    ::= { mpcIngressCacheEntry 1 }

mpcIngressCacheDestAddr OBJECT-TYPE
    SYNTAX InternetworkAddr
--    Rsyntax OCTET STRING(SIZE(0..60))
    ACCESS read-only
    STATUS mandatory
    DESCRIPTION
        "The destination internetwork layer address for which
        this entry is defined."
    ::= { mpcIngressCacheEntry 2 }

mpcIngressCachePrefixLen OBJECT-TYPE
    SYNTAX Integer32
    ACCESS read-only
    STATUS mandatory
    DESCRIPTION
        "Defines an equivalence class of addresses that match
        Prefix Length bit positions of the destination
        internetwork layer address."
    ::= { mpcIngressCacheEntry 3 }

mpcIngressCacheDestAtmAddr OBJECT-TYPE
    SYNTAX AtmAddr
--    Rsyntax OCTET STRING(SIZE(0..20))
    ACCESS read-only
    STATUS mandatory
    DESCRIPTION
        "The Destination ATM Address received in the MPOA
        Resolution Reply."
    ::= { mpcIngressCacheEntry 4 }

mpcIngressCacheSrcAtmAddr OBJECT-TYPE
    SYNTAX AtmAddr
--    Rsyntax OCTET STRING(SIZE(0..20))
    ACCESS read-only
    STATUS mandatory
    DESCRIPTION
        "The Source ATM Address for the MPOA Resolution Request."
    ::= { mpcIngressCacheEntry 5 }

mpcIngressCacheEntryState OBJECT-TYPE
    SYNTAX INTEGER {
        doesNotExist(1),
        inactive(2),
        active(3),
        negative(4)
        }
    ACCESS read-only
    STATUS mandatory
    DESCRIPTION
        "The present state of this MPC ingress cache.
        The states are:
        doesNotExist (1) -- the state is not yet available
        inactive (2)     -- state exists, entry is not yet
                            active.  For an example, if
                            using the Finite State Machine
                            Appendix I.2, then the states
                            Cached and query are considered
                            `inactive'.
        active (3)       -- state exists, entry is active.
                            For an example, if using the
        
        
                            Finite State Machine in Appendix I.2,
                            then the states resolved and refresh
                            are considered `active'.
        negative (4)     -- state exists, entry is negative,
                            which could mean a NAK response was
                            received, or entry is doing a
                            retry, etc.  For example, if using
                            the Finite State Machine in Appendix
                            I.2, then the state `hold down' is
                            considered `negative'."
    REFERENCE
        "Multiprotocol Over ATM, Letter Ballot, Appendix I.2."
    ::= { mpcIngressCacheEntry 6 }

mpcIngressCacheEgressCacheTagValid OBJECT-TYPE
    SYNTAX TruthValue
--    Rsyntax INTEGER {
--        true(1),
--        false(2)
--        }
    ACCESS read-only
    STATUS mandatory
    DESCRIPTION
        "If the value of this object is true(1), then a valid
        Egress Cache Tag is present and the value of the Egress
        Cache Tag is in mpcIngressCacheEgressCacheTag.  Otherwise,
        if this value is false(2), then there was no Egress Cache
        Tag, and the value of mpcIngressCacheEgressCacheTag is
        undefined."
    ::= { mpcIngressCacheEntry 7 }

mpcIngressCacheEgressCacheTag OBJECT-TYPE
    SYNTAX Integer32
    ACCESS read-only
    STATUS mandatory
    DESCRIPTION
        "If a valid Egress Cache Tag is present, then this
        object contains the value of that tag.  To determine
        if this object contains a valid value,
        mpcIngressCacheEgressTagValid should be used."
    REFERENCE
        "Multiprotocol Over ATM Version 1.0  (Letter Ballot),
        Section 4.4.4.1."
    ::= { mpcIngressCacheEntry 8 }

mpcIngressCacheLastNhrpCieCode OBJECT-TYPE
    SYNTAX INTEGER(0..255)
    ACCESS read-only
    STATUS mandatory
    DESCRIPTION
        "The last NHRP CIE code received for this entry.  This
        
        
        value is valid only during the Hold Down period of the
        cache entry.  This value is undefined otherwise."
    REFERENCE
        "Normative section 4.4.6.1.1 of Multiprotocol Over
        ATM Version 1.0  (Letter Ballot)"
    ::= { mpcIngressCacheEntry 9 }

mpcIngressCacheSigErrCode OBJECT-TYPE
    SYNTAX Integer32
    ACCESS read-only
    STATUS mandatory
    DESCRIPTION
        "Error code or Success of the last sinalling request
        for this cache entry."
    ::= { mpcIngressCacheEntry 10 }

mpcIngressCacheRetries OBJECT-TYPE
    SYNTAX Counter32
    ACCESS read-only
    STATUS mandatory
    DESCRIPTION
        "The current number of times this MPC has issued a
        resolution request since it received a valid reply."
    ::= { mpcIngressCacheEntry 11 }

mpcIngressCacheTimeUntilNextResolutionRequest OBJECT-TYPE
    SYNTAX TimeInterval
--    Rsyntax INTEGER(0..2147483647)
    ACCESS read-only
    STATUS mandatory
    DESCRIPTION
        "The amount of time  the MPC
        must wait before issuing the next resolution request."
    ::= { mpcIngressCacheEntry 12 }

mpcIngressCacheHoldingTime OBJECT-TYPE
    SYNTAX TimeInterval
--    Rsyntax INTEGER(0..2147483647)
    ACCESS read-only
    STATUS mandatory
    DESCRIPTION
        "The time that this MPC's Ingress Cache Entry will remain
        valid.  If the mpcIngressCacheEntryState is not active
        this value will be zero."
    ::= { mpcIngressCacheEntry 13 }

mpcIngressCacheServiceCategory OBJECT-TYPE
    SYNTAX INTEGER(0..65535)
    ACCESS read-only
    STATUS mandatory
    DESCRIPTION
        "The service categories supported for this shortcut."
    REFERENCE
        "Lane V2 LUNI TLVs. AF-LANE-0084 page 122"
    ::= { mpcIngressCacheEntry 14 }

mpcEgressCacheRxTotalPackets OBJECT-TYPE
    SYNTAX Counter32
    ACCESS read-only
    STATUS mandatory
    DESCRIPTION
        "This counts the total number of packets
        received by MPC Short Cuts."
    ::= { mpcObjects 13 }

mpcEgressCacheRxTotalOctets OBJECT-TYPE
    SYNTAX Counter64
    ACCESS read-only
    STATUS mandatory
    DESCRIPTION
        "This counts the total number of octets
        received by MPC Short Cuts."
    ::= { mpcObjects 14 }

mpcEgressCacheTable OBJECT-TYPE
    SYNTAX SEQUENCE OF MpcEgressCacheEntry
    ACCESS not-accessible
    STATUS mandatory
    DESCRIPTION
        "This table contains Egress Cache information for
        all the MPCs which this agent manages."
    ::= { mpcObjects 15 }

mpcEgressCacheEntry OBJECT-TYPE
    SYNTAX MpcEgressCacheEntry
    ACCESS not-accessible
    STATUS mandatory
    DESCRIPTION
        "An entry in the MPOA Client's Egress Cache table."
    INDEX { mpcEgressCacheId, mpcIndex, mpcMpsIndex }
    ::= { mpcEgressCacheTable 1 }

MpcEgressCacheEntry ::= SEQUENCE {
    mpcEgressCacheId Integer32,
    mpcEgressCacheInetworkAddrType InternetworkAddrType,
    mpcEgressCacheIDestAddr InternetworkAddr,
    mpcEgressCachePrefixLen Integer32,
    mpcEgressCacheEntryState INTEGER,
    mpcEgressCacheEgressCacheTagValid TruthValue,
    mpcEgressCacheEgressCacheTag Integer32,
    mpcEgressCacheHoldTime TimeInterval,
    mpcEgressCacheDataLinkHeader OCTET STRING,
    mpcEgressCacheIngressMpcDataAtmAddr AtmAddr,
    mpcEgressCacheLecIndex LecIndex,
    mpcEgressCacheServiceCategory INTEGER
    }

mpcEgressCacheId OBJECT-TYPE
    SYNTAX Integer32(1..2147483647)
    ACCESS read-only
    STATUS mandatory
    DESCRIPTION
        "Cache ID Provided by the MPS in the Cache
        Imposition Request."
    ::= { mpcEgressCacheEntry 1 }

mpcEgressCacheInetworkAddrType OBJECT-TYPE
    SYNTAX InternetworkAddrType
--    Rsyntax INTEGER {
--        other(0),
--        ipV4(1),
--        ipV6(2),
--        nsap(3),
--        hdlc(4),
--        bbn1822(5),
--        ieee802(6),
--        e163(7),
--        e164(8),
--        f69(9),
--        x121(10),
--        ipx(11),
--        appleTalk(12),
--        decnetIV(13),
--        banyanVines(14),
--        e164WithNsap(15)
--        }
    ACCESS read-only
    STATUS mandatory
    DESCRIPTION
        "Type of Internetwork Address in this cache entry."
    ::= { mpcEgressCacheEntry 2 }

mpcEgressCacheIDestAddr OBJECT-TYPE
    SYNTAX InternetworkAddr
--    Rsyntax OCTET STRING(SIZE(0..60))
    ACCESS read-only
    STATUS mandatory
    DESCRIPTION
        "The destination internetwork layer address
        for which this entry is defined."
    ::= { mpcEgressCacheEntry 3 }

mpcEgressCachePrefixLen OBJECT-TYPE
    SYNTAX Integer32
    ACCESS read-only
    STATUS mandatory
    DESCRIPTION
        "Defines an equivalence class of addresses that match
        Prefix Length bit positions of the destination
        internetwork layer address."
    ::= { mpcEgressCacheEntry 4 }

mpcEgressCacheEntryState OBJECT-TYPE
    SYNTAX INTEGER {
        doesNotExist(1),
        inactive(2),
        active(3),
        negative(4)
        }
    ACCESS read-only
    STATUS mandatory
    DESCRIPTION
        "The present state of this MPC egress cache entry.
        The states are:
             doesNotExist (1) -- the state is not yet available,
             inactive (2) -- state exists, entry is not yet active,
             active (3)   -- state exists, entry is active.
                             For example,if using the Finite State
                             Machine in Appendix 1.5,
                             the states active and flooding
                             are `active' state.
             negative (4) -- state exists, entry is negative.
        
        For example,if using the Finite
        State Machine in Appendix 1.5,
        the state purging is `negative'."
    REFERENCE
        "MPOA Letter Ballot, Appendix I.5."
    ::= { mpcEgressCacheEntry 5 }

mpcEgressCacheEgressCacheTagValid OBJECT-TYPE
    SYNTAX TruthValue
--    Rsyntax INTEGER {
--        true(1),
--        false(2)
--        }
    ACCESS read-only
    STATUS mandatory
    DESCRIPTION
        "If the value of this object is true(1), then a valid
        Egress Cache Tag is present and the value of the Egress
        Cache Tag is in mpcEgressCacheEgressCacheTag.  Otherwise,
        if this value is false(2), then there was no Egress
        Cache Tag, and the value of mpcEgressCacheEgressCacheTag
        is undefined."
    ::= { mpcEgressCacheEntry 6 }

mpcEgressCacheEgressCacheTag OBJECT-TYPE
    SYNTAX Integer32
    ACCESS read-only
    STATUS mandatory
    DESCRIPTION
        "If a valid Egress Cache Tag is present, then this
        object contains the value of that tag.  To determine
        if this object contains a valid value,
        mpcEgressCacheEgressCacheTagValid should be used."
    ::= { mpcEgressCacheEntry 7 }

mpcEgressCacheHoldTime OBJECT-TYPE
    SYNTAX TimeInterval
--    Rsyntax INTEGER(0..2147483647)
    ACCESS read-only
    STATUS mandatory
    DESCRIPTION
        "The remaining time for which this entry is valid."
    ::= { mpcEgressCacheEntry 8 }

mpcEgressCacheDataLinkHeader OBJECT-TYPE
    SYNTAX OCTET STRING(SIZE(0..255))
    ACCESS read-only
    STATUS mandatory
    DESCRIPTION
        "The DataLink header that the egress client rebuilds
        the original DataLink packet with."
    ::= { mpcEgressCacheEntry 9 }

mpcEgressCacheIngressMpcDataAtmAddr OBJECT-TYPE
    SYNTAX AtmAddr
--    Rsyntax OCTET STRING(SIZE(0..20))
    ACCESS read-only
    STATUS mandatory
    DESCRIPTION
        "The Data ATM Address of the ingress MPC that issued
        the MPOA Resolution request"
    REFERENCE
        "Multiprotocol Over ATM.  AF-MPOA-0087.000. Page 81."
    ::= { mpcEgressCacheEntry 10 }

mpcEgressCacheLecIndex OBJECT-TYPE
    SYNTAX LecIndex
--    Rsyntax INTEGER(1..2147483647)
    ACCESS read-only
    STATUS mandatory
    DESCRIPTION
        "This is the lecIndex of the LANE Client that this flow
        
        
        is associated with.  This can be used to get the ELAN
        name as well as other LANE parameters."
    ::= { mpcEgressCacheEntry 11 }

mpcEgressCacheServiceCategory OBJECT-TYPE
    SYNTAX INTEGER(0..65535)
    ACCESS read-only
    STATUS mandatory
    DESCRIPTION
        "This is a bitmap describing the service categories
        supported for this shortcut.  This value represents
        an inclusive OR of the bits:
        
        bit 1 - if rt-VBR is supported,
        bit 2 - if nrt-VBR is supported,
        bit 4 - if ABR is supported,
        bit 8 - if CBR is supported
        
        A value of 0 (zero) indicates that UBR is supported."
    REFERENCE
        "Lane V2 LUNI TLVs.  AF-LANE-0084, page 122."
    ::= { mpcEgressCacheEntry 12 }

mpsNextIndex OBJECT-TYPE
    SYNTAX Integer32(0..2147483647)
    ACCESS read-only
    STATUS mandatory
    DESCRIPTION
        "This object contains an appropriate value to
        be used for mpsIndex when creating entries in
        the mpsConfigTable.  The value 0 indicates that
        no new rows can be created.  Otherwise, it is
        recommended that values are assigned contiguously,
        starting from 1.
        
        MPS creation by a Manager:  To obtain the mpsIndex
        value for a new entry, the manager issues a management
        protocol retrieval operation to obtain the current value
        of this object.  If the value retrieved is 0 (zero), the
        manager cannot create a row.
        
        
        After each retrieval of a non-zero value, the manager
        should issue a management protocol SET operation using
        the value just retrieved.  If the SET is successful,
        the agent should update the value to the next
        unassigned index, or zero if appropriate.
        
        NOTE:  the manager may also issue a set on this object
        with a value of its own choosing.  If the set is successful,
        the manager may use this value for the mpsIndex. In this
        case, the agent would update the value to the next
        unassigned index, or zero if appropriate.
        The definition of `next unassigned index' is any
        mpsNextIndex value that has not yet been set by a
        manager, or reserved by the agent (see next paragraph),
        since this agent was last re-initialized.
        
        MPS creation by an Agent:  When a row in the mpsConfigTable is
        created by an agent, the agent should reserve the value of
        the index by updating the value of this object to
        the next unassigned index or zero if appropriate.  Thus, a
        manager will not be able to set an index reserved by an agent.
        In the situation of an agent re-initialization all currently
        used mpsIndexes must be preserved.  In other words, the Agent
        should store in non-volatile memory  all the currently used
        mpsIndexes (along with all necessary configuration information
        from the mpsConfigTable).  When the agent is re-initialized,
        the mpsNextIndex value is any valid Integer32 which is not
        being used as an mpsIndex, except 0 which maintains its
        original definition of indicating that a row cannot be created."
    ::= { mpsObjects 1 }

mpsConfigTable OBJECT-TYPE
    SYNTAX SEQUENCE OF MpsConfigEntry
    ACCESS not-accessible
    STATUS mandatory
    DESCRIPTION
        "The MPOA Server Configuration Table.
        This table represents the configuration information for
        all MPOA Servers which this agent manages."
    ::= { mpsObjects 2 }

mpsConfigEntry OBJECT-TYPE
    SYNTAX MpsConfigEntry
    ACCESS not-accessible
    STATUS mandatory
    DESCRIPTION
        "MPOA Server Configuration Entry.
        Each entry contains configuration information
        for one MPOA Server."
    INDEX { mpsIndex }
    ::= { mpsConfigTable 1 }

MpsConfigEntry ::= SEQUENCE {
    mpsIndex MpsIndex,
    mpsRowStatus RowStatus,
    mpsConfigMode INTEGER,
    mpsCtrlAtmAddr AtmConfigAddr,
    mpsKeepAliveTime Integer32,
    mpsKeepAliveLifeTime Integer32,
    mpsInitialRetryTime Integer32,
    mpsRetryTimeMaximum Integer32,
    mpsGiveupTime Integer32,
    mpsDefaultHoldingTime Integer32
    }

mpsIndex OBJECT-TYPE
    SYNTAX MpsIndex
--    Rsyntax Integer32(1..2147483647)
--  ACCESS not-accessible
    ACCESS read-only
    STATUS mandatory
    DESCRIPTION
        "A value which uniquely identifies this conceptual
        row in the mpsConfigTable.  The `mpsNextIndex' object
        needs to be used to determine the value of this object.
        A row cannot be added, unless the mpsCtrlAtmAddress
        is unique.
        In the event of an MPS re-initialization, the value
        of this mpsIndex must remain the same.  However, in
        the event of an agent re-initialization, this value
        does not need to be preserved."
    ::= { mpsConfigEntry 1 }

mpsRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows creation and deletion of MPOA Servers.
        Within each conceptual mpsConfigTable row, objects which are
        writable may be modified regardless of the value of
        mpsRowStatus.  It is not necessary to set a row's status
        to `notInService' first.
        
        A row cannot be created, unless the mpsAtmCtrlAddress
        in this table is unique. When an MPOA Server is created
        via this object, it will initially have
             `mpsActualState' = `initialState'."
    ::= { mpsConfigEntry 2 }

mpsConfigMode OBJECT-TYPE
    SYNTAX INTEGER {
        automatic(1),
        manual(2)
        }
    ACCESS read-write
    STATUS mandatory
    DESCRIPTION
        "Indicates whether this MPS should auto-configure
        the next time it is (re-)initialized.
        In automatic(1) mode the LECS is contacted and
        requests are made for the MPS-p* parameters.
        In manual(2) mode, the values of the configuration
        parameters are obtained from the mpsConfigTable
        and the mpsProtocolTable."
    DEFVAL { automatic }
    ::= { mpsConfigEntry 3 }

mpsCtrlAtmAddr OBJECT-TYPE
    SYNTAX AtmConfigAddr
--    Rsyntax OCTET STRING(SIZE(1 | 8 | 20))
    ACCESS read-write
    STATUS mandatory
    DESCRIPTION
        "The MPS's Control ATM Address.  There exists one
        Control ATM Address per MPS, therefore, the value
        of this entry is unique within the table."
    ::= { mpsConfigEntry 4 }

mpsKeepAliveTime OBJECT-TYPE
    SYNTAX Integer32(1..300)
    ACCESS read-write
    STATUS mandatory
    DESCRIPTION
        "MPS-p1 Keep-alive time is max interval between
        the MPS sending MPOA Keep-Alives in seconds."
    DEFVAL { 10 }
    ::= { mpsConfigEntry 5 }

mpsKeepAliveLifeTime OBJECT-TYPE
    SYNTAX Integer32(3..1000)
    ACCESS read-write
    STATUS mandatory
    DESCRIPTION
        "MPS-p2 Keep-Alive Lifetime
        The length of time an MPC may consider a Keep-Alive
        valid in seconds.  This value must be at least
        three times the mpsKeepAliveTime (MPS-p1)."
    DEFVAL { 35 }
    ::= { mpsConfigEntry 6 }

mpsInitialRetryTime OBJECT-TYPE
    SYNTAX Integer32(1..300)
    ACCESS read-write
    STATUS mandatory
    DESCRIPTION
        "MPS-p4 is initial value in seconds for the
        MPOA retry mechanism."
    DEFVAL { 5 }
    ::= { mpsConfigEntry 7 }

mpsRetryTimeMaximum OBJECT-TYPE
    SYNTAX Integer32(10..300)
    ACCESS read-write
    STATUS mandatory
    DESCRIPTION
        "MPS-p5 cumulative max value in seconds
        for Retry Time (MPS-p4)."
    REFERENCE
        "Multiprotocol Over ATM.  AF-MPOA-0087.000.
        Section 4.3 MPOA Retry Mechanism"
    DEFVAL { 40 }
    ::= { mpsConfigEntry 8 }

mpsGiveupTime OBJECT-TYPE
    SYNTAX Integer32(5..300)
    ACCESS read-write
    STATUS mandatory
    DESCRIPTION
        "MPS-p6 Give Up Time.
        Minimum time in seconds to wait before giving up on a
        pending resolution request."
    DEFVAL { 40 }
    ::= { mpsConfigEntry 9 }

mpsDefaultHoldingTime OBJECT-TYPE
    SYNTAX Integer32(1..120)
    ACCESS read-write
    STATUS mandatory
    DESCRIPTION
        "MPS-p7 Default Holding Time in minutes.
        The default Holding Time used in NHRP
        Resolution Replies.  An egress MPS may use
        local information to determine a more
        appropriate Holding Time."
    DEFVAL { 20 }
    ::= { mpsConfigEntry 10 }

mpsActualTable OBJECT-TYPE
    SYNTAX SEQUENCE OF MpsActualEntry
    ACCESS not-accessible
    STATUS mandatory
    DESCRIPTION
        "A read-only table containing identification, status,
        and operational information about the MPOA
        Servers this agent manages."
    ::= { mpsObjects 3 }

mpsActualEntry OBJECT-TYPE
    SYNTAX MpsActualEntry
    ACCESS not-accessible
    STATUS mandatory
    DESCRIPTION
        "An entry in the MPS Actual Table.
        An entry represents a specific MPOA Server's
        status and operation information."
    INDEX { mpsIndex }
-- Augments mpsConfigEntry
    ::= { mpsActualTable 1 }

MpsActualEntry ::= SEQUENCE {
    mpsActualState INTEGER,
    mpsDiscontinuityTime TimeStamp,
    mpsActualConfigMode INTEGER,
    mpsActualKeepAlive Integer32,
    mpsActualKeepAliveLifeTime Integer32,
    mpsActualInitialRetryTime Integer32,
    mpsActualRetryTimeMaximum Integer32,
    mpsActualGiveupTime Integer32,
    mpsActualDefaultHoldingTime Integer32
    }

mpsActualState OBJECT-TYPE
    SYNTAX INTEGER {
        unknown(1),
        initialState(2),
        up(3),
        down(4)
        }
    ACCESS read-only
    STATUS mandatory
    DESCRIPTION
        "This object indicates the current operational
        status of the MPOA Server."
    ::= { mpsActualEntry 1 }

mpsDiscontinuityTime OBJECT-TYPE
    SYNTAX TimeStamp
--    Rsyntax TimeTicks
    ACCESS read-only
    STATUS mandatory
    DESCRIPTION
        "The value of sysUpTime on the most recent occasion at
        which any one or more of this MPS's counters
        experienced a discontinuity.  The relevant counters
        are the specific instances associated with this
        MPS.  If discontinuities have not occurred since the
        last re-initialization of the local management subsystem,
        then this object contains a zero value."
    ::= { mpsActualEntry 2 }

mpsActualConfigMode OBJECT-TYPE
    SYNTAX INTEGER {
        automatic(1),
        manual(2)
        }
    ACCESS read-only
    STATUS mandatory
    DESCRIPTION
        "Indicates whether this MPS auto-configured
        when it was last (re-)initialized."
    ::= { mpsActualEntry 3 }

mpsActualKeepAlive OBJECT-TYPE
    SYNTAX Integer32
    ACCESS read-only
    STATUS mandatory
    DESCRIPTION
        "The maximum amount of time in seconds this MPS waits
        between sending MPOA Keep-Alives."
    ::= { mpsActualEntry 5 }

mpsActualKeepAliveLifeTime OBJECT-TYPE
    SYNTAX Integer32
    ACCESS read-only
    STATUS mandatory
    DESCRIPTION
        "The length of time in seconds this MPS
        considers a Keep-Alive valid."
    ::= { mpsActualEntry 6 }

mpsActualInitialRetryTime OBJECT-TYPE
    SYNTAX Integer32(1..300)
    ACCESS read-only
    STATUS mandatory
    DESCRIPTION
        "The actual initial value in seconds for the MPOA
        retry mechanism."
    DEFVAL { 5 }
    ::= { mpsActualEntry 7 }

mpsActualRetryTimeMaximum OBJECT-TYPE
    SYNTAX Integer32(30..300)
    ACCESS read-only
    STATUS mandatory
    DESCRIPTION
        "The actual cumulative max value in seconds
        for Retry Time."
    REFERENCE
        "Multiprotocol Over ATM.  AF-MPOA-0087.000.
        Section 4.3 MPOA Retry Mechanism"
    DEFVAL { 40 }
    ::= { mpsActualEntry 8 }

mpsActualGiveupTime OBJECT-TYPE
    SYNTAX Integer32(5..300)
    ACCESS read-only
    STATUS mandatory
    DESCRIPTION
        "Minimum time in seconds that this MPS waits
        before giving up on a pending resolution request."
    DEFVAL { 40 }
    ::= { mpsActualEntry 9 }

mpsActualDefaultHoldingTime OBJECT-TYPE
    SYNTAX Integer32(1..120)
    ACCESS read-only
    STATUS mandatory
    DESCRIPTION
        "The actual Holding Time in minutes used in
        NHRP Resolution Replies."
    ::= { mpsActualEntry 10 }

mpsStatisticsTable OBJECT-TYPE
    SYNTAX SEQUENCE OF MpsStatisticsEntry
    ACCESS not-accessible
    STATUS mandatory
    DESCRIPTION
        "This table represents the statistical information
        for the MPSs, which this agent manages."
    ::= { mpsObjects 4 }

mpsStatisticsEntry OBJECT-TYPE
    SYNTAX MpsStatisticsEntry
    ACCESS not-accessible
    STATUS mandatory
    DESCRIPTION
        "Each row in this table contains statistics
        for one MPOA server."
    INDEX { mpsIndex }
-- Augments mpsConfigEntry
    ::= { mpsStatisticsTable 1 }

MpsStatisticsEntry ::= SEQUENCE {
    mpsStatRxMpoaResolveRequests Counter32,
    mpsStatTxMpoaResolveReplyAcks Counter32,
    mpsStatTxMpoaResolveReplyInsufECResources Counter32,
    mpsStatTxMpoaResolveReplyInsufSCResources Counter32,
    mpsStatTxMpoaResolveReplyInsufEitherResources Counter32,
    mpsStatTxMpoaResolveReplyUnsupportedInetProt Counter32,
    mpsStatTxMpoaResolveReplyUnsupportedMacEncaps Counter32,
    mpsStatTxMpoaResolveReplyUnspecifiedOther Counter32,
    mpsStatTxMpoaResolveReplyOther Counter32,
    mpsStatGiveupTimeExpireds Counter32,
    mpsStatTxMpoaImpRequests Counter32,
    mpsStatRxMpoaImpReplyAcks Counter32,
    mpsStatRxMpoaImpReplyInsufECResources Counter32,
    mpsStatRxMpoaImpReplyInsufSCResources Counter32,
    mpsStatRxMpoaImpReplyInsufEitherResources Counter32,
    mpsStatRxMpoaImpReplyUnsupportedInetProt Counter32,
    mpsStatRxMpoaImpReplyUnsupportedMacEncaps Counter32,
    mpsStatRxMpoaImpReplyUnspecifiedOther Counter32,
    mpsStatRxMpoaImpReplyOther Counter32,
    mpsStatRxMpoaEgressCachePurgeRequests Counter32,
    mpsStatTxMpoaEgressCachePurgeReplies Counter32,
    mpsStatTxMpoaTriggers Counter32,
    mpsStatTxNhrpResolveRequests Counter32,
    mpsStatRxNhrpResolveReplies Counter32,
    mpsStatRxNhrpResolveRequests Counter32,
    mpsStatTxNhrpResolveReplies Counter32
    }

mpsStatRxMpoaResolveRequests OBJECT-TYPE
    SYNTAX Counter32
    ACCESS read-only
    STATUS mandatory
    DESCRIPTION
        "The number of MPOA Resolve Requests received
        by this MPS which are translated to NHRP
        resolve requests.
        Discontinuities in the value of this counter can occur
        at re-initialization of the management system, and/or
        re-initialization of the MPS, and at other times,
        as indicated by the value of mpsDiscontinuityTime."
    ::= { mpsStatisticsEntry 1 }

mpsStatTxMpoaResolveReplyAcks OBJECT-TYPE
    SYNTAX Counter32
    ACCESS read-only
    STATUS mandatory
    DESCRIPTION
        "The number of MPOA Resolve Replies transmitted by this
        MPS which contain the MPOA CIE Code of 0x00, `Success'.
        Discontinuities in the value of this counter can occur
        at re-initialization of the management system, and/or
        re-initialization of the MPS, and at other times,
        as indicated by the value of mpsDiscontinuityTime."
    REFERENCE
        "Multiprotocol Over ATM.  AF-MPOA-0087.000. Page 62."
    ::= { mpsStatisticsEntry 2 }

mpsStatTxMpoaResolveReplyInsufECResources OBJECT-TYPE
    SYNTAX Counter32
    ACCESS read-only
    STATUS mandatory
    DESCRIPTION
        "The number of MPOA Resolve Replies transmitted by this MPS
        which contain the MPOA CIE Code of 0x81, `Insufficient
        resources to accept egress cache entry'.
        Discontinuities in the value of this counter can occur
        at re-initialization of the management system, and/or
        re-initialization of the MPS, and at other times,
        as indicated by the value of mpsDiscontinuityTime."
    REFERENCE
        "Multiprotocol Over ATM.  AF-MPOA-0087.000. Page 62."
    ::= { mpsStatisticsEntry 3 }

mpsStatTxMpoaResolveReplyInsufSCResources OBJECT-TYPE
    SYNTAX Counter32
    ACCESS read-only
    STATUS mandatory
    DESCRIPTION
        "The number of MPOA Resolve Replies transmitted by this MPS
        which contain the MPOA CIE Code of 0x82,
        `Insufficient resources to accept shortcut'.
        Discontinuities in the value of this counter can occur
        at re-initialization of the management system, and/or
        re-initialization of the MPS, and at other times,
        as indicated by the value of mpsDiscontinuityTime."
    REFERENCE
        "Multiprotocol Over ATM.  AF-MPOA-0087.000. Page 62."
    ::= { mpsStatisticsEntry 4 }

mpsStatTxMpoaResolveReplyInsufEitherResources OBJECT-TYPE
    SYNTAX Counter32
    ACCESS read-only
    STATUS mandatory
    DESCRIPTION
        "The number of MPOA Resolve Replies transmitted by this MPS
        which contain the MPOA CIE CODE of 0x83, `Insufficient
        resources to accept either shortcut or egress cache entry'.
        Discontinuities in the value of this counter can occur
        at re-initialization of the management system, and/or
        re-initialization of the MPS, and at other times,
        as indicated by the value of mpsDiscontinuityTime."
    REFERENCE
        "Multiprotocol Over ATM.  AF-MPOA-0087.000. Page 62."
    ::= { mpsStatisticsEntry 5 }

mpsStatTxMpoaResolveReplyUnsupportedInetProt OBJECT-TYPE
    SYNTAX Counter32
    ACCESS read-only
    STATUS mandatory
    DESCRIPTION
        "The number of MPOA Resolve Replies transmitted by this MPS
        which contain the MPOA CIE CODE of 0x84, `Unsupported
        Internetwork
        Layer protocol'.
        Discontinuities in the value of this counter can occur
        at re-initialization of the management system, and/or
        re-initialization of the MPS, and at other times,
        as indicated by the value of mpsDiscontinuityTime."
    REFERENCE
        "Multiprotocol Over ATM.  AF-MPOA-0087.000. Page 62."
    ::= { mpsStatisticsEntry 6 }

mpsStatTxMpoaResolveReplyUnsupportedMacEncaps OBJECT-TYPE
    SYNTAX Counter32
    ACCESS read-only
    STATUS mandatory
    DESCRIPTION
        "The number of MPOA Resolve Replies transmitted by this MPS
        which contain the MPOA CIE CODE of 0x85, `Unsupported MAC
        layer encapsulation'.
        Discontinuities in the value of this counter can occur
        at re-initialization of the management system, and/or
        re-initialization of the MPS, and at other times,
        as indicated by the value of mpsDiscontinuityTime."
    REFERENCE
        "Multiprotocol Over ATM.  AF-MPOA-0087.000. Page 62."
    ::= { mpsStatisticsEntry 7 }

mpsStatTxMpoaResolveReplyUnspecifiedOther OBJECT-TYPE
    SYNTAX Counter32
    ACCESS read-only
    STATUS mandatory
    DESCRIPTION
        "The number of MPOA Resolve Replies transmitted by this MPS
        which contain the MPOA CIE CODE of 0x88, `Unspecified/Other'.
        Discontinuities in the value of this counter can occur
        at re-initialization of the management system, and/or
        re-initialization of the MPS, and at other times,
        as indicated by the value of mpsDiscontinuityTime."
    REFERENCE
        "Multiprotocol Over ATM.  AF-MPOA-0087.000. Page 62."
    ::= { mpsStatisticsEntry 8 }

mpsStatTxMpoaResolveReplyOther OBJECT-TYPE
    SYNTAX Counter32
    ACCESS read-only
    STATUS mandatory
    DESCRIPTION
        "The number of MPOA Resolve Replies transmitted by this
        MPS which are not counted above.  NOTE:  this would
        include NHRP errors.
        Discontinuities in the value of this counter can occur
        at re-initialization of the management system, and/or
        re-initialization of the MPS, and at other times,
        as indicated by the value of mpsDiscontinuityTime."
    REFERENCE
        "Multiprotocol Over ATM.  AF-MPOA-0087.000. Page 62."
    ::= { mpsStatisticsEntry 9 }

mpsStatGiveupTimeExpireds OBJECT-TYPE
    SYNTAX Counter32
    ACCESS read-only
    STATUS mandatory
    DESCRIPTION
        "The number of times the MPS Give up Time (MPS-p6)
        has expired while waiting for a reply from a
        re-originated MPOA resolution request, i.e. a
        reply for a translated NHRP resolution request.
        Discontinuities in the value of this counter can occur
        at re-initialization of the management system, and/or
        re-initialization of the MPS, and at other times,
        as indicated by the value of mpsDiscontinuityTime."
    ::= { mpsStatisticsEntry 10 }

mpsStatTxMpoaImpRequests OBJECT-TYPE
    SYNTAX Counter32
    ACCESS read-only
    STATUS mandatory
    DESCRIPTION
        "The number of MPOA Cache Imposition Requests
        transmitted by this MPS.
        Discontinuities in the value of this counter can occur
        at re-initialization of the management system, and/or
        re-initialization of the MPS, and at other times,
        as indicated by the value of mpsDiscontinuityTime."
    ::= { mpsStatisticsEntry 11 }

mpsStatRxMpoaImpReplyAcks OBJECT-TYPE
    SYNTAX Counter32
    ACCESS read-only
    STATUS mandatory
    DESCRIPTION
        "The number of successful MPOA Cache Imposition Replies
        received by this MPS which contain an MPOA CIE Code of 0x00,
        `Success'.
        Discontinuities in the value of this counter can occur
        at re-initialization of the management system, and/or
        re-initialization of the MPS, and at other times,
        as indicated by the value of mpsDiscontinuityTime."
    ::= { mpsStatisticsEntry 12 }

mpsStatRxMpoaImpReplyInsufECResources OBJECT-TYPE
    SYNTAX Counter32
    ACCESS read-only
    STATUS mandatory
    DESCRIPTION
        "The number of MPOA Cache Imposition Replies received by
        this MPS which contain the MPOA CIE Code of 0x81,
        `Insufficient resources to accept egress cache entry'.
        Discontinuities in the value of this counter can occur
        at re-initialization of the management system, and/or
        re-initialization of the MPS, and at other times,
        as indicated by the value of mpsDiscontinuityTime."
    REFERENCE
        "Multiprotocol Over ATM. AF-MPOA-0087.000. Page 62."
    ::= { mpsStatisticsEntry 13 }

mpsStatRxMpoaImpReplyInsufSCResources OBJECT-TYPE
    SYNTAX Counter32
    ACCESS read-only
    STATUS mandatory
    DESCRIPTION
        "The number of MPOA Cache Imposition Replies received by
        this MPS which contain the MPOA CIE Code of 0x82,
        `Insufficient resources to accept shortcut'.
        Discontinuities in the value of this counter can occur
        at re-initialization of the management system, and/or
        re-initialization of the MPS, and at other times,
        as indicated by the value of mpsDiscontinuityTime."
    REFERENCE
        "Multiprotocol Over ATM. AF-MPOA-0087.000. Page 62."
    ::= { mpsStatisticsEntry 14 }

mpsStatRxMpoaImpReplyInsufEitherResources OBJECT-TYPE
    SYNTAX Counter32
    ACCESS read-only
    STATUS mandatory
    DESCRIPTION
        "The number of MPOA Cache Imposition Replies received by
        this MPS which contain the MPOA CIE Code of 0x83,
        `Insufficient resources to accept either shortcut or
        egress cache entry'.
        Discontinuities in the value of this counter can occur
        at re-initialization of the management system, and/or
        re-initialization of the MPS, and at other times,
        as indicated by the value of mpsDiscontinuityTime."
    REFERENCE
        "Multiprotocol Over ATM. AF-MPOA-0087.000. Page 62."
    ::= { mpsStatisticsEntry 15 }

mpsStatRxMpoaImpReplyUnsupportedInetProt OBJECT-TYPE
    SYNTAX Counter32
    ACCESS read-only
    STATUS mandatory
    DESCRIPTION
        "The number of MPOA Cache Imposition Replies received by
        this MPS which contain the MPOA CIE Code of 0x84,
        `Unsupported Internetwork Layer protocol'.
        Discontinuities in the value of this counter can occur
        at re-initialization of the management system, and/or
        re-initialization of the MPS, and at other times,
        as indicated by the value of mpsDiscontinuityTime."
    REFERENCE
        "Multiprotocol Over ATM. AF-MPOA-0087.000. Page 62."
    ::= { mpsStatisticsEntry 16 }

mpsStatRxMpoaImpReplyUnsupportedMacEncaps OBJECT-TYPE
    SYNTAX Counter32
    ACCESS read-only
    STATUS mandatory
    DESCRIPTION
        "The number of MPOA Cache Imposition Replies received by
        this MPS which contain the MPOA CIE Code of 0x85,
        `Unsupported MAC layer encapsulation'.
        Discontinuities in the value of this counter can occur
        at re-initialization of the management system, and/or
        re-initialization of the MPS, and at other times,
        as indicated by the value of mpsDiscontinuityTime."
    REFERENCE
        "Multiprotocol Over ATM. AF-MPOA-0087.000. Page 62."
    ::= { mpsStatisticsEntry 17 }

mpsStatRxMpoaImpReplyUnspecifiedOther OBJECT-TYPE
    SYNTAX Counter32
    ACCESS read-only
    STATUS mandatory
    DESCRIPTION
        "The number of MPOA Cache Imposition Replies received by
        this MPS which contain the MPOA CIE Code of 0x88,
        `Unspecified/Other'.
        Discontinuities in the value of this counter can occur
        at re-initialization of the management system, and/or
        re-initialization of the MPS, and at other times,
        as indicated by the value of mpsDiscontinuityTime."
    REFERENCE
        "Multiprotocol Over ATM. AF-MPOA-0087.000. Page 62."
    ::= { mpsStatisticsEntry 18 }

mpsStatRxMpoaImpReplyOther OBJECT-TYPE
    SYNTAX Counter32
    ACCESS read-only
    STATUS mandatory
    DESCRIPTION
        "The number of MPOA Cache Imposition Replies received by
        this MPS which are not counted previously.  NOTE:
        this would include NHRP errors.
        Discontinuities in the value of this counter can occur
        at re-initialization of the management system, and/or
        re-initialization of the MPS, and at other times,
        as indicated by the value of mpsDiscontinuityTime."
    REFERENCE
        "Multiprotocol Over ATM. AF-MPOA-0087.000. Page 62."
    ::= { mpsStatisticsEntry 19 }

mpsStatRxMpoaEgressCachePurgeRequests OBJECT-TYPE
    SYNTAX Counter32
    ACCESS read-only
    STATUS mandatory
    DESCRIPTION
        "The number of MPOA Egress Cache Purges Requests
        received by this MPS.
        Discontinuities in the value of this counter can occur
        at re-initialization of the management system, and/or
        re-initialization of the MPS, and at other times,
        as indicated by the value of mpsDiscontinuityTime."
    ::= { mpsStatisticsEntry 20 }

mpsStatTxMpoaEgressCachePurgeReplies OBJECT-TYPE
    SYNTAX Counter32
    ACCESS read-only
    STATUS mandatory
    DESCRIPTION
        "The number of MPOA Egress Cache Purge Replies
        transmitted by this MPS.
        Discontinuities in the value of this counter can occur
        at re-initialization of the management system, and/or
        re-initialization of the MPS, and at other times,
        as indicated by the value of mpsDiscontinuityTime."
    ::= { mpsStatisticsEntry 21 }

mpsStatTxMpoaTriggers OBJECT-TYPE
    SYNTAX Counter32
    ACCESS read-only
    STATUS mandatory
    DESCRIPTION
        "The number of MPOA Trigger messages transmitted by this MPS.
        Discontinuities in the value of this counter can occur
        at re-initialization of the management system, and/or
        re-initialization of the MPS, and at other times,
        as indicated by the value of mpsDiscontinuityTime."
    REFERENCE
        "Multiprotocol Over ATM.  AF-MPOA-0087.000.
        Section 4.7.2.1 MPOA Trigger"
    ::= { mpsStatisticsEntry 22 }

mpsStatTxNhrpResolveRequests OBJECT-TYPE
    SYNTAX Counter32
    ACCESS read-only
    STATUS mandatory
    DESCRIPTION
        "Total count of MPOA Resolution Requests received
        by the Ingress MPS which were translated to NHRP
        
        
        Resolution Requests and transmitted to the NHS.
        Discontinuities in the value of this counter can occur
        at re-initialization of the management system, and/or
        re-initialization of the MPS, and at other times,
        as indicated by the value of mpsDiscontinuityTime."
    ::= { mpsStatisticsEntry 23 }

mpsStatRxNhrpResolveReplies OBJECT-TYPE
    SYNTAX Counter32
    ACCESS read-only
    STATUS mandatory
    DESCRIPTION
        "Total count of NHRP Resolution Replies received
        by the Ingress.
        Discontinuities in the value of this counter can occur
        at re-initialization of the management system, and/or
        re-initialization of the MPS, and at other times,
        as indicated by the value of mpsDiscontinuityTime."
    ::= { mpsStatisticsEntry 24 }

mpsStatRxNhrpResolveRequests OBJECT-TYPE
    SYNTAX Counter32
    ACCESS read-only
    STATUS mandatory
    DESCRIPTION
        "Total count of NHRP Resolution Requests received by
        the Egress MPS from the NHS.
        Discontinuities in the value of this counter can occur
        at re-initialization of the management system, and/or
        re-initialization of the MPS, and at other times,
        as indicated by the value of mpsDiscontinuityTime."
    ::= { mpsStatisticsEntry 25 }

mpsStatTxNhrpResolveReplies OBJECT-TYPE
    SYNTAX Counter32
    ACCESS read-only
    STATUS mandatory
    DESCRIPTION
        "Total count of NHRP Resolution Replies transmitted
        by the Egress MPS to the NHS.
        Discontinuities in the value of this counter can occur
        at re-initialization of the management system, and/or
        re-initialization of the MPS, and at other times,
        as indicated by the value of mpsDiscontinuityTime."
    ::= { mpsStatisticsEntry 26 }

mpsProtocolTable OBJECT-TYPE
    SYNTAX SEQUENCE OF MpsProtocolEntry
    ACCESS not-accessible
    STATUS mandatory
    DESCRIPTION
        "List of protocols, per MPS, for which
        MPOA resolution is enabled."
    REFERENCE
        "Multiprotocol Over ATM Version 1.0 (Letter Ballot),
        Section 4.1.1.1 MPS Parameters"
    ::= { mpsObjects 5 }

mpsProtocolEntry OBJECT-TYPE
    SYNTAX MpsProtocolEntry
    ACCESS not-accessible
    STATUS mandatory
    DESCRIPTION
        "Each row indicates one protocol for which an MPS
        will perform MPOA resolution.
        If the LECS was contacted for configuration
        information, and the MPS-p3's control octet is set to Enable,
        0x01, then protocol values retrieved from the LECS are reflected
        in this table and the mpsLECSValue object will be (1) true.
        Also, the user or agent can create rows which
        appropriately correspond to the MPS denoted by mpsIndex,
        and the mpsLECSValue object will be set to (2) false.
        NOTE:  if the LECS does not return information for
        the MPS-p3 parameter, or if in manual mode, the user or agent
        should create at least one entry for the corresponding MPS.
        Both, LECS and user and/or agent created rows may exist in
        this Table."
    INDEX { mpsIndex, mpsInternetworkLayerProtocol }
    ::= { mpsProtocolTable 1 }

MpsProtocolEntry ::= SEQUENCE {
    mpsInternetworkLayerProtocol InternetworkAddrType,
    mpsLECSValue TruthValue,
    mpsProtocolRowStatus RowStatus
    }

mpsInternetworkLayerProtocol OBJECT-TYPE
    SYNTAX InternetworkAddrType
--    Rsyntax INTEGER {
--        other(0),
--        ipV4(1),
--        ipV6(2),
--        nsap(3),
--        hdlc(4),
--        bbn1822(5),
--        ieee802(6),
--        e163(7),
--        e164(8),
--        f69(9),
--        x121(10),
--        ipx(11),
--        appleTalk(12),
--        decnetIV(13),
--        banyanVines(14),
--        e164WithNsap(15)
--        }
--  ACCESS not-accessible
    ACCESS read-only
    STATUS mandatory
    DESCRIPTION
        "MPS-p3 A protocol on which to perform MPOA resolution."
    ::= { mpsProtocolEntry 1 }

mpsLECSValue OBJECT-TYPE
    SYNTAX TruthValue
--    Rsyntax INTEGER {
--        true(1),
--        false(2)
--        }
    ACCESS read-only
    STATUS mandatory
    DESCRIPTION
        "This object reflects if the current entry is due to
        a retrieval from the LECS or not.  If this entry is
        due to the LECS, then true(1) is the value for this object,
        otherwise, false (2)."
    ::= { mpsProtocolEntry 2 }

mpsProtocolRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object allows network managers to enable
        resolution for the `mpsInternetworkLayerProtocol'."
    ::= { mpsProtocolEntry 3 }

mpsMappingTable OBJECT-TYPE
    SYNTAX SEQUENCE OF MpsMappingEntry
    ACCESS not-accessible
    STATUS mandatory
    DESCRIPTION
        "A table mapping the `lecIndex' values of
        LANE Clients to the `mpsIndex' values of
        corresponding MPOA Servers."
    ::= { mpsObjects 6 }

mpsMappingEntry OBJECT-TYPE
    SYNTAX MpsMappingEntry
    ACCESS not-accessible
    STATUS mandatory
    DESCRIPTION
        "Each row defines one lecIndex --> mpsIndex mapping.
        
        
        The mpsIndex that a lecIndex maps to is not
        necessarily unique. In other words, there can be
        multiple LECs associated with one MPS."
    REFERENCE
        "LAN Emulation Client Management Specification.
        af-lane-0044-000."
    INDEX { lecIndex }
    ::= { mpsMappingTable 1 }

MpsMappingEntry ::= SEQUENCE {
    mpsMappingRowStatus RowStatus,
    mpsMappingIndex MpsIndex
    }

mpsMappingRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Allows creation, enabling/disabling of this row."
    ::= { mpsMappingEntry 1 }

mpsMappingIndex OBJECT-TYPE
    SYNTAX MpsIndex
--    Rsyntax Integer32(1..2147483647)
    ACCESS read-only
    STATUS mandatory
    DESCRIPTION
        "The mpsMappingIndex of the MPOA Server that is associated with
        this LEC.  The mpsMappingIndex corresponds to the mpsIndex."
    ::= { mpsMappingEntry 2 }

mpsMpcTable OBJECT-TYPE
    SYNTAX SEQUENCE OF MpsMpcEntry
    ACCESS not-accessible
    STATUS mandatory
    DESCRIPTION
        "This read-only table contains information about the
        MPCs that these MPSs know about."
    ::= { mpsObjects 9 }

mpsMpcEntry OBJECT-TYPE
    SYNTAX MpsMpcEntry
    ACCESS not-accessible
    STATUS mandatory
    DESCRIPTION
        "A row created by an MPS.  The MPS learns about the MPC and
        creates a row."
    INDEX { mpsIndex, mpsMpcIndex }
    ::= { mpsMpcTable 1 }

MpsMpcEntry ::= SEQUENCE {
    mpsMpcIndex MpcIndex,
    mpsMpcCtrlAtmAddr AtmAddr
    }

mpsMpcIndex OBJECT-TYPE
    SYNTAX MpcIndex
--    Rsyntax Integer32(1..2147483647)
--  ACCESS not-accessible
    ACCESS read-only
    STATUS mandatory
    DESCRIPTION
        "The local index for the mpc represented by this entry"
    ::= { mpsMpcEntry 1 }

mpsMpcCtrlAtmAddr OBJECT-TYPE
    SYNTAX AtmAddr
--    Rsyntax OCTET STRING(SIZE(0..20))
    ACCESS read-only
    STATUS mandatory
    DESCRIPTION
        "MPC control ATM address "
    ::= { mpsMpcEntry 2 }

mpsIngressCacheTable OBJECT-TYPE
    SYNTAX SEQUENCE OF MpsIngressCacheEntry
    ACCESS not-accessible
    STATUS mandatory
    DESCRIPTION
        "This table tracks all the Ingress Cache information
        of the MPSs which this agents manages."
    ::= { mpsObjects 7 }

mpsIngressCacheEntry OBJECT-TYPE
    SYNTAX MpsIngressCacheEntry
    ACCESS not-accessible
    STATUS mandatory
    DESCRIPTION
        "A entry contains parameters and state variables
        for a row in a MPS's Ingress Cache."
    INDEX { mpsIngressCacheDestInternetworkAddrType, mpsIngressCacheDestAddr, mpsIndex, mpsMpcIndex }
    ::= { mpsIngressCacheTable 1 }

MpsIngressCacheEntry ::= SEQUENCE {
    mpsIngressCacheDestInternetworkAddrType InternetworkAddrType,
    mpsIngressCacheDestAddr InternetworkAddr,
    mpsIngressCachePrefixLen Integer32,
    mpsIngressCacheEntryState INTEGER,
    mpsIngressCacheSrcInternetworkAddrType InternetworkAddrType,
    mpsIngressCacheSrcAddr InternetworkAddr,
    mpsIngressCacheSourceMpcCtrlAtmAddr AtmAddr,
    mpsIngressCacheResolvedAtmAddr AtmAddr,
    mpsIngressCacheHoldTime TimeInterval,
    mpsIngressCacheMpoaRequestId Integer32,
    mpsIngressCacheNhrpRequestId Integer32,
    mpsIngressCacheServiceCategory INTEGER
    }

mpsIngressCacheDestInternetworkAddrType OBJECT-TYPE
    SYNTAX InternetworkAddrType
--    Rsyntax INTEGER {
--        other(0),
--        ipV4(1),
--        ipV6(2),
--        nsap(3),
--        hdlc(4),
--        bbn1822(5),
--        ieee802(6),
--        e163(7),
--        e164(8),
--        f69(9),
--        x121(10),
--        ipx(11),
--        appleTalk(12),
--        decnetIV(13),
--        banyanVines(14),
--        e164WithNsap(15)
--        }
    ACCESS read-only
    STATUS mandatory
    DESCRIPTION
        "The type of internetwork layer address of the
        Destination Address."
    ::= { mpsIngressCacheEntry 1 }

mpsIngressCacheDestAddr OBJECT-TYPE
    SYNTAX InternetworkAddr
--    Rsyntax OCTET STRING(SIZE(0..60))
    ACCESS read-only
    STATUS mandatory
    DESCRIPTION
        "The Ingress MPS Destination Internetwork Layer Address."
    ::= { mpsIngressCacheEntry 2 }

mpsIngressCachePrefixLen OBJECT-TYPE
    SYNTAX Integer32
    ACCESS read-only
    STATUS mandatory
    DESCRIPTION
        "The Prefix Length of the mpsIngressCacheDestAddr."
    ::= { mpsIngressCacheEntry 3 }

mpsIngressCacheEntryState OBJECT-TYPE
    SYNTAX INTEGER {
        doesNotExist(1),
        inactive(2),
        active(3),
        negative(4)
        }
    ACCESS read-only
    STATUS mandatory
    DESCRIPTION
        "The state of this MPS Ingress cache.
        The states are:
             doesNotExist (1) -- the state is not yet available
             inactive (2) -- state exists, entry is not yet active
                             For example,if using the Finite
                             State Machine in Appendix I.3,
                             the state resolving is `inactive'.
             active (3) -- state exists, entry is active.
                           For example,if using the Finite
                           State Machine in Appendix I.3,
                           the state resolved
                           is `active' state.
             negative (4) -- state exists, entry is negative.
                             For example,if using the Finite
                             State Machine in Appendix I.3,
                             the state purging is `negative'."
    REFERENCE
        "Multiprotocol Over ATM, Letter Ballot, Appendix I.3."
    ::= { mpsIngressCacheEntry 4 }

mpsIngressCacheSrcInternetworkAddrType OBJECT-TYPE
    SYNTAX InternetworkAddrType
--    Rsyntax INTEGER {
--        other(0),
--        ipV4(1),
--        ipV6(2),
--        nsap(3),
--        hdlc(4),
--        bbn1822(5),
--        ieee802(6),
--        e163(7),
--        e164(8),
--        f69(9),
--        x121(10),
--        ipx(11),
--        appleTalk(12),
--        decnetIV(13),
--        banyanVines(14),
--        e164WithNsap(15)
--        }
    ACCESS read-only
    STATUS mandatory
    DESCRIPTION
        "The type of internetwork layer address of the
        Source Address."
    ::= { mpsIngressCacheEntry 5 }

mpsIngressCacheSrcAddr OBJECT-TYPE
    SYNTAX InternetworkAddr
--    Rsyntax OCTET STRING(SIZE(0..60))
    ACCESS read-only
    STATUS mandatory
    DESCRIPTION
        "The Ingress MPS Source Internetwork Layer Address."
    ::= { mpsIngressCacheEntry 6 }

mpsIngressCacheSourceMpcCtrlAtmAddr OBJECT-TYPE
    SYNTAX AtmAddr
--    Rsyntax OCTET STRING(SIZE(0..20))
    ACCESS read-only
    STATUS mandatory
    DESCRIPTION
        "The ATM Address from the source of this MPOA request.
        In other words, the Ingress MPC's Control Atm Address."
    ::= { mpsIngressCacheEntry 7 }

mpsIngressCacheResolvedAtmAddr OBJECT-TYPE
    SYNTAX AtmAddr
--    Rsyntax OCTET STRING(SIZE(0..20))
    ACCESS read-only
    STATUS mandatory
    DESCRIPTION
        "The ATM Address which has been resolved by an Egress MPC."
    ::= { mpsIngressCacheEntry 8 }

mpsIngressCacheHoldTime OBJECT-TYPE
    SYNTAX TimeInterval
--    Rsyntax INTEGER(0..2147483647)
    ACCESS read-only
    STATUS mandatory
    DESCRIPTION
        "Time interval that this value is valid."
    ::= { mpsIngressCacheEntry 9 }

mpsIngressCacheMpoaRequestId OBJECT-TYPE
    SYNTAX Integer32
    ACCESS read-only
    STATUS mandatory
    DESCRIPTION
        "The request ID contained in the MPOA resolution request
        from the local Ingress MPC."
    ::= { mpsIngressCacheEntry 10 }

mpsIngressCacheNhrpRequestId OBJECT-TYPE
    SYNTAX Integer32
    ACCESS read-only
    STATUS mandatory
    DESCRIPTION
        "The request ID which this MPS generates to identify the
        NHRP resolution request."
    ::= { mpsIngressCacheEntry 11 }

mpsIngressCacheServiceCategory OBJECT-TYPE
    SYNTAX INTEGER(0..65535)
    ACCESS read-only
    STATUS mandatory
    DESCRIPTION
        "The service categories supported for this shortcut."
    REFERENCE
        "Lane V2 LUNI TLVs"
    ::= { mpsIngressCacheEntry 12 }

mpsEgressCacheTable OBJECT-TYPE
    SYNTAX SEQUENCE OF MpsEgressCacheEntry
    ACCESS not-accessible
    STATUS mandatory
    DESCRIPTION
        "This table contains information regarding the
        Egress MPOA Server Cache Table."
    ::= { mpsObjects 8 }

mpsEgressCacheEntry OBJECT-TYPE
    SYNTAX MpsEgressCacheEntry
    ACCESS not-accessible
    STATUS mandatory
    DESCRIPTION
        "An entry represents an entry in the MPS's Egress
        cache Table which keeps track of the state of the
        impositions."
    INDEX { mpsEgressCacheId, mpsIndex, mpsMpcIndex }
    ::= { mpsEgressCacheTable 1 }

MpsEgressCacheEntry ::= SEQUENCE {
    mpsEgressCacheId Integer32,
    mpsEgressCacheDestInternetworkAddrType InternetworkAddrType,
    mpsEgressCacheDestAddr InternetworkAddr,
    mpsEgressCachePrefixLen INTEGER,
    mpsEgressCacheHoldTime TimeInterval,
    mpsEgressCacheEntryState INTEGER,
    mpsEgressCacheDataLinkHeader OCTET STRING,
    mpsEgressCacheElanId Integer32,
    mpsEgressCacheSourceClientAtmAddr AtmAddr,
    mpsEgressCacheNhrpRequestId Integer32,
    mpsEgressCacheMpoaRequestId Integer32,
    mpsEgressCacheServiceCategory INTEGER,
    mpsEgressCacheNextHopInternetworkAddrType InternetworkAddrType,
    mpsEgressCacheNextHopAddr InternetworkAddr
    }

mpsEgressCacheId OBJECT-TYPE
    SYNTAX Integer32
    ACCESS read-only
    STATUS mandatory
    DESCRIPTION
        "The id which identifies this cache entry."
    ::= { mpsEgressCacheEntry 1 }

mpsEgressCacheDestInternetworkAddrType OBJECT-TYPE
    SYNTAX InternetworkAddrType
--    Rsyntax INTEGER {
--        other(0),
--        ipV4(1),
--        ipV6(2),
--        nsap(3),
--        hdlc(4),
--        bbn1822(5),
--        ieee802(6),
--        e163(7),
--        e164(8),
--        f69(9),
--        x121(10),
--        ipx(11),
--        appleTalk(12),
--        decnetIV(13),
--        banyanVines(14),
--        e164WithNsap(15)
--        }
    ACCESS read-only
    STATUS mandatory
    DESCRIPTION
        "The destination protocol address type."
    ::= { mpsEgressCacheEntry 2 }

mpsEgressCacheDestAddr OBJECT-TYPE
    SYNTAX InternetworkAddr
--    Rsyntax OCTET STRING(SIZE(0..60))
    ACCESS read-only
    STATUS mandatory
    DESCRIPTION
        "The destination protocol address."
    ::= { mpsEgressCacheEntry 3 }

mpsEgressCachePrefixLen OBJECT-TYPE
    SYNTAX INTEGER(0..255)
    ACCESS read-only
    STATUS mandatory
    DESCRIPTION
        "The destination prefix length."
    ::= { mpsEgressCacheEntry 4 }

mpsEgressCacheHoldTime OBJECT-TYPE
    SYNTAX TimeInterval
--    Rsyntax INTEGER(0..2147483647)
    ACCESS read-only
    STATUS mandatory
    DESCRIPTION
        "Time interval that this value is valid."
    ::= { mpsEgressCacheEntry 5 }

mpsEgressCacheEntryState OBJECT-TYPE
    SYNTAX INTEGER {
        doesNotExist(1),
        inactive(2),
        active(3),
        negative(4)
        }
    ACCESS read-only
    STATUS mandatory
    DESCRIPTION
        "The present states of this MPS egress cache entry.
        The states are:
             doesNotExist (1) -- the state is not yet available
             inactive (2) -- state exists, entry is not yet active
                  For example,if using the Finite
                  State Machine in Appendix 1.4,
                  the state imposing is `inactive'.
             active (3) -- state exists, entry is active.
                  For example,if using the Finite
                  State Machine in Appendix 1.4,
                  the state imposed
                  is `active' state.
             negative (4) -- state exists, entry is negative.
                  For example,if using the Finite
                  State Machine in Appendix 1.4,
                  the states purging and clearing
                  are `negative'."
    REFERENCE
        "Multiprotocol Over ATM.  AF-MPOA-0087.000.
        Appendix I.4 Egress MPS Control State Machine."
    ::= { mpsEgressCacheEntry 6 }

mpsEgressCacheDataLinkHeader OBJECT-TYPE
    SYNTAX OCTET STRING(SIZE(0..255))
    ACCESS read-only
    STATUS mandatory
    DESCRIPTION
        "Data-Link Layer Header."
    ::= { mpsEgressCacheEntry 7 }

mpsEgressCacheElanId OBJECT-TYPE
    SYNTAX Integer32
    ACCESS read-only
    STATUS mandatory
    DESCRIPTION
        "The elan id that this Cache Imposition is sent on."
    ::= { mpsEgressCacheEntry 8 }

mpsEgressCacheSourceClientAtmAddr OBJECT-TYPE
    SYNTAX AtmAddr
--    Rsyntax OCTET STRING(SIZE(0..20))
    ACCESS read-only
    STATUS mandatory
    DESCRIPTION
        "The Ingress NHC's Atm Address used in the
        original cache imposition."
    REFERENCE
        "Multiprotocol Over ATM.  AF-MPOA-0087.000.
        Page 45."
    ::= { mpsEgressCacheEntry 9 }

mpsEgressCacheNhrpRequestId OBJECT-TYPE
    SYNTAX Integer32
    ACCESS read-only
    STATUS mandatory
    DESCRIPTION
        "The request id from the original NHRP Resolution Request,
        may be only useful in the Resolving State."
    ::= { mpsEgressCacheEntry 10 }

mpsEgressCacheMpoaRequestId OBJECT-TYPE
    SYNTAX Integer32
    ACCESS read-only
    STATUS mandatory
    DESCRIPTION
        "The new request id which is generated for this imposition's
        request, may be only useful in the Resolving State."
    ::= { mpsEgressCacheEntry 11 }

mpsEgressCacheServiceCategory OBJECT-TYPE
    SYNTAX INTEGER(0..65535)
    ACCESS read-only
    STATUS mandatory
    DESCRIPTION
        "The service categories supported for this shortcut."
    REFERENCE
        "Lane V2 LUNI TLVs"
    ::= { mpsEgressCacheEntry 12 }

mpsEgressCacheNextHopInternetworkAddrType OBJECT-TYPE
    SYNTAX InternetworkAddrType
--    Rsyntax INTEGER {
--        other(0),
--        ipV4(1),
--        ipV6(2),
--        nsap(3),
--        hdlc(4),
--        bbn1822(5),
--        ieee802(6),
--        e163(7),
--        e164(8),
--        f69(9),
--        x121(10),
--        ipx(11),
--        appleTalk(12),
--        decnetIV(13),
--        banyanVines(14),
--        e164WithNsap(15)
--        }
    ACCESS read-only
    STATUS mandatory
    DESCRIPTION
        "The NextHop protocol address type."
    ::= { mpsEgressCacheEntry 13 }

mpsEgressCacheNextHopAddr OBJECT-TYPE
    SYNTAX InternetworkAddr
--    Rsyntax OCTET STRING(SIZE(0..60))
    ACCESS read-only
    STATUS mandatory
    DESCRIPTION
        "The NextHop protocol address."
    ::= { mpsEgressCacheEntry 14 }

mpoaDeviceTypeGroup OBJECT IDENTIFIER ::= { mpoaMIBGroups 1 }
-- OBJECT-GROUP
--  Status
--    mandatory
--  Descr
--    A collection of objects which exists when
--    the MPOA device learns the MPOA device type and
--    
--    
--    MPOA control addresses of neighboring MPOA devices
--    using the LANEv2 Device Type TLV.
--  objects
--    deviceTypeLecIndex, deviceTypeRemoteLecAtmAddress, 
--    deviceTypeType, deviceTypeMpsAtmAddress, 
--    deviceTypeMpcAtmAddress

mpoaDeviceTypeMpsMacGroup OBJECT IDENTIFIER ::= { mpoaMIBGroups 2 }
-- OBJECT-GROUP
--  Status
--    mandatory
--  Descr
--    A collection of objects which is present when the
--    MPOA device learns the MPOA device type and MPOA
--    control addresses of neighboring MPOA devices using
--    the LANEv2 Device Type TLV.
--  objects
--    deviceTypeMpsMacAddress

mpcConfigGroup OBJECT IDENTIFIER ::= { mpoaMIBGroups 3 }
-- OBJECT-GROUP
--  Status
--    mandatory
--  Descr
--    A collection of objects used for creating and
--    configuring MPOA Clients.
--  objects
--    mpcNextIndex, mpcRowStatus, mpcConfigMode, mpcCtrlAtmAddr, 
--    mpcSCSetupFrameCount, mpcSCSetupFrameTime, 
--    mpcInitialRetryTime, mpcRetryTimeMaximum, mpcHoldDownTime

mpcActualGroup OBJECT IDENTIFIER ::= { mpoaMIBGroups 4 }
-- OBJECT-GROUP
--  Status
--    mandatory
--  Descr
--    A collection of objects describing the status
--    and operational parameters of the managed MPC.
--  objects
--    mpcActualState, mpcDiscontinuityTime, mpcActualConfigMode, 
--    mpcActualSCSetupFrameCount, mpcActualSCSetupFrameTime, 
--    mpcActualInitialRetryTime, mpcActualRetryTimeMaximum, 
--    mpcActualHoldDownTime

mpcDataAtmAddressGroup OBJECT IDENTIFIER ::= { mpoaMIBGroups 5 }
-- OBJECT-GROUP
--  Status
--    mandatory
--  Descr
--    A collection of objects which describe the
--    set of data ATM addresses for the MPCs.
--  objects
--    mpcDataAtmAddressRowStatus

mpcStatisticsGroup OBJECT IDENTIFIER ::= { mpoaMIBGroups 6 }
-- OBJECT-GROUP
--  Status
--    mandatory
--  Descr
--    A collection of objects that provide statistics
--    on the MPOA protocol parameters.
--  objects
--    mpcStatTxMpoaResolveRequests, mpcStatRxMpoaResolveReplyAcks, 
--    mpcStatRxMpoaResolveReplyInsufECResources, 
--    mpcStatRxMpoaResolveReplyInsufSCResources, 
--    mpcStatRxMpoaResolveReplyInsufEitherResources, 
--    mpcStatRxMpoaResolveReplyUnsupportedInetProt, 
--    mpcStatRxMpoaResolveReplyUnsupportedMacEncaps, 
--    mpcStatRxMpoaResolveReplyUnspecifiedOther, 
--    mpcStatRxMpoaImpRequests, mpcStatTxMpoaImpReplyAcks, 
--    mpcStatTxMpoaImpReplyInsufECResources, 
--    mpcStatTxMpoaImpReplyInsufSCResources, 
--    mpcStatTxMpoaImpReplyInsufEitherResources, 
--    mpcStatTxMpoaImpReplyUnsupportedInetProt, 
--    mpcStatTxMpoaImpReplyUnsupportedMacEncaps, 
--    mpcStatTxMpoaImpReplyUnspecifiedOther, 
--    mpcStatTxMpoaEgressCachePurgeRequests, 
--    mpcStatRxMpoaEgressCachePurgeReplies, mpcStatRxMpoaKeepAlives, 
--    mpcStatRxMpoaTriggers, mpcStatRxMpoaDataPlanePurges, 
--    mpcStatTxMpoaDataPlanePurges, mpcStatRxNhrpPurgeRequests, 
--    mpcStatTxNhrpPurgeReplies, mpcStatRxErrUnrecognizedExtensions, 
--    mpcStatRxErrLoopDetecteds, mpcStatRxErrProtoAddrUnreachables, 
--    mpcStatRxErrProtoErrors, mpcStatRxErrSduSizeExceededs, 
--    mpcStatRxErrInvalidExtensions, mpcStatRxErrInvalidReplies, 
--    mpcStatRxErrAuthenticationFailures, 
--    mpcStatRxErrHopCountExceededs

mpcProtocolGroup OBJECT IDENTIFIER ::= { mpoaMIBGroups 7 }
-- OBJECT-GROUP
--  Status
--    mandatory
--  Descr
--    A collection of objects to specify which
--    parameters this MPC is enabled for.
--  objects
--    mpcLECSValue, mpcProtocolRowStatus

mpcMappingGroup OBJECT IDENTIFIER ::= { mpoaMIBGroups 8 }
-- OBJECT-GROUP
--  Status
--    mandatory
--  Descr
--    A collection of objects to map from LEC to MPC
--  objects
--    mpcMappingRowStatus, mpcMappingIndex

mpcMpsGroup OBJECT IDENTIFIER ::= { mpoaMIBGroups 9 }
-- OBJECT-GROUP
--  Status
--    mandatory
--  Descr
--    A collection of objects which aid the MPCs to track
--    information for all the MPSs which are known by the MPCs.
--  objects
--    mpcMpsAtmAddr

mpcMpsMacAddressGroup OBJECT IDENTIFIER ::= { mpoaMIBGroups 10 }
-- OBJECT-GROUP
--  Status
--    mandatory
--  Descr
--    A collection of objects which aid the MPCs to track
--    MAC Address information for all the MPSs which are known
--    by the MPCs.
--  objects
--    mpcMpsMacAddress

mpcIngressCacheTotalPacketGroup OBJECT IDENTIFIER ::= { mpoaMIBGroups 11 }
-- OBJECT-GROUP
--  Status
--    mandatory
--  Descr
--    A collection of objects which count the total
--    number of packets transmitted over MPC
--    short cuts.
--  objects
--    mpcIngressCacheTxTotalPackets

mpcIngressCacheTotalOctetGroup OBJECT IDENTIFIER ::= { mpoaMIBGroups 12 }
-- OBJECT-GROUP
--  Status
--    mandatory
--  Descr
--    A collection of objects which count the total
--    number of octets transmitted over MPC
--    short cuts.
--  objects
--    mpcIngressCacheTxTotalOctets

mpcIngressCacheGroup OBJECT IDENTIFIER ::= { mpoaMIBGroups 13 }
-- OBJECT-GROUP
--  Status
--    mandatory
--  Descr
--    A collection of objects used to monitor the
--    MPOA ingress cache.
--  objects
--    mpcIngressCacheDestInetworkAddrType, mpcIngressCacheDestAddr, 
--    mpcIngressCachePrefixLen, mpcIngressCacheDestAtmAddr, 
--    mpcIngressCacheSrcAtmAddr, mpcIngressCacheEntryState, 
--    mpcIngressCacheEgressCacheTagValid, 
--    mpcIngressCacheEgressCacheTag, mpcIngressCacheLastNhrpCieCode, 
--    mpcIngressCacheSigErrCode, mpcIngressCacheRetries, 
--    mpcIngressCacheTimeUntilNextResolutionRequest, 
--    mpcIngressCacheHoldingTime, mpcIngressCacheServiceCategory

mpcEgressCacheTotalPacketGroup OBJECT IDENTIFIER ::= { mpoaMIBGroups 14 }
-- OBJECT-GROUP
--  Status
--    mandatory
--  Descr
--    A collection of objects which count the total
--    number of packets received by MPC short cuts.
--  objects
--    mpcEgressCacheRxTotalPackets

mpcEgressCacheTotalOctetGroup OBJECT IDENTIFIER ::= { mpoaMIBGroups 15 }
-- OBJECT-GROUP
--  Status
--    mandatory
--  Descr
--    A collection of objects which count the total
--    number of octets received by MPC short cuts.
--  objects
--    mpcEgressCacheRxTotalOctets

mpcEgressCacheGroup OBJECT IDENTIFIER ::= { mpoaMIBGroups 16 }
-- OBJECT-GROUP
--  Status
--    mandatory
--  Descr
--    A collection of objects used to monitor the
--    MPOA egress cache.
--  objects
--    mpcEgressCacheId, mpcEgressCacheInetworkAddrType, 
--    mpcEgressCacheIDestAddr, mpcEgressCachePrefixLen, 
--    mpcEgressCacheEntryState, mpcEgressCacheEgressCacheTagValid, 
--    mpcEgressCacheEgressCacheTag, mpcEgressCacheHoldTime, 
--    mpcEgressCacheDataLinkHeader, 
--    mpcEgressCacheIngressMpcDataAtmAddr, mpcEgressCacheLecIndex, 
--    mpcEgressCacheServiceCategory

mpsConfigGroup OBJECT IDENTIFIER ::= { mpoaMIBGroups 17 }
-- OBJECT-GROUP
--  Status
--    mandatory
--  Descr
--    A collection of objects used for creating and
--    configuring MPOA Servers.
--  objects
--    mpsNextIndex, mpsRowStatus, mpsConfigMode, mpsCtrlAtmAddr, 
--    mpsKeepAliveTime, mpsKeepAliveLifeTime, mpsInitialRetryTime, 
--    mpsRetryTimeMaximum, mpsGiveupTime, mpsDefaultHoldingTime

mpsActualGroup OBJECT IDENTIFIER ::= { mpoaMIBGroups 18 }
-- OBJECT-GROUP
--  Status
--    mandatory
--  Descr
--    A collection of objects describing the status
--    and operational parameters of the managed MPS.
--  objects
--    mpsActualState, mpsDiscontinuityTime, mpsActualConfigMode, 
--    mpsActualKeepAlive, mpsActualKeepAliveLifeTime, 
--    mpsActualInitialRetryTime, mpsActualRetryTimeMaximum, 
--    mpsActualGiveupTime, mpsActualDefaultHoldingTime

mpsStatisticsGroup OBJECT IDENTIFIER ::= { mpoaMIBGroups 19 }
-- OBJECT-GROUP
--  Status
--    mandatory
--  Descr
--    A collection of objects that provide statistics
--    on the MPOA Server protocol parameters.
--  objects
--    mpsStatRxMpoaResolveRequests, mpsStatTxMpoaResolveReplyAcks, 
--    mpsStatTxMpoaResolveReplyInsufECResources, 
--    mpsStatTxMpoaResolveReplyInsufSCResources, 
--    mpsStatTxMpoaResolveReplyInsufEitherResources, 
--    mpsStatTxMpoaResolveReplyUnsupportedInetProt, 
--    mpsStatTxMpoaResolveReplyUnsupportedMacEncaps, 
--    mpsStatTxMpoaResolveReplyUnspecifiedOther, 
--    mpsStatTxMpoaResolveReplyOther, mpsStatGiveupTimeExpireds, 
--    mpsStatTxMpoaImpRequests, mpsStatRxMpoaImpReplyAcks, 
--    mpsStatRxMpoaImpReplyInsufECResources, 
--    mpsStatRxMpoaImpReplyInsufSCResources, 
--    mpsStatRxMpoaImpReplyInsufEitherResources, 
--    mpsStatRxMpoaImpReplyUnsupportedInetProt, 
--    mpsStatRxMpoaImpReplyUnsupportedMacEncaps, 
--    mpsStatRxMpoaImpReplyUnspecifiedOther, 
--    mpsStatRxMpoaImpReplyOther, 
--    mpsStatRxMpoaEgressCachePurgeRequests, 
--    mpsStatTxMpoaEgressCachePurgeReplies, mpsStatTxMpoaTriggers, 
--    mpsStatTxNhrpResolveRequests, mpsStatRxNhrpResolveReplies, 
--    mpsStatRxNhrpResolveRequests, mpsStatTxNhrpResolveReplies

mpsProtocolGroup OBJECT IDENTIFIER ::= { mpoaMIBGroups 20 }
-- OBJECT-GROUP
--  Status
--    mandatory
--  Descr
--    A collection of objects to specify which
--    parameters this MPS is enabled for.
--  objects
--    mpsLECSValue, mpsProtocolRowStatus

mpsMappingGroup OBJECT IDENTIFIER ::= { mpoaMIBGroups 21 }
-- OBJECT-GROUP
--  Status
--    mandatory
--  Descr
--    A collection of objects to map from MPSs to LECs.
--  objects
--    mpsMappingRowStatus, mpsMappingIndex

mpsMpcGroup OBJECT IDENTIFIER ::= { mpoaMIBGroups 22 }
-- OBJECT-GROUP
--  Status
--    mandatory
--  Descr
--    A collection of objects which aid the MPSs to track
--    information for all the MPCs which are known by the
--    MPSs.
--  objects
--    mpsMpcCtrlAtmAddr

mpsIngressCacheGroup OBJECT IDENTIFIER ::= { mpoaMIBGroups 23 }
-- OBJECT-GROUP
--  Status
--    mandatory
--  Descr
--    A collection of objects to monitor the MPS
--    ingress cache.
--  objects
--    mpsIngressCacheDestInternetworkAddrType, 
--    mpsIngressCacheDestAddr, mpsIngressCachePrefixLen, 
--    mpsIngressCacheEntryState, 
--    mpsIngressCacheSrcInternetworkAddrType, 
--    mpsIngressCacheSrcAddr, mpsIngressCacheSourceMpcCtrlAtmAddr, 
--    mpsIngressCacheResolvedAtmAddr, mpsIngressCacheHoldTime, 
--    mpsIngressCacheMpoaRequestId, mpsIngressCacheNhrpRequestId, 
--    mpsIngressCacheServiceCategory

mpsEgressCacheGroup OBJECT IDENTIFIER ::= { mpoaMIBGroups 24 }
-- OBJECT-GROUP
--  Status
--    mandatory
--  Descr
--    A collection of objects to monitor MPS's egress
--    cache parameters.
--  objects
--    mpsEgressCacheId, mpsEgressCacheDestInternetworkAddrType, 
--    mpsEgressCacheDestAddr, mpsEgressCachePrefixLen, 
--    mpsEgressCacheHoldTime, mpsEgressCacheEntryState, 
--    mpsEgressCacheDataLinkHeader, mpsEgressCacheElanId, 
--    mpsEgressCacheSourceClientAtmAddr, 
--    mpsEgressCacheNhrpRequestId, mpsEgressCacheMpoaRequestId, 
--    mpsEgressCacheServiceCategory, 
--    mpsEgressCacheNextHopInternetworkAddrType, 
--    mpsEgressCacheNextHopAddr

mpoaMpcMibBasicCompliance OBJECT IDENTIFIER ::= { mpoaMIBCompliances 1 }
-- MODULE-COMPLIANCE
--  Status
--    mandatory
--  Descr
--    The basic implementation requirements for SNMP entities
--    which support MPOA Clients.
--  Module
--    >>current<<
--   MandGroup
--    mpcConfigGroup
--   MandGroup
--    mpcActualGroup
--   MandGroup
--    mpcDataAtmAddressGroup
--   MandGroup
--    mpcStatisticsGroup
--   MandGroup
--    mpcProtocolGroup
--   MandGroup
--    mpcMpsGroup
--   MandGroup
--    mpcMpsMacAddressGroup
--   MandGroup
--    mpcIngressCacheGroup
--   MandGroup
--    mpcEgressCacheGroup
--   ObjVar
--    mpcRowStatus
--   ObjVar
--    mpcDataAtmAddressRowStatus
--   ObjVar
--    mpcProtocolRowStatus
--   OptGroup
--    mpcMappingGroup
--   ObjVar
--    mpcMappingRowStatus
--   ObjVar
--    mpcMappingIndex

mpoaMpcMibAdvancedCompliance OBJECT IDENTIFIER ::= { mpoaMIBCompliances 2 }
-- MODULE-COMPLIANCE
--  Status
--    mandatory
--  Descr
--    The advanced implementation requirements for SNMP entities
--    which support MPOA Clients.
--  Module
--    >>current<<
--   MandGroup
--    mpoaDeviceTypeGroup
--   MandGroup
--    mpoaDeviceTypeMpsMacGroup
--   MandGroup
--    mpcConfigGroup
--   MandGroup
--    mpcActualGroup
--   MandGroup
--    mpcDataAtmAddressGroup
--   MandGroup
--    mpcStatisticsGroup
--   MandGroup
--    mpcProtocolGroup
--   MandGroup
--    mpcMpsGroup
--   MandGroup
--    mpcMpsMacAddressGroup
--   MandGroup
--    mpcIngressCacheTotalPacketGroup
--   MandGroup
--    mpcIngressCacheGroup
--   MandGroup
--    mpcEgressCacheTotalPacketGroup
--   MandGroup
--    mpcEgressCacheGroup
--   ObjVar
--    mpcRowStatus
--   ObjVar
--    mpcDataAtmAddressRowStatus
--   ObjVar
--    mpcProtocolRowStatus
--   OptGroup
--    mpcMappingGroup
--   ObjVar
--    mpcMappingRowStatus
--   ObjVar
--    mpcMappingIndex

mpoaMpcMibAdvancedPlusOctetsCompliance OBJECT IDENTIFIER ::= { mpoaMIBCompliances 3 }
-- MODULE-COMPLIANCE
--  Status
--    mandatory
--  Descr
--    The AdvancedPlusOctets implementation requirements for SNMP
--    entities
--    which support MPOA Clients.  This includes supporting
--    the 64 bit octet counters.
--  Module
--    >>current<<
--   MandGroup
--    mpoaDeviceTypeGroup
--   MandGroup
--    mpoaDeviceTypeMpsMacGroup
--   MandGroup
--    mpcConfigGroup
--   MandGroup
--    mpcActualGroup
--   MandGroup
--    mpcDataAtmAddressGroup
--   MandGroup
--    mpcStatisticsGroup
--   MandGroup
--    mpcProtocolGroup
--   MandGroup
--    mpcMpsGroup
--   MandGroup
--    mpcMpsMacAddressGroup
--   MandGroup
--    mpcIngressCacheTotalPacketGroup
--   MandGroup
--    mpcIngressCacheTotalOctetGroup
--   MandGroup
--    mpcIngressCacheGroup
--   MandGroup
--    mpcEgressCacheTotalPacketGroup
--   MandGroup
--    mpcEgressCacheTotalOctetGroup
--   MandGroup
--    mpcEgressCacheGroup
--   ObjVar
--    mpcRowStatus
--   ObjVar
--    mpcDataAtmAddressRowStatus
--   ObjVar
--    mpcProtocolRowStatus
--   OptGroup
--    mpcMappingGroup
--   ObjVar
--    mpcMappingRowStatus
--   ObjVar
--    mpcMappingIndex

mpoaMpsMibBasicCompliance OBJECT IDENTIFIER ::= { mpoaMIBCompliances 4 }
-- MODULE-COMPLIANCE
--  Status
--    mandatory
--  Descr
--    The implementation requirements for SNMP entities
--    which support MPOA Servers.
--  Module
--    >>current<<
--   MandGroup
--    mpsConfigGroup
--   MandGroup
--    mpsActualGroup
--   MandGroup
--    mpsStatisticsGroup
--   MandGroup
--    mpsProtocolGroup
--   MandGroup
--    mpsIngressCacheGroup
--   MandGroup
--    mpsEgressCacheGroup
--   ObjVar
--    mpsRowStatus
--   ObjVar
--    mpsProtocolRowStatus
--   OptGroup
--    mpsMappingGroup
--   ObjVar
--    mpsMappingRowStatus

mpoaMpsMibAdvancedCompliance OBJECT IDENTIFIER ::= { mpoaMIBCompliances 5 }
-- MODULE-COMPLIANCE
--  Status
--    mandatory
--  Descr
--    The advanced implementation requirements for SNMP entities
--    which support MPOA Servers.
--  Module
--    >>current<<
--   MandGroup
--    mpoaDeviceTypeGroup
--   MandGroup
--    mpoaDeviceTypeMpsMacGroup
--   MandGroup
--    mpsConfigGroup
--   MandGroup
--    mpsActualGroup
--   MandGroup
--    mpsStatisticsGroup
--   MandGroup
--    mpsProtocolGroup
--   MandGroup
--    mpsIngressCacheGroup
--   MandGroup
--    mpsEgressCacheGroup
--   ObjVar
--    mpsRowStatus
--   ObjVar
--    mpsProtocolRowStatus
--   OptGroup
--    mpsMappingGroup
--   ObjVar
--    mpsMappingRowStatus


END

-- MIB created 7/02/98 13:15:10, by
--   SMIC (the next generation) version 1.6.31, December 11, 1994.

ATM-SOFT-PVC-MIB DEFINITIONS ::= BEGIN

-- From file: "af-pnni-0066_000.mib"
-- Compile options "G P A"

IMPORTS
--    enterprises
--            FROM RFC1155-SMI
    Counter32, Gauge32
            FROM SNMPv2-SMI-v1
    OBJECT-TYPE
            FROM RFC-1212
    TRAP-TYPE
            FROM RFC-1215
    RowStatus, TruthValue, TimeStamp
            FROM SNMPv2-TC-v1
    ifIndex
            FROM RFC1213-MIB
    atmForumNetworkManagement       FROM LAN-EMULATION-CLIENT-MIB
    atmVplVpi, atmVclVpi, atmVclVci
            FROM ATM-MIB;

-- MODULE-IDENTITY
--  LastUpdated
--    9606210000Z
--  OrgName
--    The ATM Forum.
--  ContactInfo
--    The ATM Forum
--    2570 West El Camino Real, Suite 304
--    Mountain View, CA 94040-1313 USA
--    Phone: +1 415-949-6700
--    Fax:  +1 415-949-6705
--    info@atmforum.com
--  Descr
--    ATM Soft PVC MIB
--  RevDate
--    9606210000Z
--  RevDescr
--    Initial version of this MIB module.

-- atmForum        OBJECT IDENTIFIER ::= { enterprises 353 }
-- atmForumNetworkManagement OBJECT IDENTIFIER ::= { atmForum 5 }
atmfSoftPvc     OBJECT IDENTIFIER ::= { atmForumNetworkManagement 5 }
atmSoftPvcMIB OBJECT IDENTIFIER ::= { atmfSoftPvc 1 }
atmSoftPvcMIBObjects OBJECT IDENTIFIER ::= { atmSoftPvcMIB 1 }
atmSoftPvcMIBTraps OBJECT IDENTIFIER ::= { atmSoftPvcMIB 2 }
atmSoftPvcBaseGroup OBJECT IDENTIFIER ::= { atmSoftPvcMIBObjects 1 }
atmSoftPvcTraps OBJECT IDENTIFIER ::= { atmSoftPvcMIBTraps 1 }
atmSoftPvcTrapsPrefix OBJECT IDENTIFIER ::= { atmSoftPvcTraps 0 }
atmSoftPvcMIBConformance OBJECT IDENTIFIER ::= { atmSoftPvcMIB 3 }
atmSoftPvcMIBCompliances OBJECT IDENTIFIER ::= { atmSoftPvcMIBConformance 1 }
atmSoftPvcMIBGroups OBJECT IDENTIFIER ::= { atmSoftPvcMIBConformance 2 }

AtmAddr ::= OCTET STRING(SIZE(0..20))
-- AtmAddr ::= OCTET STRING(SIZE(0 | 8 | 20))
-- TEXTUAL-CONVENTION
--  Status
--    mandatory
--  Descr
--    The ATM address used by the network entity.
--    The address types are: no address (0 octets),
--    E.164 (8 octets)and NSAP (20 octets).
--    Note: The E.164 address is encoded in BCD format.

atmSoftPvcCallFailuresTrapEnable OBJECT-TYPE
    SYNTAX TruthValue
--    Rsyntax INTEGER {
--        true(1),
--        false(2)
--        }
    ACCESS read-write
    STATUS mandatory
    DESCRIPTION
        "Allows the generation of traps in response to call
        failures. By default, this object is set to 'false'."
    ::= { atmSoftPvcBaseGroup 1 }

atmSoftPvcCallFailures OBJECT-TYPE
    SYNTAX Counter32
    ACCESS read-only
    STATUS mandatory
    DESCRIPTION
        "The number of times a series of call attempts has failed to
        establish a Soft PVCC or Soft PVPC. The number of call
        attempts in a series is determined by
        atmSoftPVccRetryThreshold or atmSoftPVpcRetryThreshold,
        respectively."
    ::= { atmSoftPvcBaseGroup 2 }

atmSoftPvcCurrentlyFailingSoftPVccs OBJECT-TYPE
    SYNTAX Gauge32
    ACCESS read-only
    STATUS mandatory
    DESCRIPTION
        "The current number of Soft PVCCs for which there is
        an active row in the atmSoftPVccTable having an
        atmSoftPVccOperStatus with a value other than 'connected'."
    ::= { atmSoftPvcBaseGroup 3 }

atmSoftPvcCurrentlyFailingSoftPVpcs OBJECT-TYPE
    SYNTAX Gauge32
    ACCESS read-only
    STATUS mandatory
    DESCRIPTION
        "The current number of Soft PVPCs for which there is an
        active row in the atmSoftPVpcTable having an 
        atmSoftPVpcOperStatus with a value other than 'connected'."
    ::= { atmSoftPvcBaseGroup 4 }

atmSoftPvcNotificationInterval OBJECT-TYPE
    SYNTAX INTEGER(0..3600)
--  Units
--    seconds
    ACCESS read-write
    STATUS mandatory
    DESCRIPTION
        "The minimum interval between the sending
        of atmSoftPvcCallFailuresTrap notifications."
    DEFVAL { 30 }
    ::= { atmSoftPvcBaseGroup 5 }

atmSoftPVccTable OBJECT-TYPE
    SYNTAX SEQUENCE OF AtmSoftPVccEntry
    ACCESS not-accessible
    STATUS mandatory
    DESCRIPTION
        "The (conceptual) table used to manage Soft
        Permanent Virtual Channel Connections (Soft PVCCs).
        The Soft PVCC table is applicable only to switches."
    ::= { atmSoftPvcMIBObjects 2 }

atmSoftPVccEntry OBJECT-TYPE
    SYNTAX AtmSoftPVccEntry
    ACCESS not-accessible
    STATUS mandatory
    DESCRIPTION
        "Each entry in this table represents a  Soft
        Permanent Virtual Channel Connection (Soft PVCC)
        originating at a switch interface.
        
        A Soft PVCC is a VCC that is:
          - provisioned at the originating (source)
         interface of the connection
          - established by signalling procedures
         across a network to a destination interface.
        
        A row in the atmVclTable must be created,
        defining a VCL on the source interface, prior to
        creating an atmSoftPVccEntry row. The row in the
        atmVclTable must be active prior to activating the
        atmSoftPVccEntry row.
        
        The contents of this table reflect only the
        characteristics unique to a Soft PVCC. The traffic
        parameters are defined in the VCL row for the source
        interface, as specified in the ATOMMIB (RFC1695) and 
        the forthcoming addition, the Supplemental ATOMMIB.
        
        Note that the atmSigDescrParamTable contains some objects
        such as the AAL parameters, Broadband high layer
        information and Broadband low layer information
        elements which are used to carry end-to-end information.
        For this reason, these objects are not relevant to Soft
        PVCCs.
        
        When a row is made active, an attempt is made
        to set up a switched connection to an interface at
        the destination switch. No objects (other than
        atmSoftPVccRowStatus) can be set while the row is 
        active.
        
        At the destination, the VCL may be defined (but 
        not cross-connected) prior to arrival of the Setup 
        request.
        
        The combination of ifIndex, atmVclVpi, and atmVclVci
        specified in the index clause of this entry serves to
        identify the VCL on the source interface. The
        atmSoftPVccLeafReference object aids in distinguishing
        between leaves of a point-to-multipoint Soft PVCC."
    INDEX { ifIndex, atmVclVpi, atmVclVci, atmSoftPVccLeafReference }
    ::= { atmSoftPVccTable 1 }

AtmSoftPVccEntry ::= SEQUENCE {
    atmSoftPVccLeafReference INTEGER,
    atmSoftPVccTargetAddress AtmAddr,
    atmSoftPVccTargetSelectType INTEGER,
    atmSoftPVccTargetVpi INTEGER,
    atmSoftPVccTargetVci INTEGER,
    atmSoftPVccLastReleaseCause INTEGER,
    atmSoftPVccLastReleaseDiagnostic OCTET STRING,
    atmSoftPVccOperStatus INTEGER,
    atmSoftPVccRestart INTEGER,
    atmSoftPVccRetryInterval INTEGER,
    atmSoftPVccRetryTimer INTEGER,
    atmSoftPVccRetryThreshold INTEGER,
    atmSoftPVccRetryFailures Gauge32,
    atmSoftPVccRetryLimit INTEGER,
    atmSoftPVccRowStatus RowStatus
    }

atmSoftPVccLeafReference OBJECT-TYPE
    SYNTAX INTEGER(1..65535)
    ACCESS not-accessible
    STATUS mandatory
    DESCRIPTION
        "An arbitrary integer which, in the case of the
        source VCL having an atmVclCastType of
        'p2mpRoot', serves to distinguish between the 
        multiple leaves attached to a root of a 
        point-to-multipoint Soft PVCC. If the atmVclCastType 
        is not 'p2mpRoot' the value 1 shall be used."
    ::= { atmSoftPVccEntry 1 }

atmSoftPVccTargetAddress OBJECT-TYPE
    SYNTAX AtmAddr
--    Rsyntax OCTET STRING(SIZE(0 | 8 | 20))
    ACCESS read-write
    STATUS mandatory
    DESCRIPTION
        "The target ATM Address of this Soft PVCC."
    ::= { atmSoftPVccEntry 2 }

atmSoftPVccTargetSelectType OBJECT-TYPE
    SYNTAX INTEGER {
        required(1),
        any(2)
        }
    ACCESS read-write
    STATUS mandatory
    DESCRIPTION
        "Indicates whether the target VPI/VCI values
        are to be used at the destination.
        
        If the value 'any' is specified, the destination
        switch will choose the VPI/VCI values. In such a
        case, once the Soft PVCC atmSoftPVccOperStatus
        value is 'connected', the value of this object
        changes to 'required', such that the same VPI/VCI
        values will continue to be used even if the connection
        is subsequently torn down and re-established. The
        VPI/VCI values chosen will be available for reading in 
        atmSoftPVccTargetVpi and atmSoftPVccTargetVci.
        
        If the value 'required' is specified, then values
        must be supplied for objects atmSoftPVccTargetVpi
        and atmSoftPVccTargetVci prior to activation of the
        row. These values are then to be used at the destination."
    DEFVAL { required }
    ::= { atmSoftPVccEntry 3 }

atmSoftPVccTargetVpi OBJECT-TYPE
    SYNTAX INTEGER(0..4095)
    ACCESS read-write
    STATUS mandatory
    DESCRIPTION
        "The VPI value of the VCL used at the target interface.
        This value is not relevant when the value of 
        atmSoftPVccTargetSelectType is 'any'."
    DEFVAL { 0 }
    ::= { atmSoftPVccEntry 4 }

atmSoftPVccTargetVci OBJECT-TYPE
    SYNTAX INTEGER(0..65535)
    ACCESS read-write
    STATUS mandatory
    DESCRIPTION
        "The VCI value of the VCL used at the target interface.
        This value must be filled in when the
        atmSoftPVccTargetSelectType is set to 'required'.This 
        value is not relevant when the value of 
        atmSoftPVccTargetSelectType is 'any'."
    ::= { atmSoftPVccEntry 5 }

atmSoftPVccLastReleaseCause OBJECT-TYPE
    SYNTAX INTEGER(1..127)
    ACCESS read-only
    STATUS mandatory
    DESCRIPTION
        "Value of the Cause field of the Cause
        Information Element in the last RELEASE
        signalling message received for this Soft PVCC.
        Indicates the reason for the Release."
    ::= { atmSoftPVccEntry 6 }

atmSoftPVccLastReleaseDiagnostic OBJECT-TYPE
    SYNTAX OCTET STRING(SIZE(0..8))
    ACCESS read-only
    STATUS mandatory
    DESCRIPTION
        "Value of the first 8 bytes of diagnostic information
        from the Cause field of the Cause Information Element
        in the last RELEASE signalling message received for
        this Soft PVCC."
    ::= { atmSoftPVccEntry 7 }

atmSoftPVccOperStatus OBJECT-TYPE
    SYNTAX INTEGER {
        other(1),
        establishmentInProgress(2),
        connected(3),
        retriesExhausted(4)
        }
    ACCESS read-only
    STATUS mandatory
    DESCRIPTION
        "Describes the status of the Soft PVCC. When the
        row is not 'active', the value of this
        object is 'other'."
    ::= { atmSoftPVccEntry 8 }

atmSoftPVccRestart OBJECT-TYPE
    SYNTAX INTEGER {
        restart(1),
        noop(2)
        }
    ACCESS read-write
    STATUS mandatory
    DESCRIPTION
        "When the value is set to 'restart' the Soft PVCC
        is released if necessary and a new setup procedure
        is begun. As a result of this action, the
        atmSoftPVccOperStatus object transitions to
        'establishmentInProgress' (if not already in this state)
        and the atmSoftPVccRetryFailures object is cleared
        
        When the value is set to 'noop' no operation is
        performed. When read, the value 'noop' is returned."
    ::= { atmSoftPVccEntry 9 }

atmSoftPVccRetryInterval OBJECT-TYPE
    SYNTAX INTEGER(0..3600)
--  Units
--    seconds
    ACCESS read-write
    STATUS mandatory
    DESCRIPTION
        "Defines the period to wait before attempting
        to establish the Soft PVC after the first failed call
        attempt.  Zero represents an infinite interval indicating no
        retries."
    DEFVAL { 10 }
    ::= { atmSoftPVccEntry 10 }

atmSoftPVccRetryTimer OBJECT-TYPE
    SYNTAX INTEGER(0..86400)
--  Units
--    seconds
    ACCESS read-only
    STATUS mandatory
    DESCRIPTION
        "Indicates the current value of the retry timer for
        this connection. When the value reaches zero an attempt
        will be made to establish the Soft PVCC. When the timer
        is not running, the value zero shall be returned."
    ::= { atmSoftPVccEntry 11 }

atmSoftPVccRetryThreshold OBJECT-TYPE
    SYNTAX INTEGER(0..65535)
    ACCESS read-write
    STATUS mandatory
    DESCRIPTION
        "Indicates the number of consecutive call setup attempts for
        the same Soft PVCC which need to fail before the
        atmSoftPvcCallFailures object is incremented. A value of
        zero indicates that an infinite number of call attempts
        are required to increment the atmSoftPvcCallFailures object
        and thus disables alarms for the Soft PVCC."
    DEFVAL { 1 }
    ::= { atmSoftPVccEntry 12 }

atmSoftPVccRetryFailures OBJECT-TYPE
    SYNTAX Gauge32
    ACCESS read-only
    STATUS mandatory
    DESCRIPTION
        "Indicates how many attempts to establish the connection
        have failed.  This count is reset whenever a connection
        is successfully established or the Soft PVCC is restarted."
    ::= { atmSoftPVccEntry 13 }

atmSoftPVccRetryLimit OBJECT-TYPE
    SYNTAX INTEGER(0..65535)
    ACCESS read-write
    STATUS mandatory
    DESCRIPTION
        "Sets a maximum limit on how many consecutive unsuccessful
        call setup attempts can be made before stopping the attempt
        to set up the connection. If this limit is reached then
        management action will be required (e.g. setting 
        atmSoftPVccRestart to 'restart') to initiate a new attempt
        to establish the connection. A value of zero indicates
        no limit - the attempts will continue until successful."
    DEFVAL { 0 }
    ::= { atmSoftPVccEntry 14 }

atmSoftPVccRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Used to create and delete a Soft PVCC. When this
        object is set to 'active' an attempt is made to
        set up the Soft PVCC. When this object has the value
        'active' and is set to another value, any
        set-up or connection in-progress is released."
    ::= { atmSoftPVccEntry 15 }

atmSoftPVpcTable OBJECT-TYPE
    SYNTAX SEQUENCE OF AtmSoftPVpcEntry
    ACCESS not-accessible
    STATUS mandatory
    DESCRIPTION
        "The (conceptual) table used to manage Soft
        Permanent Virtual Path Connections (Soft PVPCs)
        The Soft PVPC table is applicable only to switches."
    ::= { atmSoftPvcMIBObjects 3 }

atmSoftPVpcEntry OBJECT-TYPE
    SYNTAX AtmSoftPVpcEntry
    ACCESS not-accessible
    STATUS mandatory
    DESCRIPTION
        "Each entry in this table represents a  Soft
        Permanent Virtual Path Connection (Soft PVPC)
        originating at a switch interface.
        
        A Soft PVPC is a VPC that is:
          - provisioned at the originating (source)
         interface of the connection
          - established by signalling procedures
         across a network to a destination interface.
        
        A row in the atmVplTable must be created,
        defining a VPL on the source interface, prior to
        creating an atmSoftPVpcEntry row. The row in the
        atmVplTable must be active prior to activating the
        atmSoftPVpcEntry row.
        
        The contents of this table reflect only the
        characteristics unique to a Soft PVPC. The traffic
        parameters are defined in the VPL row for the source
        interface, as specified in the ATOMMIB (RFC1695) and
        the forthcoming addition, the Supplemental ATOMMIB.
        
        Note that the atmSigDescrParamTable contains some
        objects such as the AAL parameters, Broadband high
        layer information, and Broadband low layer information
        elements which are used to carry end-to-end information.
        For this reason, these objects are not relevant to Soft
        PVPCs.
        
        When a row is made active, an attempt is made
        to set up a switched connection to an interface at
        the destination switch. No objects (other than
        atmSoftPVpcRowStatus) can be set while the row is
        active.
        
        At the destination, the VPL may be defined (but
        not cross-connected) prior to arrival of the Setup
        request.
        
        The combination of ifIndex, atmVplVpi specified
        in the index clause of this entry serves to
        identify the VPL on the source interface. The
        atmSoftPVpcLeafReference object aids in distinguishing
        between leaves of a point-to-multipoint Soft PVPC."
    INDEX { ifIndex, atmVplVpi, atmSoftPVpcLeafReference }
    ::= { atmSoftPVpcTable 1 }

AtmSoftPVpcEntry ::= SEQUENCE {
    atmSoftPVpcLeafReference INTEGER,
    atmSoftPVpcTargetAddress AtmAddr,
    atmSoftPVpcTargetSelectType INTEGER,
    atmSoftPVpcTargetVpi INTEGER,
    atmSoftPVpcLastReleaseCause INTEGER,
    atmSoftPVpcLastReleaseDiagnostic OCTET STRING,
    atmSoftPVpcOperStatus INTEGER,
    atmSoftPVpcRestart INTEGER,
    atmSoftPVpcRetryInterval INTEGER,
    atmSoftPVpcRetryTimer INTEGER,
    atmSoftPVpcRetryThreshold INTEGER,
    atmSoftPVpcRetryFailures Gauge32,
    atmSoftPVpcRetryLimit INTEGER,
    atmSoftPVpcRowStatus RowStatus
    }

atmSoftPVpcLeafReference OBJECT-TYPE
    SYNTAX INTEGER(1..63535)
    ACCESS not-accessible
    STATUS mandatory
    DESCRIPTION
        "An arbitrary integer which, in the case of the
        source VPL having a atmVplCastType of
        'p2mpRoot', serves to distinguish between the
        multiple leaves attached to a root of a
        point-to-multipoint Soft PVPC.
        
        If the atmVplCastType is not 'p2mpRoot', the
        value 1 shall be used."
    ::= { atmSoftPVpcEntry 1 }

atmSoftPVpcTargetAddress OBJECT-TYPE
    SYNTAX AtmAddr
--    Rsyntax OCTET STRING(SIZE(0 | 8 | 20))
    ACCESS read-write
    STATUS mandatory
    DESCRIPTION
        "The target ATM Address of this Soft PVPC."
    ::= { atmSoftPVpcEntry 2 }

atmSoftPVpcTargetSelectType OBJECT-TYPE
    SYNTAX INTEGER {
        required(1),
        any(2)
        }
    ACCESS read-write
    STATUS mandatory
    DESCRIPTION
        "Indicates whether the target VPI value
        is to be used at the destination.
        If the value 'any' is specified, the
        destination switch will choose the VPI
        value. In such a case, once the Soft PVPC
        atmSoftPVpcOperStatus value is 'connected',
        the value of this object changes to 'required',
        such that the same VPI value will continue to
        be used even if the connection is subsequently
        torn down and re-established. The VPI value
        chosen will be available for reading in
        atmSoftPVpcTargetVpi.
        
        If the value 'required' is specified, then
        a value must be supplied for object
        atmSoftPVpcTargetVpi prior to activation
        of the row. This value is then to be used
        at the destination."
    DEFVAL { required }
    ::= { atmSoftPVpcEntry 3 }

atmSoftPVpcTargetVpi OBJECT-TYPE
    SYNTAX INTEGER(0..4095)
    ACCESS read-write
    STATUS mandatory
    DESCRIPTION
        "The VPI value of the VPL used at the
        target interface.
        
        This value must be filled in when the
        atmSoftPVpcTargetSelectType is set to 'required'.
        This value is not relevant when the value of
        atmSoftPVpcTargetSelectType is 'any'."
    ::= { atmSoftPVpcEntry 4 }

atmSoftPVpcLastReleaseCause OBJECT-TYPE
    SYNTAX INTEGER(1..127)
    ACCESS read-only
    STATUS mandatory
    DESCRIPTION
        "Value of the Cause field of the Cause
        Information Element in the last RELEASE
        signalling message received for this Soft PVPC.
        Indicates the reason for the Release."
    ::= { atmSoftPVpcEntry 5 }

atmSoftPVpcLastReleaseDiagnostic OBJECT-TYPE
    SYNTAX OCTET STRING(SIZE(0..8))
    ACCESS read-only
    STATUS mandatory
    DESCRIPTION
        "Value of the first 8 bytes of diagnostic information
        from the Cause field of the Cause Information Element
        in the last RELEASE signalling message received for
        this Soft PVPC."
    ::= { atmSoftPVpcEntry 6 }

atmSoftPVpcOperStatus OBJECT-TYPE
    SYNTAX INTEGER {
        other(1),
        establishmentInProgress(2),
        connected(3),
        retriesExhausted(4)
        }
    ACCESS read-only
    STATUS mandatory
    DESCRIPTION
        "Describes the status of the Soft PVPC. When the
        row is not 'active', the value of this
        object is 'other'."
    ::= { atmSoftPVpcEntry 7 }

atmSoftPVpcRestart OBJECT-TYPE
    SYNTAX INTEGER {
        restart(1),
        noop(2)
        }
    ACCESS read-write
    STATUS mandatory
    DESCRIPTION
        "When the value is set to 'restart', the Soft PVPC is
        released if necessary and a new setup procedure is begun.
        As a result of this action, the atmSoftPVpcOperStatus
        object transitions to 'establishmentInProgress' (if not
        already in this state) and the atmSoftPVpcRetryFailures
        object is cleared.
        
        When the value is set to 'noop', no operation is performed.
        When read, the value 'noop' is returned."
    ::= { atmSoftPVpcEntry 8 }

atmSoftPVpcRetryInterval OBJECT-TYPE
    SYNTAX INTEGER(0..3600)
--  Units
--    seconds
    ACCESS read-write
    STATUS mandatory
    DESCRIPTION
        "Defines the period to wait before attempting
        to establish the Soft PVPC connection after the first
        failed call attempt.  Zero represents an infinite
        interval indicating no retries."
    DEFVAL { 10 }
    ::= { atmSoftPVpcEntry 9 }

atmSoftPVpcRetryTimer OBJECT-TYPE
    SYNTAX INTEGER(0..86400)
--  Units
--    seconds
    ACCESS read-only
    STATUS mandatory
    DESCRIPTION
        "Indicates the current value of the retry timer for
        this connection. When the value reaches zero an attempt
        will be made to establish the Soft PVPC. When the
        timer is not running, the value zero shall be returned."
    ::= { atmSoftPVpcEntry 10 }

atmSoftPVpcRetryThreshold OBJECT-TYPE
    SYNTAX INTEGER(0..65535)
    ACCESS read-write
    STATUS mandatory
    DESCRIPTION
        "Indicates the number of consecutive call setup attempts for
        the same Soft PVPC which need to fail before the
        atmSoftPvcCallFailures object is incremented. A value of
        zero indicates that an infinite number of call attempts
        are required to increment the atmSoftPvcCallFailures object
        and thus disables alarms for the Soft PVPC."
    DEFVAL { 1 }
    ::= { atmSoftPVpcEntry 11 }

atmSoftPVpcRetryFailures OBJECT-TYPE
    SYNTAX Gauge32
    ACCESS read-only
    STATUS mandatory
    DESCRIPTION
        "Indicates how many attempts to establish the connection
        have failed.  This count is reset whenever a connection
        is successfully established or the Soft PVPC is restarted."
    ::= { atmSoftPVpcEntry 12 }

atmSoftPVpcRetryLimit OBJECT-TYPE
    SYNTAX INTEGER(0..65535)
    ACCESS read-write
    STATUS mandatory
    DESCRIPTION
        "Sets a maximum limit on how many consecutive unsuccessful
        call setup attempts can be made before stopping the attempt
        to set up the connection. If this limit is reached then
        management action will be required (e.g. setting
        atmSoftPVpcRestart to 'restart') to initiate a new attempt
        to establish the connection. A value of zero indicates no
        limit - the attempts will continue until successful."
    DEFVAL { 0 }
    ::= { atmSoftPVpcEntry 13 }

atmSoftPVpcRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Used to create and delete a Soft PVPC. When this
        object is set to 'active' an attempt is made to
        set up the Soft PVPC. When this object has the value
        'active' and is set to another value, any
        set-up or connection in-progress is released."
    ::= { atmSoftPVpcEntry 14 }

atmInterfaceSoftPvcAddressTable OBJECT-TYPE
    SYNTAX SEQUENCE OF AtmInterfaceSoftPvcAddressEntry
    ACCESS not-accessible
    STATUS mandatory
    DESCRIPTION
        "This table is used to configure ATM addresses at 
        an ATM interface on this node prior to setting up
        Soft PVPCs or Soft PVPCs at that interface."
    ::= { atmSoftPvcMIBObjects 4 }

atmInterfaceSoftPvcAddressEntry OBJECT-TYPE
    SYNTAX AtmInterfaceSoftPvcAddressEntry
    ACCESS not-accessible
    STATUS mandatory
    DESCRIPTION
        "ATM address entry for configuring Soft PVCCs or
        Soft PVPCs at an ATM interface."
    INDEX { ifIndex, atmInterfaceSoftPvcAddress }
    ::= { atmInterfaceSoftPvcAddressTable 1 }

AtmInterfaceSoftPvcAddressEntry ::= SEQUENCE {
    atmInterfaceSoftPvcAddress AtmAddr,
    atmInterfaceSoftPvcAddressRowStatus RowStatus
    }

atmInterfaceSoftPvcAddress OBJECT-TYPE
    SYNTAX AtmAddr
--    Rsyntax OCTET STRING(SIZE(0 | 8 | 20))
    ACCESS not-accessible
    STATUS mandatory
    DESCRIPTION
        "Specifies the address that can be used to establish a Soft
        PVCC or Soft PVPC to this interface."
    ::= { atmInterfaceSoftPvcAddressEntry 1 }

atmInterfaceSoftPvcAddressRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Used to create and delete an ATM address at this interface
        for setting up Soft PVCCs or Soft PVPCs."
    ::= { atmInterfaceSoftPvcAddressEntry 2 }

atmCurrentlyFailingSoftPVccTable OBJECT-TYPE
    SYNTAX SEQUENCE OF AtmCurrentlyFailingSoftPVccEntry
    ACCESS not-accessible
    STATUS mandatory
    DESCRIPTION
        "A table indicating all Soft Permanent Virtual Channel
        Connections (Soft PVCCs) for which the atmSoftPVccRowStatus
        is 'active' and the atmSoftPVccOperStatus is other than
        'connected'."
    ::= { atmSoftPvcMIBObjects 5 }

atmCurrentlyFailingSoftPVccEntry OBJECT-TYPE
    SYNTAX AtmCurrentlyFailingSoftPVccEntry
    ACCESS not-accessible
    STATUS mandatory
    DESCRIPTION
        "Each entry in this table represents a Soft Permanent
        Virtual Channel Connection (Soft PVCC) for which the
        atmSoftPVccRowStatus is 'active' and the 
        atmSoftPVccOperStatus is other than 'connected'."
    INDEX { ifIndex, atmVclVpi, atmVclVci, atmSoftPVccLeafReference }
    ::= { atmCurrentlyFailingSoftPVccTable 1 }

AtmCurrentlyFailingSoftPVccEntry ::= SEQUENCE {
    atmCurrentlyFailingSoftPVccTimeStamp TimeStamp
    }

atmCurrentlyFailingSoftPVccTimeStamp OBJECT-TYPE
    SYNTAX TimeStamp
--    Rsyntax TimeTicks
    ACCESS read-only
    STATUS mandatory
    DESCRIPTION
        "The time at which this Soft PVCC began to fail."
    ::= { atmCurrentlyFailingSoftPVccEntry 1 }

atmCurrentlyFailingSoftPVpcTable OBJECT-TYPE
    SYNTAX SEQUENCE OF AtmCurrentlyFailingSoftPVpcEntry
    ACCESS not-accessible
    STATUS mandatory
    DESCRIPTION
        "A table indicating all Soft Permanent Virtual Path
        Connections (Soft PVPCs) for which the atmSoftPVpcRowStatus
        is 'active' and the atmSoftPVpcOperStatus is other than
        'connected'."
    ::= { atmSoftPvcMIBObjects 6 }

atmCurrentlyFailingSoftPVpcEntry OBJECT-TYPE
    SYNTAX AtmCurrentlyFailingSoftPVpcEntry
    ACCESS not-accessible
    STATUS mandatory
    DESCRIPTION
        "Each entry in this table represents a Soft Permanent
        Virtual Path Connection (Soft PVPC) for which the
        atmSoftPVpcRowStatus is 'active' and the 
        atmSoftPVpcOperStatus is other than 'connected'."
    INDEX { ifIndex, atmVclVpi, atmSoftPVpcLeafReference }
    ::= { atmCurrentlyFailingSoftPVpcTable 1 }

AtmCurrentlyFailingSoftPVpcEntry ::= SEQUENCE {
    atmCurrentlyFailingSoftPVpcTimeStamp TimeStamp
    }

atmCurrentlyFailingSoftPVpcTimeStamp OBJECT-TYPE
    SYNTAX TimeStamp
--    Rsyntax TimeTicks
    ACCESS read-only
    STATUS mandatory
    DESCRIPTION
        "The time at which this Soft PVPC began to fail."
    ::= { atmCurrentlyFailingSoftPVpcEntry 1 }

atmSoftPvcCallFailuresTrap TRAP-TYPE
-- Reverse mappable trap
    ENTERPRISE atmSoftPvcTraps
    VARIABLES {
        atmSoftPvcCallFailures, atmSoftPvcCurrentlyFailingSoftPVccs, 
        atmSoftPvcCurrentlyFailingSoftPVpcs }
--  Status
--    mandatory
    DESCRIPTION
        "A notification indicating that one or more series of
        call attempts in trying to establish a Soft PVPC or
        Soft PVCC have failed since the last
        atmSoftPvcCallFailureTrap was sent. If this trap has
        not been sent for the last atmSoftPvcNotificationInterval,
        then it will be sent on the next increment of
        atmSoftPvcCallFailures."
    ::= 1

atmSoftPvcBaseMIBGroup OBJECT IDENTIFIER ::= { atmSoftPvcMIBGroups 1 }
-- OBJECT-GROUP
--  Status
--    mandatory
--  Descr
--    A collection of objects to related to failing
--    Soft PVCCs and Soft PVPCs.
--  objects
--    atmSoftPvcCallFailuresTrapEnable, atmSoftPvcCallFailures, 
--    atmSoftPvcCurrentlyFailingSoftPVccs, 
--    atmSoftPvcCurrentlyFailingSoftPVpcs, 
--    atmSoftPvcNotificationInterval

atmSoftPvcVccMIBGroup OBJECT IDENTIFIER ::= { atmSoftPvcMIBGroups 2 }
-- OBJECT-GROUP
--  Status
--    mandatory
--  Descr
--    A collection of objects managing Soft PVCCs.
--  objects
--    atmSoftPVccTargetAddress, atmSoftPVccTargetSelectType, 
--    atmSoftPVccTargetVpi, atmSoftPVccTargetVci, 
--    atmSoftPVccLastReleaseCause, atmSoftPVccLastReleaseDiagnostic, 
--    atmSoftPVccOperStatus, atmSoftPVccRestart, 
--    atmSoftPVccRetryInterval, atmSoftPVccRetryTimer, 
--    atmSoftPVccRetryThreshold, atmSoftPVccRetryFailures, 
--    atmSoftPVccRetryLimit, atmSoftPVccRowStatus

atmSoftPvcVpcMIBGroup OBJECT IDENTIFIER ::= { atmSoftPvcMIBGroups 3 }
-- OBJECT-GROUP
--  Status
--    mandatory
--  Descr
--    A collection of objects managing Soft PVPCs.
--  objects
--    atmSoftPVpcTargetAddress, atmSoftPVpcTargetSelectType, 
--    atmSoftPVpcTargetVpi, atmSoftPVpcLastReleaseCause, 
--    atmSoftPVpcLastReleaseDiagnostic, atmSoftPVpcOperStatus, 
--    atmSoftPVpcRestart, atmSoftPVpcRetryInterval, 
--    atmSoftPVpcRetryTimer, atmSoftPVpcRetryThreshold, 
--    atmSoftPVpcRetryFailures, atmSoftPVpcRetryLimit, 
--    atmSoftPVpcRowStatus

atmSoftPvcAddressMIBGroup OBJECT IDENTIFIER ::= { atmSoftPvcMIBGroups 4 }
-- OBJECT-GROUP
--  Status
--    mandatory
--  Descr
--    A collection of objects managing interfaces addresses for
--    Soft PVCCs and Soft PVPCs.
--  objects
--    atmInterfaceSoftPvcAddressRowStatus

atmCurrentlyFailingSoftPVccMIBGroup OBJECT IDENTIFIER ::= { atmSoftPvcMIBGroups 5 }
-- OBJECT-GROUP
--  Status
--    mandatory
--  Descr
--    A collection of objects for management of currently
--    failing Soft PVCCs.
--  objects
--    atmCurrentlyFailingSoftPVccTimeStamp

atmCurrentlyFailingSoftPVpcMIBGroup OBJECT IDENTIFIER ::= { atmSoftPvcMIBGroups 6 }
-- OBJECT-GROUP
--  Status
--    mandatory
--  Descr
--    A collection of objects for management of currently
--    failing Soft PVPCs.
--  objects
--    atmCurrentlyFailingSoftPVpcTimeStamp

atmSoftPvcMIBCompliance OBJECT IDENTIFIER ::= { atmSoftPvcMIBCompliances 1 }
-- MODULE-COMPLIANCE
--  Status
--    mandatory
--  Descr
--    The compliance statement for the ATM Soft PVC group.
--  Module
--    >>current<<
--   MandGroup
--    atmSoftPvcBaseMIBGroup
--   MandGroup
--    atmSoftPvcVccMIBGroup
--   MandGroup
--    atmSoftPvcAddressMIBGroup
--   ObjVar
--    atmSoftPVccRetryLimit
--   OptGroup
--    atmSoftPvcVpcMIBGroup
--   ObjVar
--    atmSoftPVpcRetryLimit


END
-- SECTION 1: Top Level Definitions

SYNOPTICS-ROOT-MIB DEFINITIONS ::= BEGIN


-- SynOptics Root MIB Release 1.5.8
-- Revision 9/03/97

-- Copyright 1996, 97 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	enterprises
		FROM RFC1155-SMI;

-- Textual Conventions

SnpxBackplaneType ::= INTEGER {
	other(1),		-- none of the following
	eth(2),			-- ethernet
	ethTok(3),		-- ethernet and tokenring
	ethFddi(4),		-- ethernet and FDDI
	ethTokFddi(5),		-- ethernet, tokenring, and FDDI
	ethTokRed(6),		-- ethernet and tokenring with
				--   redundant powersupply
	ethTokFddiRed(7),	-- ethernet, tokenring, and FDDI
				--   with redundant powersupply
	tok(8),			-- tokenring
        enetTrFastEnet(9),      -- ethernet, tokenring, and fast ethernet
        enetFastEnet(10),       -- ethernet and fast ethernet
        enetTrFastEnetRed(11)   -- ethernet, tokenring, and fast ethernet
                                -- with redundant powersupply
	}
-- This type is used to specify a concentrator backplane.


SnpxChassisType ::= INTEGER {
	other(1),		-- none of the following
	m3000(2),		-- product 3000
	m3030(3),		-- product 3030
	m2310(4),		-- product 2310
	m2810(5),		-- product 2810
	m2912(6),		-- product 2912
	m2914(7),		-- product 2914
	m271x(8),		-- product 271x
	m2813(9),		-- product 2813
	m2814(10),		-- product 2814
	m2915(11),		-- product 2915
	m5000(12),		-- product 5000
	m2813SA(13),		-- product 2813SA
	m2814SA(14),		-- product 2814SA
	m810M(15),		-- product 810M
	m1032x(16),		-- product EtherCell
	m5005(17),		-- product 5005
	mAlcatelEthConc(18),	-- product Alcatel Ethernet workgroup conc.
	m2715SA(20),		-- product 2715SA
	m2486(21),		-- product 2486
	m28xxx(22),		-- product 28000 series
	m2300x(23),		-- product 23000 series
	m5DN00x(24),		-- product 5DN00x series
	mBayStackEth(25),	-- product BayStack Ethernet
	m2310x(26),		-- product 23100 series
	mBayStack100Hub(27),	-- product 100Base-T Hub
	m3000FastEth(28),       -- product 3000 Fast Ethernet
	mXediaSwitch(29),	-- product Orion switch
	notUsed(30),            -- not used 
        m28200EthSwitch(31),    -- product DDS 
	mCent6Slot(32),         -- product Centillion
	mCent12Slot(33),        -- product Centillion
	mCent1Slot(34),         -- product Centillion
	mBayStack301(35),       -- product BayStack 301
	mBayStackTr(36),        -- product BayStack TokenRing Hub
	mFVC10625(37),          -- product FVC Multimedia Switch
	mSwitchNode(38),        -- product Switch Node
	mBayStack302(39),       -- product BayStack 302 Switch
	mBayStack350(40),       -- product BayStack 350 Switch
	mBayStack150(41),       -- product BayStack 150 Ethernet Hub
        mCent50N3Slot(42),      -- product Centillion 50N switch
        mCent50T3Slot(43),      -- product Centillion 50T switch
        mBayStack303-304(44),   -- product BayStack 303 and 304 Switches
	mBayStack200(45),       -- product BayStack 200 Ethernet Hub
	mBayStack250(46)        -- product BayStack 250 10/100 Ethernet Hub
	}
-- This type is used to specify a concentrator chassis.


-- Top Branches under "synoptics"

synoptics	OBJECT IDENTIFIER ::= { enterprises 45 }

products	OBJECT IDENTIFIER ::= { synoptics 1 }
temporary 	OBJECT IDENTIFIER ::= { synoptics 2 }
registration	OBJECT IDENTIFIER ::= { synoptics 3 }


-- Branches under "products"

series1000	OBJECT IDENTIFIER ::= { products 1 }
s3SnmpAgent	OBJECT IDENTIFIER ::= { products 2 }
series3000	OBJECT IDENTIFIER ::= { products 3 }
superAgent	OBJECT IDENTIFIER ::= { products 4 }
specialTraps	OBJECT IDENTIFIER ::= { products 5 }
series5000	OBJECT IDENTIFIER ::= { products 6 }
lanSwitch	OBJECT IDENTIFIER ::= { products 7 }


-- Branches under "temporary"

-- ieee8023	OBJECT IDENTIFIER ::= { temporary 1 }
-- proj1(del)	OBJECT IDENTIFIER ::= { temporary 2 }
-- proj2(sa)	OBJECT IDENTIFIER ::= { temporary 3 }
-- proj3(lc)	OBJECT IDENTIFIER ::= { temporary 4 }
-- proj4(pen)	OBJECT IDENTIFIER ::= { temporary 5 }
-- proj5(phe)	OBJECT IDENTIFIER ::= { temporary 6 }
-- proj6(fddi)	OBJECT IDENTIFIER ::= { temporary 7 }
-- proj7(xo)	OBJECT IDENTIFIER ::= { temporary 8 }

-- Branches under "registration" (values for object sysObjectId)
s3reg-other	OBJECT IDENTIFIER ::= { registration 1 }


s3reg-3000	OBJECT IDENTIFIER ::= { registration 2 }
  s3reg-3000-enetNMM
		OBJECT IDENTIFIER ::= { s3reg-3000 1 }
  s3reg-3000-trNMM
		OBJECT IDENTIFIER ::= { s3reg-3000 2 }
  s3reg-3000-FDDI-NMM
		OBJECT IDENTIFIER ::= { s3reg-3000 3 }
  s3reg-3000-FastEthNMM
		OBJECT IDENTIFIER ::= { s3reg-3000 4 }
  s3reg-3000-ethSwitchNMM
		OBJECT IDENTIFIER ::= { s3reg-3000 5 }


s3reg-3030	OBJECT IDENTIFIER ::= { registration 3 }
  s3reg-3030-enetNMM
		OBJECT IDENTIFIER ::= { s3reg-3030 1 }
  s3reg-3030-trNMM
		OBJECT IDENTIFIER ::= { s3reg-3030 2 }
  s3reg-3030-FDDI-NMM
		OBJECT IDENTIFIER ::= { s3reg-3030 3 }
  s3reg-3030-ethSwitchNMM
		OBJECT IDENTIFIER ::= { s3reg-3030 4 } 


s3reg-2310	OBJECT IDENTIFIER ::= { registration 4 }
  s3reg-2310-enetNMM
		OBJECT IDENTIFIER ::= { s3reg-2310 1 }
  s3reg-2310-trNMM
		OBJECT IDENTIFIER ::= { s3reg-2310 2 }
  s3reg-2310-FDDI-NMM
		OBJECT IDENTIFIER ::= { s3reg-2310 3 }


s3reg-332X	OBJECT IDENTIFIER ::= { registration 5 }
s3reg-332XS	OBJECT IDENTIFIER ::= { registration 6 }
s3reg-3356	OBJECT IDENTIFIER ::= { registration 7 }


s3reg-2810	OBJECT IDENTIFIER ::= { registration 8 }
  s3reg-2810-enetNMM
		OBJECT IDENTIFIER ::= { s3reg-2810 1 }


s3reg-2715	OBJECT IDENTIFIER ::= { registration 9 }
  s3reg-2715-trNMM
	OBJECT IDENTIFIER ::= { s3reg-2715 1 }


s3reg-291X	OBJECT IDENTIFIER ::= { registration 10 }
  s3reg-291X-FDDI-NMM
		OBJECT IDENTIFIER ::= { s3reg-291X 1 }


s3reg-3394	OBJECT IDENTIFIER ::= { registration 11 }

s3reg-281X	OBJECT IDENTIFIER ::= { registration 12 }
  s3reg-281X-enetNMM
		OBJECT IDENTIFIER ::= { s3reg-281X 1 }


s5reg-5000	OBJECT IDENTIFIER ::= { registration 13 }
  s5reg-5000-ethNMM  -- Ethernet NMM in 5000 Chassis
		OBJECT IDENTIFIER ::= { s5reg-5000 1 }
  s5reg-5000-tokNMM  -- Token Ring NMM in 5000 Chassis
		OBJECT IDENTIFIER ::= { s5reg-5000 2 }
  s5reg-5000-fddNMM  -- FDDI NMM in 5000 Chassis
		OBJECT IDENTIFIER ::= { s5reg-5000 3 }
  s5reg-5000-atmNMM  -- ATM NMM in 5000 Chassis
		OBJECT IDENTIFIER ::= { s5reg-5000 4 }
  s5reg-5000-ethSwitchNMM  -- Ethernet Switch NMM in 5000 Chassis
		OBJECT IDENTIFIER ::= {s5reg-5000 5}
  s5reg-5000-ethFastEthNMM  -- 10/100 Ethernet NMM in 5000 Chassis
		OBJECT IDENTIFIER ::= { s5reg-5000 6 }
  s5reg-5000-eth10-100SwitchNMM  -- 10/100 Ethernet Switch NMM in 5000 Chassis
		OBJECT IDENTIFIER ::= { s5reg-5000 7 }


s3reg-281XSA	OBJECT IDENTIFIER ::= { registration 14 }
  s3reg-281XSA-enetNMM
		OBJECT IDENTIFIER ::= { s3reg-281XSA 1 }


lsreg-28xxx	OBJECT IDENTIFIER ::= { registration 15 }
  lsreg-28xxx-NMM
		OBJECT IDENTIFIER ::= { lsreg-28xxx 1 }


s3reg-8xx	OBJECT IDENTIFIER ::= { registration 16 }
  s3reg-810M-enetNMM
		OBJECT IDENTIFIER ::= { s3reg-8xx 1 }


s5reg-5005	OBJECT IDENTIFIER ::= { registration 17 }
  s5reg-5005-ethNMM  -- Ethernet NMM in 5005 Chassis
		OBJECT IDENTIFIER ::= { s5reg-5005 1 }
  s5reg-5005-tokNMM  -- Token Ring NMM in 5005 Chassis
		OBJECT IDENTIFIER ::= { s5reg-5005 2 }
  s5reg-5005-ethSwitchNMM -- Ethernet Switch NMM in 5005 Chassis
	        OBJECT IDENTIFIER ::= { s5reg-5005 3 }
  s5reg-5005-fddNMM  -- FDDI NMM in 5005 Chassis
		OBJECT IDENTIFIER ::= { s5reg-5005 4 }
  s5reg-5005-ethFastEthNMM  -- 10/100 Ethernet NMM in 5005 Chassis
		OBJECT IDENTIFIER ::= { s5reg-5005 5 }
  s5reg-5005-eth10-100SwitchNMM -- 10/100 Ethernet Switch NMM in 5005 Chassis
		OBJECT IDENTIFIER ::= { s5reg-5005 7 }

s3reg-AlcatelConc	OBJECT IDENTIFIER ::= { registration 18 }
  s3reg-AlcatelEthConc-enetNMM
		OBJECT IDENTIFIER ::= { s3reg-AlcatelConc 1 }


s3reg-271XSA	OBJECT IDENTIFIER ::= { registration 19 }
  s3reg-271XSA-trNMM	OBJECT IDENTIFIER ::= { s3reg-271XSA 1 }


ecreg-1032x	OBJECT IDENTIFIER ::= { registration 20 }
  s3reg-1032x-NMM	OBJECT IDENTIFIER ::= { ecreg-1032x 1 }


sreg-5DN00x	OBJECT IDENTIFIER ::= { registration 21 }
  sreg-5DN00x-EthNMM	OBJECT IDENTIFIER ::= { sreg-5DN00x 1 } 


sreg-BayStackEth	OBJECT IDENTIFIER ::= { registration 22 }
  sreg-BayStackEth-ethNMM   OBJECT IDENTIFIER ::= { sreg-BayStackEth 1 }


sreg-2300x	OBJECT IDENTIFIER ::= { registration 23 }
  sreg-2300x-NMM	OBJECT IDENTIFIER ::= { sreg-2300x 1 }


sreg-2310x	OBJECT IDENTIFIER ::= { registration 24 }
  sreg-2310x-NMM	OBJECT IDENTIFIER ::= { sreg-2310x 1 }

sreg-Orion	OBJECT IDENTIFIER ::= { registration 25 }
  sreg-Orion-ethNMM	OBJECT IDENTIFIER ::= { sreg-Orion 1 }

sreg-BayStack100Hub     OBJECT IDENTIFIER ::= { registration 26 }
  sreg-BayStack100Unit-12Port
                OBJECT IDENTIFIER ::= { sreg-BayStack100Hub 1 }

sreg-BayStackTr  OBJECT IDENTIFIER ::= { registration 27 }
   sreg-BayStackTr-trNMM -- BayStackTr NMM in a virtual Chassis
		 OBJECT IDENTIFIER ::= { sreg-BayStackTr 1 }

lsreg-28200   OBJECT IDENTIFIER ::= { registration 28 }
   lsreg-28200-ethSwitchNMM -- 28200 Ethernet Switch
                 OBJECT IDENTIFIER ::= { lsreg-28200 1 }

sreg-BayStack302   OBJECT IDENTIFIER ::= { registration 29 }
   sreg-BayStack302-9port -- BayStack302 8+1Tx/Fx 10 Mb/s Ethernet Switch 
                 OBJECT IDENTIFIER ::= { sreg-BayStack302 1 }

sreg-BayStack350   OBJECT IDENTIFIER ::= { registration 30 }
   sreg-BayStack350-ethSwitchNMM  -- BayStack350 Family 10/100 Adaptive Switches
                 OBJECT IDENTIFIER ::= { sreg-BayStack350 1 }

sreg-BayStack150Eth        OBJECT IDENTIFIER ::= { registration 31 }
  sreg-BayStack150Eth-ethNMM
		OBJECT IDENTIFIER ::= { sreg-BayStack150Eth 1 }
   
sreg-BayStack303-304	OBJECT IDENTIFIER ::= { registration 32 }
  sreg-BayStack303-304-Sw   -- 12-24 10mb 1 100mb with MDA Switch
                 OBJECT IDENTIFIER ::= { sreg-BayStack303-304 1 }

sreg-BayStack200Eth        OBJECT IDENTIFIER ::= { registration 33 }
  sreg-BayStack200Eth-ethNMM  --BayStack200 Ethernet Hub
		OBJECT IDENTIFIER ::= { sreg-BayStack200Eth 1 }

sreg-BayStack250Eth        OBJECT IDENTIFIER ::= { registration 34 }
  sreg-BayStack250Eth-ethNMM  --BayStack250 10/100 Ethernet Hub
              OBJECT IDENTIFIER ::= { sreg-BayStack250Eth 1 }
 		 
END
-- SECTION 1: Top Level Definitions

S5-ROOT-MIB DEFINITIONS ::= BEGIN


-- 5000 Root MIB Release 1.1.7
-- Revision 04/13/00

-- Copyright 1999 Nortel Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.

-- Imports

IMPORTS
	series5000
		FROM SYNOPTICS-ROOT-MIB;

-- Branches under "series5000"

-- branch for registration of values for objects
--   with syntax of OBJECT IDENTIFIER
  s5reg		OBJECT IDENTIFIER ::= { series5000 1 }

-- Branch for 'Enterprise' field values in traps
  s5Traps	OBJECT IDENTIFIER ::= { series5000 2 }
    s5EthTrap	-- Ethernet
		OBJECT IDENTIFIER ::= { s5Traps 1 }
    s5TokTrap	-- Token Ring
		OBJECT IDENTIFIER ::= { s5Traps 2 }
    s5FddTrap	-- FDDI
		OBJECT IDENTIFIER ::= { s5Traps 3 }
    s5ChaTrap	-- Chassis
		OBJECT IDENTIFIER ::= { s5Traps 4 }
    s5ComTrap	-- Common
		OBJECT IDENTIFIER ::= { s5Traps 5 }
    s5EcellTrap	-- EtherCell
		OBJECT IDENTIFIER ::= { s5Traps 6 }
    atmTraps  -- Atm
                OBJECT IDENTIFIER ::= { s5Traps 7 }
     remoteLoginTrap    -- Remote Login
                OBJECT IDENTIFIER ::= { s5Traps 8 }
     stpChangeTrap    -- STP Topology Change
                OBJECT IDENTIFIER ::= { s5Traps 9 }
     
-- Major 5000 MIB branches
  s5Chassis	OBJECT IDENTIFIER ::= { series5000 3 }
  s5Agent	OBJECT IDENTIFIER ::= { series5000 4 }
  s5Com		OBJECT IDENTIFIER ::= { series5000 5 }
  s5Eth		OBJECT IDENTIFIER ::= { series5000 6 }
  s5Tok		OBJECT IDENTIFIER ::= { series5000 7 }
  s5Fddi	OBJECT IDENTIFIER ::= { series5000 8 }
  s5EnTop	OBJECT IDENTIFIER ::= { series5000 9 }
  s5TrTop	OBJECT IDENTIFIER ::= { series5000 10 }
  s5FdTop	OBJECT IDENTIFIER ::= { series5000 11 }
  s5EnMsTop	OBJECT IDENTIFIER ::= { series5000 13 }
  s5AtmTop	OBJECT IDENTIFIER ::= { series5000 14 }
  s5IfExt	OBJECT IDENTIFIER ::= { series5000 15 }
  bnLogMsg      OBJECT IDENTIFIER ::= { series5000 16 }
END
-- SECTION 1: MIB Definition

S5-TCS-MIB DEFINITIONS ::= BEGIN


-- 5000 Common Textual Conventions MIB Release 1.1.2
-- Revision 07/28/94

-- Copyright 1993-94 SynOptics Communications, Inc.
-- All rights reserved.
-- This SynOptics SNMP Management Information Base Specification
-- (Specification) embodies SynOptics' confidential and
-- proprietary intellectual property. SynOptics retains all
-- title and ownership in the Specification, including any
-- revisions.

-- This Specification is supplied "AS IS," and SynOptics makes
-- no warranty, either express or implied, as to the use,
-- operation, condition, or performance of the Specification.


-- Textual Convention Definitions


-- A textual conventions for MAC addresses.
-- This is a 6 octet address in the "canonical" order
-- defined by IEEE 802.1a, i.e., as if it were transmitted
-- least significant bit first, even though 802.5 (in contrast
-- to other 802.x protocols) requires MAC addresses to be
-- transmitted most significant bit first.
MacAddress ::= OCTET STRING (SIZE (6))


-- A textual convention for IPX addresses. The first four bytes
-- are the network number in 'network order'. The last 6 bytes
-- are the MAC address.
IpxAddress ::= OCTET STRING (SIZE (10))


-- A textual convention for a period of time measured
-- in units of 0.01 seconds.
TimeIntervalHrd ::= INTEGER


-- A textual convention for a period of time measured
-- in units of seconds.
TimeIntervalSec ::= INTEGER



-- A textual convention for an Index of a "source".
-- The values are encoded so that the same MIB object
-- can be used to describe the same type of data, but
-- from different sources.
-- For the 5000 Chassis, this is encoded in the
-- following base 10 fields:
--   1bbiii - identifies an interface on an NMM
--              where 'bb' is the board index and
--              'iii' is the interface number.
--
--   2bbppp - identifies a connectivity port on
--              a board where 'bb' is the board INDEX
--              and 'ppp' is the port INDEX.
--
--   3bblll - identifies a local channel on a
--              board where 'bb' is the board INDEX
--              and 'll' is the local channel INDEX.
--
--   4bbccc - identifies a cluster on a board
--              where 'bb' is the board INDEX and
--              'cc' is the cluster INDEX.
--
--   5bbfff - identifies a FPU on a board where
--              'bb' is the board INDEX, and 'fff' is
--              the FPU INDEX.
--
--   6bbnnn - identifies host board backplane counters
--              where 'bb' is the board INDEX, and
--              'nnn' is the segment INDEX.
--
--   7bbccc - identifies a NULL segment on a board
--              where 'bb' is the board INDEX, and
--              'ccc' is the cluster INDEX.
--
--   8mmnnn - identifies a sum across all host board(s)
--              connected to a given backplane segment
--              where 'mm' is media type, and 'nnn' is
--              the segment INDEX. (NOTE: This is currently
--              only valid for Ethernet.)
SrcIndx ::= INTEGER (1..999999)



-- A textual convention for Media types
MediaType ::= INTEGER {
	other(1),	-- unknown or other type
	eth(2),		-- ethernet
	tok(3),		-- token ring
	fddi(4)		-- FDDI
	}		-- ATM later


-- The FDDI backplane mode.
FddiBkNetMode ::= INTEGER {
	other(1),	-- other or unknown
	thruLow(2),
	thruHigh(3),
	thruLowThruHigh(4)
	}

-- The backplane network ID. This is a numeric assignment
-- made to a backplane channel, a piece of a divided
-- backplane channel, or a grouping of several backplane
-- channels (which is done for FDDI). The number (and values)
-- of the backplane networks is determined by the setting
-- of the channel divider(s) which split some or all
-- the backplane channels into networks, and by
-- grouping when allowed by the media (such as FDDI).
-- Different media and backplane implementations may
-- have a divider or not. Also, there may be different
-- mappings of backplane network IDs to a divided (or
-- undivided) backplane channel.
--
-- Note to agent implementors - you must map the divided
-- (or undivided) backplane channel to the numbering here
-- based on the setting of the backplane channel divider(s),
-- and/or the grouping of the channels for FDDI.
BkNetId ::= INTEGER (1..255)


-- The physical backplane channel identification.
-- This does not change when a backplane is divided.
-- A value of zero means no channel. Otherwise, the
-- channels are numbered starting at one.
BkChan ::= INTEGER (0..255)

-- The physical local channel identification.
-- A value of zero means no channel. Otherwise, the
-- channels are numbered starting at one.
LocChan ::= INTEGER (0..255)

-- The attachment ID. This is either a backplane
-- network ID, a local channel, or as an indication
-- of no backplane network attachment. Negative numbers
-- are used to identify local channels on a board.
-- Where used, the board must also be specified
-- (or implied). A value of zero is used to indicate
-- no (or null) attachment. Positive numbers are the
-- backplane network IDs. The number (and values) of
-- the backplane networks is determined by the setting
-- of the channel divider(s) which split some or all
-- the backplane channels into backplane networks,
-- and by grouping when allowed by the media (such as
-- FDDI). Different media and implementations may have
-- a divider or not. Also, there may be different
-- mappings of backplane network IDs to a divided
-- (or undivided) backplane channel.
--
-- Note to agent implementors - you must map the divided
-- (or undivided) backplane channel to the numbering here
-- based on the setting of the backplane channel divider(s),
-- and/or the grouping of the channels for FDDI.
AttId ::= INTEGER (-255..255)


END

-- SECTION 1: Top Level Definitions

S5-ETH-MULTISEG-TOPOLOGY-MIB DEFINITIONS ::= BEGIN

-- 5000 Ethernet Multi-segment MIB Release 1.0.2
-- Revision 07/26/95

-- Copyright 1995 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	IpAddress, TimeTicks
		FROM RFC1155-SMI
	OBJECT-TYPE
		FROM RFC-1212
	SnpxChassisType, SnpxBackplaneType
		FROM SYNOPTICS-ROOT-MIB
	s5EnMsTop
		FROM S5-ROOT-MIB
	MacAddress
		FROM S5-TCS-MIB;


-- Groups

s5EnMsTopInfo		OBJECT IDENTIFIER ::= { s5EnMsTop 1 }

s5EnMsTopNmm		OBJECT IDENTIFIER ::= { s5EnMsTop 2 }

s5EnMsTopBdg		OBJECT IDENTIFIER ::= { s5EnMsTop 3 }

s5EnMsTopSrcMac		OBJECT IDENTIFIER ::= { s5EnMsTop 4 }

-- SECTION 2: MIB Objects

-- Topology Status and Configuration Information

s5EnMsTopIpAddr OBJECT-TYPE
	SYNTAX	IpAddress
	ACCESS	read-only
	STATUS	mandatory
	DESCRIPTION
		"An IP address of the agent. This is used to fill
		in the IP address field of transmitted SONMP packets.
		The agent should be reachable through this IP address."
	::= { s5EnMsTopInfo 1 }

s5EnMsTopStatus OBJECT-TYPE
	SYNTAX	INTEGER {
		  topOn(1),
		  topOff(2)
		}
	ACCESS	read-write
	STATUS	mandatory
	DESCRIPTION
		"Indicates if the agent is participating in
		multi-segment topology. The values are:
		  topOn(1)....topology is on
		  topOff(2)...topology is off
		When the value is topOff(2) the status of 	
		topology table entries is undefined.  However, the
		agent should make its best attempt when the value is
		changed to topOff(2) to remove all existing instances
		of topology MIB objects. The agent must save the
		setting of this object in nonvolatile memory (i.e.,
		save across reboots)."
	::= { s5EnMsTopInfo 2 }

s5EnMsTopNmmLstChg OBJECT-TYPE
	SYNTAX	TimeTicks
	ACCESS	read-only
	STATUS	mandatory
	DESCRIPTION
		"The value of sysUpTime the last time an entry in the
		NMM topology table was added, deleted, or modified.  If
		the NMM topology table has not changed since cold/warm
		start of the agent, then the value is zero."
	::= { s5EnMsTopInfo 3 }

s5EnMsTopBdgLstChg OBJECT-TYPE
	SYNTAX	TimeTicks
	ACCESS	read-only
	STATUS	mandatory
	DESCRIPTION
		"The value of sysUpTime the last time an entry in the
		bridge topology table was added, deleted, or modified.
		If the bridge topology table has not changed since
		cold/warm start of the agent, then the value is zero."
	::= { s5EnMsTopInfo 4 }

s5EnMsTopNmmMaxNum OBJECT-TYPE
	SYNTAX	INTEGER (0..65535)
	ACCESS	read-only
	STATUS	mandatory
	DESCRIPTION
		"The maximum number of entries in the NMM topology
		table."
	::= { s5EnMsTopInfo 5 }

s5EnMsTopNmmCurNum OBJECT-TYPE
	SYNTAX	INTEGER (0..65535)
	ACCESS	read-only
	STATUS	mandatory
	DESCRIPTION
		"The current number of entries in the NMM topology
		table."
	::= { s5EnMsTopInfo 6 }

s5EnMsTopBdgMaxNum OBJECT-TYPE
	SYNTAX	INTEGER (0..65535)
	ACCESS	read-only
	STATUS	mandatory
	DESCRIPTION
		"The maximum number of entries in the bridge topology
		table."
	::= { s5EnMsTopInfo 7 }

s5EnMsTopBdgCurNum OBJECT-TYPE
	SYNTAX	INTEGER (0..65535)
	ACCESS	read-only
	STATUS	mandatory
	DESCRIPTION
		"The current number of entries in the bridge topology
		table."
	::= { s5EnMsTopInfo 8 }

-- Network Management Module (NMM) Topology Table

s5EnMsTopNmmTable OBJECT-TYPE
	SYNTAX	SEQUENCE OF S5EnMsTopNmmEntry
	ACCESS	not-accessible
	STATUS	mandatory
	DESCRIPTION
		"A table of topology information from each topology
		agent that sends out NMM topology messages, and that
		has been heard by the reporting topology agent.  The
		number of entries is determined by the number of
		distinct topology messages received.  A topology
		message is identified by a combination of the IP
		address and segment-identifier contained in the
		message, and the slot-port on which it is received.
		Entries in the table are created by reception of a
		'new' NMM topology message.  An entry is removed from
		the table after no messages are received from the
		corresponding topology agent in the required time
		interval.

		NOTE: there is an entry for the reporting agent with
		the values of slot and port set to zero."
	::= { s5EnMsTopNmm 1 }

s5EnMsTopNmmEntry OBJECT-TYPE
	SYNTAX	S5EnMsTopNmmEntry
	ACCESS	not-accessible
	STATUS	mandatory
	DESCRIPTION
		"A row in the NMM topology table. Entries in the table
		can not be created or deleted via SNMP."
	INDEX	{ s5EnMsTopNmmSlot,
		  s5EnMsTopNmmPort,
		  s5EnMsTopNmmIpAddr,
		  s5EnMsTopNmmSegId }
	::= { s5EnMsTopNmmTable 1 }

S5EnMsTopNmmEntry ::= SEQUENCE {
	s5EnMsTopNmmSlot INTEGER,
	s5EnMsTopNmmPort INTEGER,
	s5EnMsTopNmmIpAddr IpAddress,
	s5EnMsTopNmmSegId INTEGER,
	s5EnMsTopNmmMacAddr  MacAddress, 
	s5EnMsTopNmmChassisType SnpxChassisType,
	s5EnMsTopNmmBkplType SnpxBackplaneType,
	s5EnMsTopNmmLocalSeg INTEGER,
	s5EnMsTopNmmCurState INTEGER
	}

s5EnMsTopNmmSlot OBJECT-TYPE
	SYNTAX	INTEGER (0..255)
	ACCESS	read-only
	STATUS	mandatory
	DESCRIPTION
		"The slot on which the topology message
		was received.

		NOTE: There is an artificial 'row' for the reporting
		agent with slot and port equal to zero.

		NOTE: Non-modular devices that do not have multiple
		slots should set this value to 1."
	::= { s5EnMsTopNmmEntry 1 }

s5EnMsTopNmmPort OBJECT-TYPE
	SYNTAX	INTEGER (0..255)
	ACCESS	read-only
	STATUS	mandatory
	DESCRIPTION
		"The port on which the topology message 
		was received.

		NOTE: there is an artificial 'row' for the reporting
		agent with slot and port equal to zero."
	::= { s5EnMsTopNmmEntry 2 }

s5EnMsTopNmmIpAddr OBJECT-TYPE
	SYNTAX	IpAddress
	ACCESS	read-only
	STATUS	mandatory
	DESCRIPTION
		"The IP address of the sender of the topology message."
	::= { s5EnMsTopNmmEntry 3 }

s5EnMsTopNmmSegId OBJECT-TYPE
	SYNTAX	INTEGER (0..'FFFFFF'H)
	ACCESS	read-only
	STATUS	mandatory
	DESCRIPTION
		"The 'segment identifier' of the segment from which
		the remote agent sent the topology message.  The value
		is extracted from the received topology message.
		Different devices may use different methods for
		representing the segment identifier.  For example,
		system 5000 NMMs that run multi-segment autotopology use
		the SrcIndx of the segment as the segment identifier;
		system 3000 NMMs use the lower three bytes of the MAC
		address of the NMM as the segment identifier.  In any
		case, the 'segment identifier' uniquely identifies the
		network segment in the remote device from which
		the topology message was sent."
	::= { s5EnMsTopNmmEntry 4 }

s5EnMsTopNmmMacAddr OBJECT-TYPE
	SYNTAX	MacAddress
	ACCESS	read-only
	STATUS	mandatory
	DESCRIPTION
		"The MAC address of the sender of the topology message."
	::= { s5EnMsTopNmmEntry 5 }

s5EnMsTopNmmChassisType OBJECT-TYPE
	SYNTAX	SnpxChassisType
	ACCESS	read-only
	STATUS	mandatory
	DESCRIPTION
		"The chassis type of the device that sent the topology
		message."
	::= { s5EnMsTopNmmEntry 6 }

s5EnMsTopNmmBkplType OBJECT-TYPE
	SYNTAX	SnpxBackplaneType
	ACCESS	read-only
	STATUS	mandatory
	DESCRIPTION
		"The backplane type of the device that sent the
		topology message."
	::= { s5EnMsTopNmmEntry 7 }

s5EnMsTopNmmLocalSeg OBJECT-TYPE
	SYNTAX	INTEGER {
		true(1),
		false(2)
		}
	ACCESS	read-only
	STATUS	mandatory
	DESCRIPTION
		"Indicates if the sender of the topology message is on
		the same Ethernet segment (i.e., NOT across a bridge)
		as the reporting agent."
	::= { s5EnMsTopNmmEntry 8 }

s5EnMsTopNmmCurState OBJECT-TYPE
	SYNTAX	INTEGER {
		topChanged(1),
		heartbeat(2),
		new(3)
		}
	ACCESS	read-only
	STATUS	mandatory
	DESCRIPTION
		"The current state of sender of the
		topology message. The values are:
		  topChanged(1)...topology information has
		                    recently changed
		  heartbeat(2)....topology information unchanged
		  new(3)..........sending agent is in new state."
	::= { s5EnMsTopNmmEntry 9 }

-- Encoded Octet Strings for NMM Topology Table

s5EnMsTopNmmEosSize OBJECT-TYPE
	SYNTAX	INTEGER (0..1440)
	ACCESS	read-only
	STATUS	mandatory
	DESCRIPTION
		"The current size of a 'row' in the table
		s5EnMsTopNmmEosTable.  This allows applications
		to be able to break apart 'rows' in the table."
	::= { s5EnMsTopNmm 2 }

s5EnMsTopNmmEosTable OBJECT-TYPE
	SYNTAX	SEQUENCE OF S5EnMsTopNmmEosEntry
	ACCESS	not-accessible
	STATUS	mandatory
	DESCRIPTION
		"A table of encoded octet strings of
		entries in table s5EnMsTopNmmTable.
		The number of entries is determined by
		packing of 'rows' from s5EnMsTopNmmTable."
	::= { s5EnMsTopNmm 3 }

s5EnMsTopNmmEosEntry OBJECT-TYPE
	SYNTAX	S5EnMsTopNmmEosEntry
	ACCESS	not-accessible
	STATUS	mandatory
	DESCRIPTION
		"A row in the table of encoded octet
		strings for table s5EnMsTopNmmTable.
		Instance returned in Response PDU:
		  On GETs: instance specified is the
		           instance returned.
		  On GET-NEXTs: instance returned is the
		                instance of the last record
		                contained in the octet string.

		Entries in the table can not be created
		or deleted via SNMP."
	INDEX	{ s5EnMsTopNmmSlot,
		  s5EnMsTopNmmPort,
		  s5EnMsTopNmmIpAddr,
		  s5EnMsTopNmmSegId }
	::= { s5EnMsTopNmmEosTable 1 }

S5EnMsTopNmmEosEntry ::= SEQUENCE {
	s5EnMsTopNmmEos OCTET STRING
	}

s5EnMsTopNmmEos OBJECT-TYPE
	SYNTAX	OCTET STRING (SIZE(0..1400))
	ACCESS	read-only
	STATUS	mandatory
	DESCRIPTION
		"An encoded octet string. On reads it contains
		an integral number of 'rows' from table
		s5EnMsTopNmmTable. All 'rows' are the same size
		which is defined by object s5EnMsTopNmmEosSize."
	::= { s5EnMsTopNmmEosEntry 1 }

-- Bridge Topology Table

s5EnMsTopBdgTable OBJECT-TYPE
	SYNTAX	SEQUENCE OF S5EnMsTopBdgEntry
	ACCESS	not-accessible
	STATUS	mandatory
	DESCRIPTION
		"A table of topology information from each Bridge in
		the network that is sending bridge topology messages
		that have been heard by the reporting agent.  The
		number of entries is determined by the number of
		detected (and active) bridges.  Entries in the table
		are created by reception of a topology message from a
		'new' bridge.  An entry is removed from the table
		after no messages are received from the corresponding
		bridge in the required time interval."
	::= { s5EnMsTopBdg 1 }

s5EnMsTopBdgEntry OBJECT-TYPE
	SYNTAX	S5EnMsTopBdgEntry
	ACCESS	not-accessible
	STATUS	mandatory
	DESCRIPTION
		"A row in the bridge topology table.  Entries in the
		table can not be created or deleted via SNMP."
	INDEX	{ s5EnMsTopBdgSlotNum,
		  s5EnMsTopBdgPortNum,
		  s5EnMsTopBdgIpAddr }
	::= { s5EnMsTopBdgTable 1 }

S5EnMsTopBdgEntry ::= SEQUENCE {
	s5EnMsTopBdgSlotNum INTEGER,
	s5EnMsTopBdgPortNum INTEGER,
	s5EnMsTopBdgIpAddr IpAddress,
	s5EnMsTopBdgNumber INTEGER,
	s5EnMsTopBdgMacAddr MacAddress,
	s5EnMsTopBdgType INTEGER,
	s5EnMsTopBdgStatus INTEGER,
	s5EnMsTopBdgNumPorts INTEGER,
	s5EnMsTopBdgHelloPortNum INTEGER,
	s5EnMsTopBdgHelloPortType INTEGER,
	s5EnMsTopBdgHelloPortStatus INTEGER,
	s5EnMsTopBdgCompBdgMac1 MacAddress,
	s5EnMsTopBdgCompBdgMac2 MacAddress
	}

s5EnMsTopBdgSlotNum OBJECT-TYPE
	SYNTAX	INTEGER (0..255)
	ACCESS	read-only
	STATUS	mandatory
	DESCRIPTION
		"The slot on which the topology message was
		received.

		NOTE: Non-modular devices that do not have multiple
		slots should set this value to 1."
	::= { s5EnMsTopBdgEntry 1 }

s5EnMsTopBdgPortNum OBJECT-TYPE
	SYNTAX	INTEGER (0..255)
	ACCESS	read-only
	STATUS	mandatory
	DESCRIPTION
		"The port on which the topology message was received."
	::= { s5EnMsTopBdgEntry 2 }

s5EnMsTopBdgIpAddr OBJECT-TYPE
	SYNTAX	IpAddress
	ACCESS	read-only
	STATUS	mandatory
	DESCRIPTION
		"The IP address of the bridge that sent the
		topology message."
	::= { s5EnMsTopBdgEntry 3 }

s5EnMsTopBdgNumber OBJECT-TYPE
	SYNTAX	INTEGER (0..65535)
	ACCESS	read-only
	STATUS	mandatory
	DESCRIPTION
		"The 'Bridge Number' of the bridge that sent
		the topology message.  This is the IEEE 802.1
		bridge number."
	::= { s5EnMsTopBdgEntry 4 }

s5EnMsTopBdgMacAddr OBJECT-TYPE
	SYNTAX	MacAddress
	ACCESS	read-only
	STATUS	mandatory
	DESCRIPTION
		"The MAC Address of the bridge that sent the
		topology message."
	::= { s5EnMsTopBdgEntry 5 }

s5EnMsTopBdgType OBJECT-TYPE
	SYNTAX	INTEGER {
		other(1),
		localSyn(2),
		remoteSyn(3),
		kalpana(4)
		}
	ACCESS	read-only
	STATUS	mandatory
	DESCRIPTION
		"The 'kind of bridge' that sent the topology
		message. The values are:
		  other(1).....unknown or other type
		  locSyn(2)....local SynOptics bridge
		  remSyn(3)....remote SynOptics bridge
		  kalpana(4)...Kalpana bridge(switch)
		"
	::= { s5EnMsTopBdgEntry 6 }

s5EnMsTopBdgNumPorts OBJECT-TYPE
	SYNTAX	INTEGER
	ACCESS	read-only
	STATUS	mandatory
	DESCRIPTION
		"The number of ports on the bridge."
	::= { s5EnMsTopBdgEntry 7 }

s5EnMsTopBdgStatus OBJECT-TYPE
	SYNTAX	INTEGER {
		other(1),
		active(2),
		standby(3)
		}
	ACCESS	read-only
	STATUS	mandatory
	DESCRIPTION
		"The current operational status from the bridge
		that sent the topology message.  The values are:
		  other(1).....unknown or other
		  active(2)....bridge is active
		  standby(3)...bridge is in standby

		A value of standby(3) means that at least ONE port
		is in standby mode.  A value of active(2) means NO
		port is in standby mode."
	::= { s5EnMsTopBdgEntry 8 }

s5EnMsTopBdgHelloPortNum OBJECT-TYPE
	SYNTAX	INTEGER (0..255)
	ACCESS	read-only
	STATUS	mandatory
	DESCRIPTION
		"The port number used by the bridge to
		send the topology message.  This port may
		or may not be in standby mode."
	::= { s5EnMsTopBdgEntry 9 }

s5EnMsTopBdgHelloPortType OBJECT-TYPE
	SYNTAX	INTEGER {
		other(1),
		eth(2),
		tok4(3),
		tok16(4),
		fddi(5),
		t1(6)
		}
	ACCESS	read-only
	STATUS	mandatory
	DESCRIPTION
		"The type of the port used by the bridge to
		send the topology message.  The values are:
		  other(1)...other or unknown type
		  eth(2).....ethernet
		  tok4(3)....4 Mbit token ring
		  tok16(4)...16 Mbit token ring
		  fddi(5)....fddi
		  t1(6)......t1

		Note: These enumerations were done for
		'completeness'. No other value than eth(2)
		should ever be received by an ethernet agent."
	::= { s5EnMsTopBdgEntry 10 }

s5EnMsTopBdgHelloPortStatus OBJECT-TYPE
	SYNTAX	INTEGER {
		other(1),
		active(2),
		standby(3)
		}
	ACCESS	read-only
	STATUS	mandatory
	DESCRIPTION
		"The status of the port used by the bridge
		to send the topology message. The values are:
		  other(1).....unknown or other
		  active(2)....port is active
		  standby(3)...port is in standby"
	::= { s5EnMsTopBdgEntry 11 }

s5EnMsTopBdgCompBdgMac1 OBJECT-TYPE
	SYNTAX	MacAddress
	ACCESS	read-only
	STATUS	mandatory
	DESCRIPTION
		"The first MAC address of a companion bridge
		of the bridge that sent the topology message.
		The value is 00:00:00:00:00:00 for local
		bridges (since there is no companion bridge)
		and also when the companion MAC address
		is unknown for remote bridges."
	::= { s5EnMsTopBdgEntry 12 }

s5EnMsTopBdgCompBdgMac2 OBJECT-TYPE
	SYNTAX	MacAddress
	ACCESS	read-only
	STATUS	mandatory
	DESCRIPTION
		"The second MAC address of a companion bridge
		of the bridge that sent the topology message.
		The value is 00:00:00:00:00:00 for local
		bridges (since there is no companion bridge)
		and also when the companion MAC address
		is unknown for remote bridges."
	::= { s5EnMsTopBdgEntry 13 }

-- Encoded Octet Strings for Bridge Topology Table

s5EnMsTopBdgEosSize OBJECT-TYPE
	SYNTAX	INTEGER (0..1440)
	ACCESS	read-only
	STATUS	mandatory
	DESCRIPTION
		"The current size of a 'row' in the table
		s5EnMsTopBdgEosTable.  This allows applications
		to be able to break apart 'rows' in the table."
	::= { s5EnMsTopBdg 2 }

s5EnMsTopBdgEosTable OBJECT-TYPE
	SYNTAX	SEQUENCE OF S5EnMsTopBdgEosEntry
	ACCESS	not-accessible
	STATUS	mandatory
	DESCRIPTION
		"A table of encoded octet strings of
		entries in table s5EnMsTopBdgTable.
		The number of entries is determined by
		packing of 'rows' from s5EnMsTopBdgTable."
	::= { s5EnMsTopBdg 3 }

s5EnMsTopBdgEosEntry OBJECT-TYPE
	SYNTAX	S5EnMsTopBdgEosEntry
	ACCESS	not-accessible
	STATUS	mandatory
	DESCRIPTION
		"A row in the table of encoded octet
		strings for table s5EnMsTopBdgTable.
		Instance returned in Response PDU:
		  On GETs: instance specified is the
		             instance returned.
		  On GET-NEXTs: instance returned is the
		                  instance of the last record
		                  contained in the octet string.

		Entries in the table can not be created
		or deleted via SNMP."
	INDEX	{ s5EnMsTopBdgSlotNum,
		  s5EnMsTopBdgPortNum,
		  s5EnMsTopBdgIpAddr }
	::= { s5EnMsTopBdgEosTable 1 }

S5EnMsTopBdgEosEntry ::= SEQUENCE {
	s5EnMsTopBdgEos OCTET STRING
	}

s5EnMsTopBdgEos OBJECT-TYPE
	SYNTAX	OCTET STRING (SIZE(0..1400))
	ACCESS	read-only
	STATUS	mandatory
	DESCRIPTION
		"An encoded octet string. On reads it contains
		an integral number of 'rows' from table
		s5EnMsTopBdgTable.  All 'rows' are the same size
		which is defined by object s5EnMsTopBdgEosSize."
	::= { s5EnMsTopBdgEosEntry 1 }

-- MAC Address-to-Segment Mapping Table

-- Implementation of this group is optional. It is supported by those
-- devices that use different source MAC addresses to transmit
-- topology messages on different segments.

s5EnMsTopSrcMacAddrTable OBJECT-TYPE
	SYNTAX	SEQUENCE OF S5EnMsTopSrcMacAddrEntry
	ACCESS	not-accessible
	STATUS	mandatory
	DESCRIPTION
		"A table describing the source MAC addresses that the
		agent uses to transmit topology messages on different
		segments in the device.  The MAC addresses are
		preallocated and remain unchanged for the agent.
		However, the mapping between a MAC address and segment
		may change, since it can depend on the current
		physical and/or logical configuration of the device.

		Implementation of this group is required for those
		devices that use different source MAC addresses to
		transmit topology messages on different segments.
		Implementation of this group is optional otherwise."
	::= { s5EnMsTopSrcMac 1 }

s5EnMsTopSrcMacAddrEntry OBJECT-TYPE
	SYNTAX	S5EnMsTopSrcMacAddrEntry
	ACCESS	not-accessible
	STATUS	mandatory
	DESCRIPTION
		"A row in the table of MAC address-to-segment mappings. 
		Entries in the table can not be created or deleted
		via SNMP."
	INDEX	{ s5EnMsTopSrcMacAddr }
	::= { s5EnMsTopSrcMacAddrTable 1 }

S5EnMsTopSrcMacAddrEntry ::= SEQUENCE {
	s5EnMsTopSrcMacAddr   MacAddress,
	s5EnMsTopSrcMacSegId  INTEGER
	}

s5EnMsTopSrcMacAddr OBJECT-TYPE
	SYNTAX	MacAddress
	ACCESS	read-only
	STATUS	mandatory
	DESCRIPTION
		"The MAC address used to transmit topology messages."
	::= { s5EnMsTopSrcMacAddrEntry 1 }

s5EnMsTopSrcMacSegId OBJECT-TYPE
	SYNTAX	INTEGER (0..16777215) 
	ACCESS	read-only
	STATUS	mandatory
	DESCRIPTION
		"The 'segment-identifier' of the segment 
		on which topology messages were transmitted."
	::= { s5EnMsTopSrcMacAddrEntry 2 }

s5EnMsTopSrcMacAddrLstChg OBJECT-TYPE
	SYNTAX	TimeTicks
	ACCESS	read-only
	STATUS	mandatory
	DESCRIPTION
		"The value of sysUpTime when an entry in the 
		table s5EnMsTopSrcMacAddrTable was last changed.
		If no changes have been done since cold/warm start
		of the agent, then the value is zero."
	::= { s5EnMsTopSrcMac 2 }

END
-- SECTION 1: Top Level Definitions


BNET-ATM-TOPOLOGY-MIB DEFINITIONS ::= BEGIN


-- Copyright 1995 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.

-- Imports

IMPORTS

	VpiInteger
		FROM LAN-EMULATION-CLIENT-MIB
        IpAddress, TimeTicks
                FROM RFC1155-SMI
        OBJECT-TYPE
                FROM RFC-1212
	s5AtmTop
		FROM S5-ROOT-MIB;



bnetAtmTopGbl     OBJECT IDENTIFIER ::= { s5AtmTop 1 }
 
bnetAtmTopLinks    OBJECT IDENTIFIER ::= { s5AtmTop 2 }
 
-- The following is global information about the reporting agent.
 

bnetAtmTopGblStatus OBJECT-TYPE
        SYNTAX  INTEGER {
                  topOn(1),
                  topOff(2)
                }
        ACCESS  read-write
        STATUS  mandatory
        DESCRIPTION
                "Indicates if the agent is participating in
                ATM topology discovery. The values are:
                  topOn(1)....topology is on
                  topOff(2)...topology is off
                When the value is topOff(2) the status of
                bnetAtmTopLinkTable entries is undefined and the topolgy 
                discovery is disabled for the entire device.

                When the value is topOn(1) the status of the topology 
                discovery of a given port is defined by the 
                bnetAtmTopLinksPeerStatus in the bnetAtmTopLinkTable.

                The agent must save the setting of this object
                in nonvolatile memory (i.e., save across reboots)."
        ::= { bnetAtmTopGbl 1 }
 
bnetAtmTopGblLstChg OBJECT-TYPE
        SYNTAX  TimeTicks
        ACCESS  read-only
        STATUS  mandatory
        DESCRIPTION
                "The value of sysUpTime the last time an entry in the
                bnetAtmTopLinkTable was added, deleted, or modified.  If
                bnetAtmTopLinkTable has not changed since cold/warm
                start of the agent, then the value is zero."
        ::= { bnetAtmTopGbl 2 }
 
bnetAtmTopGblCurNum OBJECT-TYPE
        SYNTAX  INTEGER (0..65535)
        ACCESS  read-only
        STATUS  mandatory
        DESCRIPTION
                "The current number of entries in the bnetAtmTopLinkTable."
        ::= { bnetAtmTopGbl 3 }
 
bnetAtmTopGblCurMibVer OBJECT-TYPE
        SYNTAX  INTEGER
        ACCESS  read-only
        STATUS  mandatory
        DESCRIPTION
                "The current version of the ATM Topology mib.
                This object is provided by agent so NMS can distinguish
                variations in the mib as they occur in the future."
        ::= { bnetAtmTopGbl 4 }

bnetAtmTopGblOperStatus OBJECT-TYPE
        SYNTAX  INTEGER {
                  topOn(1),
                  topOff(2),
		  topUnavailable(3)
                }
        ACCESS  read-only
        STATUS  mandatory
        DESCRIPTION
                "Indicates if the agent is participating in
                ATM topology discovery. The values are:
                  topOn(1)....topology is on
                  topOff(2)...topology is off
                When the value is topOff(2) the status of
                bnetAtmTopLinkTable entries is undefined and the topolgy 
                discovery is disabled for the entire device.

                When the value is topOn(1) the status of the topology 
                discovery of a given port is defined by the 
                bnetAtmTopLinksPeerStatus in the bnetAtmTopLinkTable.

                The agent must save the setting of this object
                in nonvolatile memory (i.e., save across reboots).

		When status is topUnavailable(3), this implies that
		ilmi is not configured on this switch at all."
        ::= { bnetAtmTopGbl 5 }
 

-- 
 
-- Aggregates bnetAtmTopLinkPeer information on each ILMI entity and
-- adds local context.

bnetAtmTopLinksTable OBJECT-TYPE
        SYNTAX  SEQUENCE OF BnetAtmTopLinksEntry
        ACCESS  not-accessible
        STATUS  mandatory
        DESCRIPTION
		"A table of all physical and virtual links attached to this
		 switch. This table is built by aggregating information
		 from all ILMI or PNNI entities in the switch and adding
		local port information."
        ::= { bnetAtmTopLinks 1 }
 
bnetAtmTopLinksEntry OBJECT-TYPE
        SYNTAX  BnetAtmTopLinksEntry
        ACCESS  not-accessible
        STATUS  mandatory
        DESCRIPTION
                "A row in the ATM topology table. Entries in the table
                can not be created or deleted via SNMP."
        INDEX   { bnetAtmTopLinksSlotNumIndx,
		  bnetAtmTopLinksPortNumIndx,
		  bnetAtmTopLinksLcnIndx		
		}
        ::= { bnetAtmTopLinksTable 1 }
 
BnetAtmTopLinksEntry ::= SEQUENCE {
	bnetAtmTopLinksSlotNumIndx INTEGER,
	bnetAtmTopLinksPortNumIndx INTEGER,
	bnetAtmTopLinksLcnIndx VpiInteger,
	bnetAtmTopLinksTopoState INTEGER,
	bnetAtmTopLinksPeerSlotNum INTEGER,
	bnetAtmTopLinksPeerPortNum INTEGER,
	bnetAtmTopLinksPeerIpAddr IpAddress,
	bnetAtmTopLinksPeerChassisType INTEGER,
	bnetAtmTopLinksPeerChassisSubType INTEGER
      }

bnetAtmTopLinksSlotNumIndx OBJECT-TYPE
        SYNTAX  INTEGER (0..255)
        ACCESS  read-only
        STATUS  mandatory
        DESCRIPTION
                "Our slot number."
        ::= { bnetAtmTopLinksEntry 1 }
 
bnetAtmTopLinksPortNumIndx OBJECT-TYPE
        SYNTAX  INTEGER (0..255)
        ACCESS  read-only
        STATUS  mandatory
        DESCRIPTION
                "Our port number."
        ::= { bnetAtmTopLinksEntry 2 }

bnetAtmTopLinksLcnIndx OBJECT-TYPE
        SYNTAX  VpiInteger 
        ACCESS  read-only
        STATUS  mandatory
        DESCRIPTION
" Logical Channel Number, This will give the VP, when the ILMI entity uses
the VP signalling. This allows to have multiple NNI or UNI links on a single
port."
        ::= { bnetAtmTopLinksEntry 3 }

bnetAtmTopLinksTopoState OBJECT-TYPE
        SYNTAX  INTEGER {
                unavailable(1),
                notParticipating(2),
                participating(3)
                }
        ACCESS  read-only
        STATUS  mandatory
        DESCRIPTION
                "The current state of link from topology point of view.
		 Possible values:
			unavailable(1)       - third party device or 
					 	older version of Bay device
			notParticipating(2) - peer has set TopoOff  
			participating(3)     - actively providing topo info. "
        ::= { bnetAtmTopLinksEntry 4 }


bnetAtmTopLinksPeerSlotNum OBJECT-TYPE
        SYNTAX  INTEGER (0..255)
        ACCESS  read-only
        STATUS  mandatory
        DESCRIPTION
		"The peer's slot number." 
        ::= { bnetAtmTopLinksEntry 5 }

bnetAtmTopLinksPeerPortNum OBJECT-TYPE
        SYNTAX  INTEGER (0..255)
        ACCESS  read-only
        STATUS  mandatory
        DESCRIPTION
		"The peer's port number." 
        ::= { bnetAtmTopLinksEntry 6 }

bnetAtmTopLinksPeerIpAddr OBJECT-TYPE
        SYNTAX  IpAddress
        ACCESS  read-only
        STATUS  mandatory
        DESCRIPTION
		"The peer's IP address." 
        ::= { bnetAtmTopLinksEntry 7 }

bnetAtmTopLinksPeerChassisType OBJECT-TYPE
        SYNTAX  INTEGER
        ACCESS  read-only
        STATUS  mandatory
        DESCRIPTION
                "The chassis type of the device that sent the topology
                message. This number is the leaf of the s5 ChassisType
		OID registered in s5reg*.mib."
        ::= { bnetAtmTopLinksEntry 8 }
 
bnetAtmTopLinksPeerChassisSubType OBJECT-TYPE
        SYNTAX  INTEGER
        ACCESS  read-only
        STATUS  mandatory
        DESCRIPTION
        "Any relavant additional information of the chassis of the peer 
         Bay device. This is an integer field which could be used as 
         backplane type or any information for stackable devices etc."
        ::= { bnetAtmTopLinksEntry 9 }


-- Encoded Octet Strings for ATM Topology Table

bnetAtmTopLinksEosSize OBJECT-TYPE
	SYNTAX	INTEGER (0..1440)
	ACCESS	read-only
	STATUS	mandatory
	DESCRIPTION
		"The current size of a row in the table
		bnetAtmTopLinksEosTable.  This allows applications
		to be able to break apart rows in the table."
	::= { bnetAtmTopLinks 2 }

bnetAtmTopLinksEosTable OBJECT-TYPE
	SYNTAX	SEQUENCE OF BnetAtmTopLinksEosEntry
	ACCESS	not-accessible
	STATUS	mandatory
	DESCRIPTION
		"A table of encoded octet strings of
		entries in table bnetAtmTopLinksTable.
		The number of entries is determined by
		packing of 'rows' from bnetAtmTopLinksTable."
	::= { bnetAtmTopLinks 3 }

bnetAtmTopLinksEosEntry OBJECT-TYPE
	SYNTAX	BnetAtmTopLinksEosEntry
	ACCESS	not-accessible
	STATUS	mandatory
	DESCRIPTION
		"A row in the table of encoded octet
		strings for table bnetAtmTopLinksTable.
		Instance returned in Response PDU:
		  On GETs: instance specified is the
		           instance returned.
		  On GET-NEXTs: instance returned is the
		                instance of the last record
		                contained in the octet string.

		Entries in the table can not be created
		or deleted via SNMP."
        INDEX   { bnetAtmTopLinksSlotNumIndx,
		  bnetAtmTopLinksPortNumIndx,
		  bnetAtmTopLinksLcnIndx	}
	::= { bnetAtmTopLinksEosTable 1 }

BnetAtmTopLinksEosEntry ::= SEQUENCE {
	bnetAtmTopLinksEos OCTET STRING
	}

bnetAtmTopLinksEos OBJECT-TYPE
	SYNTAX	OCTET STRING (SIZE(0..1400))
	ACCESS	read-only
	STATUS	mandatory
	DESCRIPTION
		"An encoded octet string. On reads it contains
		an integral number of 'rows' from table
		bnetAtmTopLinksTable. All 'rows' are the same size
		which is defined by object bnetAtmTopLinksEosSize."
	::= { bnetAtmTopLinksEosEntry 1 }

END
-- SECTION 1: Top Level Definitions

S5-CHASSIS-MIB DEFINITIONS ::= BEGIN


-- 5000 Chassis MIB Release 1.2.5
-- Revision 07/26/95

-- Copyright 1995 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	Counter, TimeTicks
		FROM RFC1155-SMI
	OBJECT-TYPE
		FROM RFC-1212
	DisplayString
		FROM RFC1213-MIB
	s5Chassis
		FROM S5-ROOT-MIB
	AttId, LocChan
		FROM S5-TCS-MIB;


-- Chassis Groups


s5ChasGen	OBJECT IDENTIFIER ::= { s5Chassis 1 }
s5ChasGrp	OBJECT IDENTIFIER ::= { s5Chassis 2 }
s5ChasCom	OBJECT IDENTIFIER ::= { s5Chassis 3 }
s5ChasBrd	OBJECT IDENTIFIER ::= { s5Chassis 4 }
s5ChasStore	OBJECT IDENTIFIER ::= { s5Chassis 5 }
s5ChasSm	OBJECT IDENTIFIER ::= { s5Chassis 6 }

-- SECTION 2: MIB Objects


-- General Chassis Information


s5ChasType OBJECT-TYPE
	SYNTAX	OBJECT IDENTIFIER
	ACCESS	read-only
	STATUS	mandatory
	DESCRIPTION
		"The chassis type. This is 'what kind of
		box' is being managed. The values are
		defined under s5ChasTypeVal in the
		Registration MIB."
	::= { s5ChasGen 1 }

s5ChasDescr OBJECT-TYPE
	SYNTAX	DisplayString (SIZE(0..64))
	ACCESS	read-only
	STATUS	mandatory
	DESCRIPTION
		"A description of the chassis.
		The value is a zero length string
		if no information is available."
	::= { s5ChasGen 2 }

s5ChasLocation OBJECT-TYPE
	SYNTAX	DisplayString (SIZE(0..64))
	ACCESS	read-write
	STATUS	mandatory
	DESCRIPTION
		"The physical location of the chassis
		(e.g., 'fourth floor wiring closet in
		building A'). The value is a zero
		length string if no information
		is available.  Note: this object is
		different from sysLocation in MIB-II.
		However, an agent may use this value for
		sysLocation if none is configured in the
		the agent."
	::= { s5ChasGen 3 }

s5ChasContact OBJECT-TYPE
	SYNTAX	DisplayString (SIZE(0..64))
	ACCESS	read-write
	STATUS	mandatory
	DESCRIPTION
		"The textual identification of the
		contact person for the chassis, together
		with information on how to contact
		this person. The value is a zero length
		string if no information is available.
		Note: this object is different from sysContact
		in MIB-II. However, an agent may use this value
		for sysContact if none is configured in the
		agent."
	::= { s5ChasGen 4 }

s5ChasVer OBJECT-TYPE
	SYNTAX	DisplayString (SIZE(0..32))
	ACCESS	read-only
	STATUS	mandatory
	DESCRIPTION
		"The version of the chassis in the form
		'major.minor.maintenance[letters]'. If the
		version is unknown or not available then
		the value should be a zero length string."
	::= { s5ChasGen 5 }

s5ChasSerNum OBJECT-TYPE
	SYNTAX	DisplayString (SIZE(0..32))
	ACCESS	read-only
	STATUS	mandatory
	DESCRIPTION
		"The serial number of the chassis. If the
		serial number is unknown or unavailable then
		the value should be a zero length string."
	::= { s5ChasGen 6 }

s5ChasGblPhysChngs OBJECT-TYPE
	SYNTAX	Counter
	ACCESS	read-only
	STATUS	mandatory
	DESCRIPTION
		"The total number of physical changes (i.e.,
		an addition or removal of a component or
		sub-component) that have been detected in the
		chassis since cold/warm start of the agent."
	::= { s5ChasGen 7 }

s5ChasGblPhysLstChng OBJECT-TYPE
	SYNTAX	TimeTicks
	ACCESS	read-only
	STATUS	mandatory
	DESCRIPTION
		"The value of sysUpTime when the last
		physical change (i.e., addition or
		removal of a module or sub-module) was
		detected in the chassis. If none have
		been detected since cold/warm start of
		the agent, then the value is zero."
	::= { s5ChasGen 8 }

s5ChasGblAttChngs OBJECT-TYPE
	SYNTAX	Counter
	ACCESS	read-only
	STATUS	mandatory
	DESCRIPTION
		"The total number of attachment changes
		across all boards in the chassis that have
		been detected since cold/warm start of
		the agent."
	::= { s5ChasGen 9 }

s5ChasGblAttLstChng OBJECT-TYPE
	SYNTAX	TimeTicks
	ACCESS	read-only
	STATUS	mandatory
	DESCRIPTION
		"The value of sysUpTime when the last
		attachment change on any board in the chassis
		was detected. If none have been detected
		since cold/warm start of the agent, then the
		value is zero."
	::= { s5ChasGen 10 }

s5ChasGblConfChngs OBJECT-TYPE
	SYNTAX	Counter
	ACCESS	read-only
	STATUS	mandatory
	DESCRIPTION
		"The total number of configuration changes
		(other than attachment changes, or physical
		additions or removals) across all boards in
		the chassis that have been detected since
		cold/warm start of the agent."
	::= { s5ChasGen 11 }

s5ChasGblConfLstChng OBJECT-TYPE
	SYNTAX	TimeTicks
	ACCESS	read-only
	STATUS	mandatory
	DESCRIPTION
		"The value of sysUpTime when the last
		configuration change (other than attachment
		changes, or physical additions or removals)
		on any board in the chassis was detected.
		If none have been detected since cold/warm
		start of the agent, then the value is zero."
	::= { s5ChasGen 12 }

-- Chassis Group Table


s5ChasGrpTable OBJECT-TYPE
	SYNTAX	SEQUENCE OF S5ChasGrpEntry
	ACCESS	not-accessible
	STATUS	mandatory
	DESCRIPTION
		"A table that contains information about
		each group that can contain chassis
		components."
	::= { s5ChasGrp 1 }

s5ChasGrpEntry OBJECT-TYPE
	SYNTAX	S5ChasGrpEntry
	ACCESS	not-accessible
	STATUS	mandatory
	DESCRIPTION
		"A row in the group table.
		Rows can not be created or deleted via
		SNMP requests. The number of entries
		is determined by the physical construction
		of the chassis."
	INDEX	{ s5ChasGrpIndx }
	::= { s5ChasGrpTable 1 }

S5ChasGrpEntry ::= SEQUENCE {
	s5ChasGrpIndx INTEGER,
	s5ChasGrpType OBJECT IDENTIFIER,
	s5ChasGrpDescr DisplayString,
	s5ChasGrpMaxEnts INTEGER,
	s5ChasGrpNumEnts INTEGER,
	s5ChasGrpPhysChngs Counter,
	s5ChasGrpPhysLstChng TimeTicks,
	s5ChasGrpEncodeFactor INTEGER
	}

s5ChasGrpIndx OBJECT-TYPE
	SYNTAX	INTEGER (1..32767)
	ACCESS	read-only
	STATUS	mandatory
	DESCRIPTION
		"The index of the group."
	::= { s5ChasGrpEntry 1 }

s5ChasGrpType OBJECT-TYPE
	SYNTAX	OBJECT IDENTIFIER
	ACCESS	read-only
	STATUS	mandatory
	DESCRIPTION
		"The type of the group. The group type
		determines the types of items that can
		be plugged into the positions in the
		group. The groups are defined under
		s5ChasGrpTypeVal in the Registration MIB."
	::= { s5ChasGrpEntry 2 }

s5ChasGrpDescr OBJECT-TYPE
	SYNTAX	DisplayString (SIZE(0..32))
	ACCESS	read-only
	STATUS	mandatory
	DESCRIPTION
		"The description of the group. If not
		available, the value is a zero length
		string."
	::= { s5ChasGrpEntry 3 }

s5ChasGrpMaxEnts OBJECT-TYPE
	SYNTAX	INTEGER (-1..32767)
	ACCESS	read-only
	STATUS	mandatory
	DESCRIPTION
		"The maximum number of entries
		in the group. If not available, a
		value of -1 is returned."
	::= { s5ChasGrpEntry 4 }

s5ChasGrpNumEnts OBJECT-TYPE
	SYNTAX	INTEGER (-1..32767)
	ACCESS	read-only
	STATUS	mandatory
	DESCRIPTION
		"The current number of entries
		in the group. If not available,
		a value of -1 is returned."
	::= { s5ChasGrpEntry 5 }

s5ChasGrpPhysChngs OBJECT-TYPE
	SYNTAX	Counter
	ACCESS	read-only
	STATUS	mandatory
	DESCRIPTION
		"The total number of physical changes (i.e.,
		an addition or removal of a component or
		sub-component) that have been detected in
		the group since cold/warm start of the agent."
	::= { s5ChasGrpEntry 6 }

s5ChasGrpPhysLstChng OBJECT-TYPE
	SYNTAX	TimeTicks
	ACCESS	read-only
	STATUS	mandatory
	DESCRIPTION
		"The value of sysUpTime that the last
		physical change (i.e., addition or
		removal of a module or sub-module) was
		detected in the group. If none have been
		detected since cold/warm start of the
		agent, then the value is zero."
	::= { s5ChasGrpEntry 7 }

s5ChasGrpEncodeFactor OBJECT-TYPE
	SYNTAX	INTEGER
	ACCESS	read-only
	STATUS	mandatory
	DESCRIPTION
		"The multiplication factor used in encoding
		the component index of a component in the group.
		The component index for any group should be
		determined in conjunction with this object for
		that group.  A value of 1 indicates 'no encoding'.

		Stackable platforms:
		  The component index is encoded using the
		  following formula:
		    Component Index =
		       (Unit# * s5ChasGrpEncodeFactor) + Module#

		  Where:  Unit# is obtained from s5ChasComIndx
		          for the Unit Group, and Module# is the
		          module number in a unit starting from 1
		          and increases in a left-to-right and
		          bottom-to-top fashion.
      
		NonStackable platforms:
		  These NMMs like 5310, 5510 will always return a
		  value of 1 for this object.  Encoding/decoding
		  should not be performed in this case."
		::= { s5ChasGrpEntry 8 }

-- Component (and sub-component) Table


s5ChasComTable OBJECT-TYPE
	SYNTAX	SEQUENCE OF S5ChasComEntry
	ACCESS	not-accessible
	STATUS	mandatory
	DESCRIPTION
		"A table that contains information
		about each chassis level component
		and sub-component."
	::= { s5ChasCom 1 }

s5ChasComEntry OBJECT-TYPE
	SYNTAX	S5ChasComEntry
	ACCESS	not-accessible
	STATUS	mandatory
	DESCRIPTION
		"A row in the component/sub-component
		table. Rows can not be created or
		deleted via SNMP requests. Entries are
		created and deleted when components or
		sub-components are inserted or removed
		from the chassis."
	INDEX	{ s5ChasComGrpIndx,
		  s5ChasComIndx,
		  s5ChasComSubIndx }
	::= { s5ChasComTable 1 }

S5ChasComEntry ::= SEQUENCE {
	s5ChasComGrpIndx INTEGER,
	s5ChasComIndx INTEGER,
	s5ChasComSubIndx INTEGER,

	s5ChasComType OBJECT IDENTIFIER,
	s5ChasComDescr DisplayString,
	s5ChasComVer DisplayString,
	s5ChasComSerNum DisplayString,
	s5ChasComLstChng TimeTicks,

	s5ChasComAdminState INTEGER,
	s5ChasComOperState INTEGER,

	s5ChasComMaxSubs INTEGER,
	s5ChasComNumSubs INTEGER,

	s5ChasComRelPos INTEGER,
	s5ChasComLocation DisplayString,
	s5ChasComGroupMap INTEGER
	}

s5ChasComGrpIndx OBJECT-TYPE
	SYNTAX	INTEGER (1..32767)
	ACCESS	read-only
	STATUS	mandatory
	DESCRIPTION
		"The index of the chassis level group which
		contains this component."
	::= { s5ChasComEntry 1 }

s5ChasComIndx OBJECT-TYPE
	SYNTAX	INTEGER (1..32767)
	ACCESS	read-only
	STATUS	mandatory
	DESCRIPTION
		"The index of the component in the group.
		For example, for modules in the 'board'
		group, this is the slot number."
	::= { s5ChasComEntry 2 }

s5ChasComSubIndx OBJECT-TYPE
	SYNTAX	INTEGER (0..32767)
	ACCESS	read-only
	STATUS	mandatory
	DESCRIPTION
		"If this table entry (i.e. table row)
		describes a component, then the value is
		zero. Otherwise, this table entry describes
		a sub-component and this is the index of
		the sub-component."
	::= { s5ChasComEntry 3 }

s5ChasComType OBJECT-TYPE
	SYNTAX	OBJECT IDENTIFIER
	ACCESS	read-only
	STATUS	mandatory
	DESCRIPTION
		"The type of component/sub-component. The
		values are defined under s5ChasComTypeVal
		in the Registration MIB."
	::= { s5ChasComEntry 4 }

s5ChasComDescr OBJECT-TYPE
	SYNTAX	DisplayString (SIZE(0..64))
	ACCESS	read-only
	STATUS	mandatory
	DESCRIPTION
		"A description of the component/sub-component.
		If not available, the value is a zero length
		string."
	::= { s5ChasComEntry 5 }

s5ChasComVer OBJECT-TYPE
	SYNTAX	DisplayString (SIZE(0..32))
	ACCESS	read-only
	STATUS	mandatory
	DESCRIPTION
		"The version number of the component/sub-component.
		If not available, the value is a zero length
		string."
	::= { s5ChasComEntry 6 }

s5ChasComSerNum OBJECT-TYPE
	SYNTAX	DisplayString (SIZE(0..32))
	ACCESS	read-only
	STATUS	mandatory
	DESCRIPTION
		"The serial number of the component/sub-component.
		If not available, the value is a zero length
		string."
	::= { s5ChasComEntry 7 }

s5ChasComLstChng OBJECT-TYPE
	SYNTAX	TimeTicks
	ACCESS	read-only
	STATUS	mandatory
	DESCRIPTION
		"The value of sysUpTime when it was
		detected that the component/sub-component
		was added to the chassis. If this has not
		occurred since the cold/warm start of the
		agent, then the value is zero."
	::= { s5ChasComEntry 8 }

s5ChasComAdminState OBJECT-TYPE
	SYNTAX	INTEGER {
		other(1),
		notAvail(2),
		disable(3),
		enable(4),
		reset(5),
		test(6)
		}
	ACCESS	read-write
	STATUS	mandatory
	DESCRIPTION
		"The desired state of the component/sub-component.
		The values that are read-only are:
		  other(1)......currently in some other state
		  notAvail(2)...actual value is not available

		The possible values that can be read and
		written are:
		  disable(3)...disable operation
		  enable(4)....enable operation
		  reset(5).....reset component
		  test(6)......start self test of component, with
		                 the result to be normal(5),
		                 warning(8), nonFatalErr(9),
		                 or fatalErr(10) in object
		                 s5ChasComOperState
		The allowable (and meaningful) values
		are determined by the component type."
	::= { s5ChasComEntry 9 }

s5ChasComOperState OBJECT-TYPE
	SYNTAX	INTEGER {
		other(1),
		notAvail(2),
		removed(3),
		disabled(4),
		normal(5),
		resetInProg(6),
		testing(7),
		warning(8),
		nonFatalErr(9),
                fatalErr(10),
		notConfig(11),
		obsoleted(12)
		}
	ACCESS	read-only
	STATUS	mandatory
	DESCRIPTION
		"The current operational state of the
		component. The possible values are:
		  other(1).........some other state
		  notAvail(2)......state not available
		  removed(3).......component removed
		  disabled(4)......operation disabled
		  normal(5)........normal operation
		  resetInProg(6)...reset in progress
		  testing(7).......doing a self test
		  warning(8).......operating at warning level
		  nonFatalErr(9)...operating at error level
		  fatalErr(10).....error stopped operation
                  notConfig(11)....module needs to be configured
		  obsoleted(12)...module is obsoleted but in the chassis
		The allowable (and meaningful) values
		are determined by the component type."
	::= { s5ChasComEntry 10 }

s5ChasComMaxSubs OBJECT-TYPE
	SYNTAX	INTEGER (-1..32767)
	ACCESS	read-only
	STATUS	mandatory
	DESCRIPTION
		"The potential number of sub-components
		that can be attached to the component.
		A value of zero means none. A value of -1
		indicates that no component information is
		available. The actual number of
		installed sub-components is found in
		s5ChasComNumSubs.
		If this entry is a sub-component, then
		this object has a value of zero."
	::= { s5ChasComEntry 11 }

s5ChasComNumSubs OBJECT-TYPE
	SYNTAX	INTEGER (-1..32767)
	ACCESS	read-only
	STATUS	mandatory
	DESCRIPTION
		"The actual number of sub-components that
		are attached to the component. A value of
		zero means none. A value of -1 indicates
		that no component information is available.
		The potential number of sub-components
		that can be installed is found in
		s5ChasComMaxSubs.
		If this entry is a sub-component, then
		this object has the value of zero."
	::= { s5ChasComEntry 12 }

s5ChasComRelPos OBJECT-TYPE
	SYNTAX	INTEGER (0..32767)
	ACCESS	read-only
	STATUS	mandatory
	DESCRIPTION
		"This object describes the position of
		each component in the unit group relative
		to each other.  Components in the unit group
		are numbered in the ascending order with the
		uppermost component being numbered one.  The
		value of this object should never be greater
		than the value of s5ChasGrpMaxEnts.  If not
		available, a value of zero will be returned.

		Note:  This object is only implemented in
		       agents that support 'virtual' chassis."
	::= { s5ChasComEntry 13 }

s5ChasComLocation OBJECT-TYPE
	SYNTAX	DisplayString (SIZE(0..32))
	ACCESS	read-write
	STATUS	mandatory
	DESCRIPTION
		"This object provides geographic location
		information of a component in a system
		modeled as a chassis, but possibly physically
		implemented with geographically separate devices
		connected together to exchange managment information.
		Chassis' modeled in this manner are sometimes refered
		to as 'virtual chassis'.  An example value is:
		      '4th flr wiring closet in blg A'.

		Notes:  1.)  This object is applicable only to
		             components that can be found in either
		             the Board or Unit groups.  If the
		             information is unavailable (i.e., not
		             modeling a virtual chassis or component
		             is not in Board or Unit group), the value
		             is a zero length string.
		        2.)  If this object is applicable and is not
		             assigned a value via a SNMP SET PDU when
		             the row  is created, the value will default
		             to the value of the object s5ChasComSerNum."
	::= { s5ChasComEntry 14 }

s5ChasComGroupMap OBJECT-TYPE
	SYNTAX	INTEGER (0..32767)
	ACCESS	read-only
	STATUS	mandatory
	DESCRIPTION
		"This object describes the group mapping of
		each component in the chassis.  For the
		components in the unit group, the value of this
		object should be the backplane number to which the
		unit is connected.  The value of this object should
		never be greater than the value of s5ChasGrpMaxEnts.
		If not available, a value of zero should be returned."
	::= { s5ChasComEntry 15 }

-- Board Table


s5ChasBrdTable OBJECT-TYPE
	SYNTAX	SEQUENCE OF S5ChasBrdEntry
	ACCESS	not-accessible
	STATUS	mandatory
	DESCRIPTION
		"A table containing information about each
		board that can be inserted into a slot.
		These include boards such as Repeater Modules
		and Network Management Modules."
	::= { s5ChasBrd 1 }

s5ChasBrdEntry OBJECT-TYPE
	SYNTAX	S5ChasBrdEntry
	ACCESS	not-accessible
	STATUS	mandatory
	DESCRIPTION
		"A row in the board table. Entries can not
		be created or deleted via SNMP. Entries are
		created and deleted when boards are inserted
		or removed from slots in the chassis."
	INDEX	{ s5ChasBrdIndx }
	::= { s5ChasBrdTable 1 }

S5ChasBrdEntry ::= SEQUENCE {
	s5ChasBrdIndx INTEGER,
	s5ChasBrdLeds OCTET STRING,
	s5ChasBrdNumAtt INTEGER,
	s5ChasBrdAttChngs Counter,
	s5ChasBrdAttLstChng TimeTicks,
	s5ChasBrdStatusDsply DisplayString,
	s5ChasBrdDateCode DisplayString,
	s5ChasBrdCfgSrc INTEGER,
	s5ChasBrdCfgChngs Counter
	}

s5ChasBrdIndx OBJECT-TYPE
	SYNTAX	INTEGER (1..255)
	ACCESS	read-only
	STATUS	mandatory
	DESCRIPTION
		"The index of the board. This corresponds to
		the index of the slot containing the board."
	::= { s5ChasBrdEntry 1 }

s5ChasBrdLeds OBJECT-TYPE
	SYNTAX	OCTET STRING
	ACCESS	read-only
	STATUS	mandatory
	DESCRIPTION
		"A bit array that contains the value of the
		front panel LEDs and the annunciator. This is
		a packed bit string; each LED is encoded into
		4 bits (a nibble). The first nibble is stored
		in the high order bits of the first octet. The
		second nibble is stored in the low order bits
		the first octet, etc. However, the current
		mapping is that the first three nibbles are
		reserved, the fourth nibble has the value of
		the 'annunciator', and the 'normal' LEDs start
		with the fifth nibble. If the LED values are not
		available, a zero length string is returned. The
		following shows the meaning of each bit (bit 0 is
		the least significant bit) when it has a value
		of one:

		  bit  meaning
		  ---  -------
		   0   green light
		   1   yellow light
		   2   blinking
		   3   reserved"
	::= { s5ChasBrdEntry 2 }

s5ChasBrdNumAtt OBJECT-TYPE
	SYNTAX	INTEGER (0..255)
	ACCESS	read-only
	STATUS	mandatory
	DESCRIPTION
		"The total number of backplane network
		attachment points on the board.
		This may vary based on the mode of the
		board for FDDI."
	::= { s5ChasBrdEntry 3 }

s5ChasBrdAttChngs OBJECT-TYPE
	SYNTAX	Counter
	ACCESS	read-only
	STATUS	mandatory
	DESCRIPTION
		"The total number of attachment changes
		for the board that have been detected since
		cold/warm start of the agent or since
		the board was inserted."
	::= { s5ChasBrdEntry 4 }

s5ChasBrdAttLstChng OBJECT-TYPE
	SYNTAX	TimeTicks
	ACCESS	read-only
	STATUS	mandatory
	DESCRIPTION
		"The value of sysUpTime when the last
		attachment change on the board
		has detected. If none have been detected
		since cold/warm start of the agent, then
		the value is zero."
	::= { s5ChasBrdEntry 5 }

s5ChasBrdStatusDsply OBJECT-TYPE
	SYNTAX	DisplayString (SIZE(0..48))
	ACCESS	read-only
	STATUS	mandatory
	DESCRIPTION
		"The current ASCII character display of
		the board. The length returned should
		match the length of the display.
		Boards with multiple displays should
		return the values concatenated together.
		Boards with no display hardware should
		return a zero length string."
	::= { s5ChasBrdEntry 6 }

s5ChasBrdDateCode OBJECT-TYPE
	SYNTAX	DisplayString (SIZE(0..8))
	ACCESS	read-only
	STATUS	mandatory
	DESCRIPTION
		"The date of manufacture of the board
		in ASCII in the format: YYYYmmdd. For
		example, the value for April 13, 1993
		is 19930413. If not available, the
		value is a zero-length string."
	::= { s5ChasBrdEntry 7 }

s5ChasBrdCfgSrc OBJECT-TYPE
	SYNTAX	INTEGER {
		other(1),
		dfltJmpr(2),
		prmMem(3),
		brdCfg(4),
		sm(5),
		smDfltJmpr(6),
		smPrmMem(7),
		smBrdCfg(8)
		}
	ACCESS	read-only
	STATUS	mandatory
	DESCRIPTION
		"The source of the configuration
		at the last board reset. The values
		are:
		  other(1)........unknown or some other value
		  dfltJmpr(2).....default jumpers
		  prmMem(3).......permanent memory on board
		  brdCfg(4).......saved configuration on board
		  sm(5)...........supervisor
		  smDfltJmpr(6)...SM and default jumpers
		  smPrmMem(7).....SM and permanent memory on board
		  smBrdCfg(8).....SM and saved configuration on board"
	::= { s5ChasBrdEntry 8 }

s5ChasBrdCfgChngs OBJECT-TYPE
	SYNTAX	Counter
	ACCESS	read-only
	STATUS	mandatory
	DESCRIPTION
		"The total number of configuration
		changes for the board that have been
		detected since cold/warm start of the
		agent or since the board was inserted."
	::= { s5ChasBrdEntry 9 }

-- Attachment Point Table


s5ChasAttTable OBJECT-TYPE
	SYNTAX	SEQUENCE OF S5ChasAttEntry
	ACCESS	not-accessible
	STATUS	mandatory
	DESCRIPTION
		"A table containing information about each
		backplane attachment point on a board.
		The number of entries for a board is the
		value of s5ChasBrdNumAtt."
	::= { s5ChasBrd 2 }

s5ChasAttEntry OBJECT-TYPE
	SYNTAX	S5ChasAttEntry
	ACCESS	not-accessible
	STATUS	mandatory
	DESCRIPTION
		"A row in the attachment point table.
		Entries can not be created or deleted
		via SNMP. Entries are created and deleted
		when boards are inserted or removed from
		slots in the chassis, or the number of
		attachment points is changed."
	INDEX	{ s5ChasAttBrdIndx,
		  s5ChasAttIndx }
	::= { s5ChasAttTable 1 }

S5ChasAttEntry ::= SEQUENCE {
	s5ChasAttBrdIndx INTEGER,
	s5ChasAttIndx INTEGER,
	s5ChasAttDfltAtt AttId,
	s5ChasAttCurAtt AttId,
	s5ChasAttChngs Counter,
	s5ChasAttLstChng TimeTicks,
	s5ChasAttClusterConnCapability OCTET STRING
	}

s5ChasAttBrdIndx OBJECT-TYPE
	SYNTAX	INTEGER (1..255)
	ACCESS	read-only
	STATUS	mandatory
	DESCRIPTION
		"The index of the board. This corresponds to
		the index of the slot containing the board."
	::= { s5ChasAttEntry 1 }

s5ChasAttIndx OBJECT-TYPE
	SYNTAX	INTEGER (1..255)
	ACCESS	read-only
	STATUS	mandatory
	DESCRIPTION
		"The index of the attachment point on
		the board."
	::= { s5ChasAttEntry 2 }

s5ChasAttDfltAtt OBJECT-TYPE
	SYNTAX	AttId
	ACCESS	read-only
	STATUS	mandatory
	DESCRIPTION
		"The default setting for the attachment
		point. An attachment point may be attached
		to a local channel, not attached to any
		backplane network, or attached to a media
		specific backplane network. (The valid choices
		depend on each specific attachment point.)
		NOTE: This value will always be valid
		and may change when the backplane divider
		switch setting is changed."
	::= { s5ChasAttEntry 3 }

s5ChasAttCurAtt OBJECT-TYPE
	SYNTAX	AttId
	ACCESS	read-write
	STATUS	mandatory
	DESCRIPTION
		"The current setting for the attachment
		point. The slot position of the board,
		the setting of the backplane divider switch(es),
		and the mode setting affect which backplane
		networks are valid values. Also, some boards
		may put limitations on which backplane
		network(s) or local channel(s) may be used."
	::= { s5ChasAttEntry 4 }

s5ChasAttChngs OBJECT-TYPE
	SYNTAX	Counter
	ACCESS	read-only
	STATUS	mandatory
	DESCRIPTION
		"The total number of attachment changes
		for the attachment point that have been
		detected since cold/warm start of the agent."
	::= { s5ChasAttEntry 5 }

s5ChasAttLstChng OBJECT-TYPE
	SYNTAX	TimeTicks
	ACCESS	read-only
	STATUS	mandatory
	DESCRIPTION
		"The value of sysUpTime when the last
		attachment change for the attachment
		point was detected. If none have been
		detected since cold/warm start of the
		agent, then the value is zero."
	::= { s5ChasAttEntry 6 }

s5ChasAttClusterConnCapability OBJECT-TYPE
	SYNTAX	OCTET STRING (SIZE(8))
	ACCESS	read-only
	STATUS	mandatory
	DESCRIPTION
		"A bit array that contains the bit map
		representing all available backplane
		segment and local segment connections for
		the cluster.  One bit is also reserved to
		indicate if the cluster has an isolate
		capability.

		The first 31 bits of the array represent
		the backplane numbers, starting from the
		lower order bit. Bit 32 indicates whether
		the Cluster has a null connection capability.
		The bits in the fifth and sixth octets,
		starting with bits in the lower order octet,
		represent local segments that the cluster
		can connect to.

		A bit with a value of 1 means that the
		cluster is capable of  connecting to the
		corresponding backplane segment, local segment
		or null segment."
	::= { s5ChasAttEntry 7 }

-- Local Channel Table


s5ChasLocChanTable OBJECT-TYPE
	SYNTAX	SEQUENCE OF S5ChasLocChanEntry
	ACCESS	not-accessible
	STATUS	mandatory
	DESCRIPTION
		"A table containing information about each
		'dual mode' local channel on a board."
	::= { s5ChasBrd 3 }

s5ChasLocChanEntry OBJECT-TYPE
	SYNTAX	S5ChasLocChanEntry
	ACCESS	not-accessible
	STATUS	mandatory
	DESCRIPTION
		"A row in the local channel table.
		Entries can not be created or deleted
		via SNMP. Entries are added or removed
		by adding or removing a board that has
		a 'dual mode' local channel from a slot
		in the chassis."
	INDEX	{ s5ChasLocChanBrdIndx,
		  s5ChasLocChanIndx }
	::= { s5ChasLocChanTable 1 }

S5ChasLocChanEntry ::= SEQUENCE {
	s5ChasLocChanBrdIndx INTEGER,
	s5ChasLocChanIndx LocChan,
	s5ChasLocChanBkplMode INTEGER
	}

s5ChasLocChanBrdIndx OBJECT-TYPE
	SYNTAX	INTEGER (1..255)
	ACCESS	read-only
	STATUS	mandatory
	DESCRIPTION
		"The index of the board. This corresponds to
		the index of the slot containing the board."
	::= { s5ChasLocChanEntry 1 }

s5ChasLocChanIndx OBJECT-TYPE
	SYNTAX	LocChan
	ACCESS	read-only
	STATUS	mandatory
	DESCRIPTION
		"The index of the local channel."
	::= { s5ChasLocChanEntry 2 }

s5ChasLocChanBkplMode OBJECT-TYPE
	SYNTAX	INTEGER {
		other(1),
		connected(2),
		notConnected(3)
		}
	ACCESS	read-write
	STATUS	mandatory
	DESCRIPTION
		"Indicates the attachment/isolation
		mode of a local channel to a backplane
		channel. The values that are read/write are:
		  connected(2)......connect local chan N to bkpl N
		  notConnected(3)...disconnect local chan N from bkpl

		The possible values that can be read are:
		  other(1)..........unknown
		  connected(2)......local chan N connected to bkpl N
		  notConnected(3)...local chan N isolated from bkpl N"
	::= { s5ChasLocChanEntry 3 }

-- Storage Area Table


s5ChasStoreTable OBJECT-TYPE
	SYNTAX	SEQUENCE OF S5ChasStoreEntry
	ACCESS	not-accessible
	STATUS	mandatory
	DESCRIPTION
		"A table listing the storage areas
		on each component/sub-component in
		the chassis. The number is determined
		by the components in the chassis
		which have manageable storage areas.
		Examples of storage areas include
		RAM(main memory), FLASH, ROM,
		EEPROM, etc. This does not include
		disk drives."
	::= { s5ChasStore 1 }

s5ChasStoreEntry OBJECT-TYPE
	SYNTAX	S5ChasStoreEntry
	ACCESS	not-accessible
	STATUS	mandatory
	DESCRIPTION
		"A row in the table of storage areas.
		The entries can not be created or
		deleted via SNMP requests. Only those
		components/sub-components that have
		storage areas that are installed are
		present. Storage areas that are on
		components have a sub-component
		index value of zero. Storage areas that
		are on sub-components have a non-zero
		sub-component index value."
	INDEX	{ s5ChasStoreGrpIndx,
		  s5ChasStoreComIndx,
		  s5ChasStoreSubIndx,
		  s5ChasStoreIndx }
	::= { s5ChasStoreTable 1 }

S5ChasStoreEntry ::= SEQUENCE {
	s5ChasStoreGrpIndx INTEGER,
	s5ChasStoreComIndx INTEGER,
	s5ChasStoreSubIndx INTEGER,
	s5ChasStoreIndx INTEGER,

	s5ChasStoreType OBJECT IDENTIFIER,
	s5ChasStoreCurSize INTEGER,
	s5ChasStoreCntntVer DisplayString
	}

s5ChasStoreGrpIndx OBJECT-TYPE
	SYNTAX	INTEGER (1..32767)
	ACCESS	read-only
	STATUS	mandatory
	DESCRIPTION
		"The index of the chassis level group
		which contains the component or
		sub-component containing the storage
		area."
	::= { s5ChasStoreEntry 1 }

s5ChasStoreComIndx OBJECT-TYPE
	SYNTAX	INTEGER (1..32767)
	ACCESS	read-only
	STATUS	mandatory
	DESCRIPTION
		"The index of the component or
		the component which contains the
		sub-component containing the
		storage area."
	::= { s5ChasStoreEntry 2 }

s5ChasStoreSubIndx OBJECT-TYPE
	SYNTAX	INTEGER (0..32767)
	ACCESS	read-only
	STATUS	mandatory
	DESCRIPTION
		"If the storage area is on a component,
		then the value zero. Otherwise, the
		storage area is on a sub-component and
		this is the index of the sub-component."
	::= { s5ChasStoreEntry 3 }

s5ChasStoreIndx OBJECT-TYPE
	SYNTAX	INTEGER (1..255)
	ACCESS	read-only
	STATUS	mandatory
	DESCRIPTION
		"The index of the storage area on the
		component or sub-component."
	::= { s5ChasStoreEntry 4 }

s5ChasStoreType OBJECT-TYPE
	SYNTAX	OBJECT IDENTIFIER
	ACCESS	read-only
	STATUS	mandatory
	DESCRIPTION
		"The storage area type on the containing
		component/sub-component. The values
		are defined under the .0 branch of the
		value of s5ChasComType for the
		component/sub-component containing the
		storage area in the Registration MIB."
	::= { s5ChasStoreEntry 5 }

s5ChasStoreCurSize OBJECT-TYPE
	SYNTAX	INTEGER (-1..2147483647)
	ACCESS	read-only
	STATUS	mandatory
	DESCRIPTION
		"The current size of the storage
		area in bytes. A value of zero
		means the storage area is not installed
		or not usable. A value of -1 indicates
		that the size is unknown (or unavailable)."
	::= { s5ChasStoreEntry 6 }

s5ChasStoreCntntVer OBJECT-TYPE
	SYNTAX	DisplayString (SIZE (0..255))
	ACCESS	read-only
	STATUS	mandatory
	DESCRIPTION
		"The version of the contents (i.e., the
		code or data) of the storage area in the
		form 'major.minor.maintenance[letters]'.
		If not known or not available, then the value
		is a zero length string. If multiple
		contents are stored in this container, the
		the value will contain multiple sub-versions,
		each separated by a semicolon (;)."
	::= { s5ChasStoreEntry 7 }

-- Supervisor Information


s5ChasSmLeds OBJECT-TYPE
	SYNTAX	OCTET STRING
	ACCESS	read-only
	STATUS	mandatory
	DESCRIPTION
		"A bit array that contains the value of the
		supervisor LEDs. (The format of these are the
		same as the format for object s5ChasBrdLeds.)
		If not available, a zero length string is
		returned."
	::= { s5ChasSm 1 }

s5ChasSmDateCode OBJECT-TYPE
	SYNTAX	DisplayString (SIZE(0..8))
	ACCESS	read-only
	STATUS	mandatory
	DESCRIPTION
		"The date of manufacture of the SM module
		in ASCII in the format: YYYYmmdd. For
		example, the value for April 13, 1993
		is 19930413. If not available, a zero
		length string is returned"
	::= { s5ChasSm 2 }

END
-- SECTION 1: Top Level Definitions

S5-AGENT-MIB DEFINITIONS ::= BEGIN


-- 5000 Agent MIB Release 1.3.9
-- Revision 10/14/98

-- Copyright 1995-98 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	IpAddress, TimeTicks
		FROM RFC1155-SMI
	OBJECT-TYPE
		FROM RFC-1212
	DisplayString
		FROM RFC1213-MIB
	s5Agent
		FROM S5-ROOT-MIB
	TimeIntervalSec, IpxAddress, MacAddress
		FROM S5-TCS-MIB;


-- Agent Groups

s5AgentHw	OBJECT IDENTIFIER ::= { s5Agent 1 }
s5AgentInfo	OBJECT IDENTIFIER ::= { s5Agent 2 }
s5AgentMgmt	OBJECT IDENTIFIER ::= { s5Agent 3 }



-- SECTION 2: MIB Objects

-- Hardware Information

s5AgMyGrpIndx OBJECT-TYPE
	SYNTAX	INTEGER (1..32767)
	ACCESS	read-only
	STATUS	mandatory
	DESCRIPTION
		"The index of the group containing
		the agent."
	::= { s5AgentHw 1 }

s5AgMyComIndx OBJECT-TYPE
	SYNTAX	INTEGER (1..32767)
	ACCESS	read-only
	STATUS	mandatory
	DESCRIPTION
		"The index of the component containing
		the agent."
	::= { s5AgentHw 2 }


-- Global Information

s5AgentGbl	OBJECT IDENTIFIER ::= { s5AgentInfo 1 }

s5AgInfoReBoot OBJECT-TYPE
	SYNTAX	INTEGER {
		other(1),
		running(2),
		restart(3),
		reboot(4),
                reset(5),
                download(6),
                downloadAndRestart(7),
                downloadAndReboot(8),
                downloadAndReset(9)
		}
	ACCESS	read-write
	STATUS	mandatory
	DESCRIPTION
		"Action object to reboot the agent.
		The following values can only be read:
		  other(1).....agent in unknown or other state
		  running(2)...agent running

		The following values can be written:
		  restart(3)...restart agent (i.e., jump to
		                 beginning of agent code)
		  reboot(4)....start boot sequence for agent
		                 (i.e., jump to beginning of
		                 boot firmware)
		  reset(5).....do a hardware reset
                  download(6)..............activate download of
                               a new agent
                  downloadAndRestart(7)....activate download of
                               a new agent and restart
                  downloadAndReboot(8).....activate download of
                               a new agent and reboot
                  downloadAndReset(9)......activate download of
                               a new agent and reset

                 If s5AgInfoScheduleBootTime is set in the same PDU as
                 s5AgInfoReBoot, the action specified occurs when the
                 scheduled time reaches zero; otherwise, the action
                 occurs immediately. The agent does best efforts to
                 return a response before the action occurs.
 
                 If any of the combined download actions are
                 requested, neither action occurs until the
                 expiry of s5AgInfoScheduleBootTime, if set."
	::= { s5AgentGbl 1 }

s5AgInfoWriteCfg OBJECT-TYPE
	SYNTAX	INTEGER {
		other(1),
		valid(2),
		write(3)
		}
	ACCESS	read-write
	STATUS	mandatory
	DESCRIPTION
		"Action object to cause current configuration
		settings to be written to local nonvolatile
		storage. The following values can only be read:
		  other(1)...some unknown or other state
		  valid(2)...contents valid

		The following value can be written:
		  write(3)...write configuration settings to
		               local storage (such as nonvol)

		If the write operation write fails, then the
		agent will return error 'genErr' on the SET."
	::= { s5AgentGbl 2 }

s5AgInfoMgmtProtocolNxtBoot OBJECT-TYPE
	SYNTAX	INTEGER {
		other(1),
		ipOnly(2),
		ipxOnly(3),
		ipAndIpx(4)
		}
	ACCESS	read-write
	STATUS	mandatory
	DESCRIPTION
		"The transport protocol(s) to use after
		the next boot of the agent. The following
		value is read-only:
		  other(1)....unknown or some other protocol

		The following value is read-write:
		  ipOnly(2).....only IP
		  ipxOnly(3)....only IPX
		  ipAndIpx(4)...IP and IPX."
	::= { s5AgentGbl 3 }

s5AgInfoMgmtProtocolCur OBJECT-TYPE
	SYNTAX	INTEGER {
		other(1),
		ipOnly(2) ,
		ipxOnly(3),
		ipAndIpx(4)
		}
	ACCESS	read-write
	STATUS	mandatory
	DESCRIPTION
		"The current transport protocol(s) that are
		being supported by the agent. The following
		value is read-only:
		  other(1)....unknown or some other protocol

		The following value is read-write: 
		  ipOnly(2).....only IP
		  ipxOnly(3)....only IPX
		  ipAndIpx(4)...IP and IPX.

		When the IP protocol stack is not enabled,
		the agent will not respond to PING or SNMP
		requests over IP.

		When the IPX protocol stack is not enabled,
		the agent will not respond to diagnostic SAP or
		SNMP requests over IPX.

		It is suggested that NMS not disable the transport
		they are using."
	::= { s5AgentGbl 4 }

s5AgInfoBootMode OBJECT-TYPE
	SYNTAX	INTEGER {
		other(1),
		local(2),
		net(3)
		}
	ACCESS	read-write
	STATUS	mandatory
	DESCRIPTION
		"The source for initial protocol configuration
		information at next boot. For IP, a setting of
		net(3) means that BOOTP will be used to get the
		agent's IP address(es), load server address, and
		configuration file name.  For IPX, a setting of net(3)
		means SAP will be used to get the agent's Novell
		network number(s), and the configuation filename
		will be loaded from local storage (note - the load
		server address is not needed in a Novell network).

		The following value is read-only:
		  other(1).....not applicable or some other case

		The following values are read-write:
		  local(2).....don't use the network
		  net(3).......try using the network and if that
		                 fails then use protocol configuration
		                 information from local storage.

		Note:   The load server address is not configurable
		        and is not available in this MIB object on a
		        Novell network."
	::= { s5AgentGbl 5 }

s5AgInfoCfgLoadMode OBJECT-TYPE
	SYNTAX	INTEGER {
		other(1),
		local(2),
		net(3),
		locAsBk(4)
		}
	ACCESS	read-write
	STATUS	mandatory
	DESCRIPTION
		"The source from which to load configuration
		information at next boot. The following value
		is read-only:
		  other(1)...not applicable or some other case

		The following values are read-write:
		  local(2).....get from local storage
		  net(3).......load from the network
		  locAsBk(4)...try using network and if it fails
		                 then use local information.

		When local(2) is specified, the configuration
		information is loaded from local storage.
		If the local configuration is not valid
		(checks for ip = 0.0.0.0), then BOOTP is used
		for the IP stack. (In IPX only mode, the IP
		address could be 0.0.0.0 and IPX does not rely
		on the IP address.  The agent checks the IPX
		address, and if the network number of the IPX
		address is equal to 0 the agent uses  SAP).

		When net(3) is specified, the configuration 
		information will be downloaded from the network
		only. The configuration information will never
		be loaded from local storage, even if downloading
		fails and the local configuration information exists.

		When locAsBk(4) is specified, a download of the
		configuration information will be tried over the
		network. If the network download fails then the
		configuration information will be loaded from
		local storage."
	::= { s5AgentGbl 6 }

s5AgInfoImgLoadMode OBJECT-TYPE
	SYNTAX	INTEGER {
		other(1),
		local(2),
		net(3),
		locAsBk(4),
		netIfNewer(5)
		}
	ACCESS	read-write
	STATUS	mandatory
	DESCRIPTION
		"The source from which to load the agent image
		at next boot. The following value is read-only:
		  other(1)...not applicable or some other case

		The following values are read-write:
		  local(2)........get from local storage
		  net(3)..........load from the network
		  locAsBk(4)......try using network and if it fails
		                    then use local information.
		  netIfNewer(5)...try loading image over the net.
		                    If can load image, and it is newer
		                    than the local image, then use it.
		                    Otherwise, use local image.

		If the local image is not valid, the setting will
		be net(3) and cannot be changed to local(2),
		or locAsBk(4) until a valid image file is loaded
		(i.e., error 'badValue' will be returned on SETS with
		value other than net(3)). When the local image is
		not valid and the network download of the image fails,
		the entire boot process will be repeated.

		When local(2) is specified, the image will be loaded
		from local storage.

		When net(3) is specified, the image will be downloaded
		from the network only. The image file will never be
		loaded from local storage, even if downloading fails
		and the local image exists.

		When locAsBk(4) is specified, a download of the image
		will be tried over the network. If the network
		download fails then the image is loaded from local
		storage.

		When netIfNewer(5) is specified, a download of the
		image will be tried over the network. If successful,
		it will then be compared to the image stored in local
		storage. The most recent version of the two will be
		used. If the local image is not valid, the network
		will always be used. If the network download fails
		then the image is loaded from the local storage."
	::= { s5AgentGbl 7 }

s5AgInfoImgSaveMode OBJECT-TYPE
	SYNTAX	INTEGER {
		notAvail(1),
		writeIfDiff(2),
		writeIfNewer(3),
		noWrite(4)
		}
	ACCESS	read-write
	STATUS	mandatory
	DESCRIPTION
		"Indicates what to do with the image (when
		loaded from the network) on the next boot.
		The following value can only be read:
		  notAvail(1)...the save operation is not
		                  available

		The following values can be written (and
		read) if the device supports this capability:
		  writeIfDiff(2)....save image to local storage
		                      at next boot if image is
		                      different from saved contents
		  writeIfNewer(3)...save image to local storage
		                      at next boot if image is
		                      newer than saved contents.
		  noWrite(4)........do not save image to local
		                      storage at next boot, even if
		                      image is newer or different."
	::= { s5AgentGbl 8 }

s5AgInfoImgSaveStatus OBJECT-TYPE
	SYNTAX	INTEGER {
		notAvail(1),
		noSave(2),
		saved(3),
		saveFailed(4)
		}
	ACCESS	read-only
	STATUS	mandatory
	DESCRIPTION
		"Indicates what happened to the image file
		on the last boot. The following values
		are returned:
		  notAvail(1).....the save operation is not
		                    available
		  noSave(2).......image not saved since image was
		                    not asked to be saved, or image
		                    was not loaded from the network
		  saved(3)........image saved
		  saveFailed(4)...tried to save image, but failed"
	::= { s5AgentGbl 9 }

s5AgInfoVer OBJECT-TYPE
	SYNTAX	DisplayString (SIZE(0..32))
	ACCESS	read-only
	STATUS	mandatory
	DESCRIPTION
		"The version of the agent in the form
		'major.minor.maintenance[letters]'. This
		is an alias for the value of the object
		s5ChasStoreCntntVer for the RAM of the
		module containing the agent."
	::= { s5AgentGbl 10 }

s5AgInfoLocStorVer OBJECT-TYPE
	SYNTAX	DisplayString (SIZE(0..32))
	ACCESS	read-only
	STATUS	mandatory
	DESCRIPTION
		"The version of the agent image saved in local
		storage such as flash memory in the form
		'major.minor.maintenance[letters]'. If not
		known or not available, then the value is
		a zero length string. This is an alias for
		the value of the object s5ChasStoreCntntVer
		for the local storage of the module containing
		the agent."
	::= { s5AgentGbl 11 }

s5AgInfoNxtBootDfltGwAddr OBJECT-TYPE
	SYNTAX	IpAddress
	ACCESS	read-write
	STATUS	mandatory
	DESCRIPTION
		"The IP address of the default gateway (router)
		for the agent to use after the next boot. (NOTE:
		the current default router is the value of object
		s5AgInfoCurDfltGwAddr (or ipRouteNextHop.0.0.0.0).)

		If not used, then this object has the value
		of 0.0.0.0."
	::= { s5AgentGbl 12 }

s5AgInfoCurDfltGwAddr OBJECT-TYPE
	SYNTAX	IpAddress
	ACCESS	read-write
	STATUS	mandatory
	DESCRIPTION
		"The IP address of the current default gateway
		(router). (NOTE: this is an alias for the object
		ipRouteNextHop in the row of the table
		ipRouteTable which has object ipRouteDest with
		a value of 0.0.0.0.)

		If not used, then this object has the value
		of 0.0.0.0."
	::= { s5AgentGbl 13 }

s5AgInfoDramUsage  OBJECT-TYPE
	SYNTAX	INTEGER  (-1..100)
	ACCESS	read-only
	STATUS	mandatory
	DESCRIPTION
		"An indication of the percentage of DRAM currently
		in use by this agent.  If this information is not
		available the agent shall return -1, otherwise the
		percentage of DRAM in use is returned as an integer
		between 0 and 100.  The percentage is defined as the
		DRAM currently used by  this agent divided by the
		total DRAM available to this agent."
	::= { s5AgentGbl 14 }

s5AgInfoLoadProtocolNxtBoot OBJECT-TYPE
	SYNTAX	INTEGER {
		other(1),
		ipOnly(2),
		ipxOnly(3),
		auto(4)
		}
	ACCESS	read-write
	STATUS	mandatory
	DESCRIPTION
		"The transport protocol(s) over which the 
		agent is to use to load the configuration 
		information and the agent image at the 
		next boot of the agent. The following 
		value is read-only:
		  other(1)....unknown or some other protocol

		The following values are read-write:
		  ipOnly(2)....use load protocol over IP
		  ipxOnly(3)...use load protocol over IPX
		  auto(4)......try using the IP load function
		                 and if that fails then use IPX
		                 load function.  If the IPX
		                 load function also fails, repeat
		                 the same process until one or
		                 the other protocol succeeds."
	::= { s5AgentGbl 15 }

s5AgInfoLoadProtocolLast OBJECT-TYPE
	SYNTAX	INTEGER {
		reserved(1),
		ip(2),
		ipx(3),
		local(4)
		}
	ACCESS	read-only
	STATUS	mandatory
	DESCRIPTION
		"The transport protocol over which the agent image
		and configuration information were last loaded.  The
		following values are read-only:
		  reserved(1)...reserved
		  ip(2).........gotten from the network using
		                  a load protocol over IP
		  ipx(3)........gotten from the network using
		                  a load protocol over IPX
		  local(4)......loaded from local storage."
	::= { s5AgentGbl 16 }


s5AgInfoSlotScope OBJECT-TYPE
      SYNTAX    OCTET STRING
      ACCESS     read-only
      STATUS     mandatory
      DESCRIPTION
              "This object contains information about all
              the slots an agent can manage.  The value is encoded
              in an octet string. One byte has information about 8
              slots. If a bit is set then agent can manage the
              corresponding slot. Byte 1 will have information about
              slots 1-8, byte 2 will have information about
              slots 9-16, and so on. For example an agent that
              can manage slots 2-7 in a 14 slot chassis should have
              the value :
                              8d:00 (0111 1110 0000 0000)
              If an agent returns a string of size 0, then it can
              manage all slots in chassis."
      ::= { s5AgentGbl 17 }

s5AgInfoImgType OBJECT-TYPE
      SYNTAX  INTEGER {
              other(1),
              typeA(2),
              typeB(3),
              typeC(4)
              }
      ACCESS  read-only
      STATUS  mandatory
      DESCRIPTION
              "Indicates the type of agent image. This object is meant
               to distinguish between agents having the same version
               number running on the same hardware, but with dissimilar
               functionality. Following are examples of possible values
               for various enumerations.
               other(1) ....... A unique agent eg., 5310A, 5dn310 etc
               typeA(2) ....... fusion basic agent.
               typeB(2) ....... fusion advanced agent."
      ::= { s5AgentGbl 18 }

s5AgInfoScheduleBootTime OBJECT-TYPE
        SYNTAX  INTEGER (0..10080)
        ACCESS  read-write
        STATUS  mandatory
        DESCRIPTION
                "The time, measured in minutes, remaining until the
                 action(s) set by s5AgInfoReBoot will be performed.
                 This value must be set in the same set request as
                 the value of s5AgInfoReBoot; otherwise, a badValue
                 error is returned.
 
                 If this value has been set, the number returned will
                 count down to zero, and the time remaining in minutes
                 will be rounded up to the next whole minute.
 
                 Actions set via s5AgInfoReBoot can be scheduled for
                 up to seven days in advance.
                 7 * 24 * 60 equals the maximum settable value of
                 10080. If this attribute has not been set, a value of 
                 zero should be returned."
        ::= { s5AgentGbl 19 }
 
s5AgInfoScheduleBootCancel OBJECT-TYPE
        SYNTAX  INTEGER {
                other(1),
                cancel(2)
                 }
        ACCESS  read-write
        STATUS  mandatory
        DESCRIPTION
                "Cancel a scheduled s5AgInfoReboot action.
                The following value is read-only:
                  other(1)...not applicable or some other case
                     This is always the value that return when
                     read.
 
                The following values are read-write:
                  cancel(2)...cancel a scheduled boot.
 
                Setting this attribute to cancel(2) sets s5AgInfoReBoot
                to running(2) and s5AgInfoScheduleBootTime to zero."
        ::= { s5AgentGbl 20 }
  
s5AgInfoNumBootBanks OBJECT-TYPE
        SYNTAX  INTEGER (0..255)
        ACCESS  read-only
        STATUS  mandatory
        DESCRIPTION
                "The number of local storage locations (or flash
		 memory banks) available on this device for
		 operational code images.
 
                 Devices without local image capability or not
		 supporting this attribute shall return a value of 0."
        ::= { s5AgentGbl 21 }
 
 
s5AgInfoNextBootBank OBJECT-TYPE
        SYNTAX  INTEGER (0..255)
        ACCESS  read-write
        STATUS  mandatory
        DESCRIPTION
                "The source of the image to be loaded upon the
		 next  boot of the device.
 
                 If a value is set larger than s5AgInfoNumBootBanks,
                 a badValue error should be returned.
 
                 Devices without local image capability or not
		 supporting this attribute shall return a value of 0."
        ::= { s5AgentGbl 22 }

 
 
s5AgInfoDstLoadBank OBJECT-TYPE
        SYNTAX  INTEGER (0..255)
        ACCESS  read-write
        STATUS  mandatory
        DESCRIPTION
                "The local storage bank where the next system image
                 image is downloaded to.
 
                 Devices without local image capability or not 
                 supporting this attribute shall return a value of 0."
        ::= { s5AgentGbl 23 }

s5AgInfoFileAction OBJECT-TYPE
    SYNTAX INTEGER {
           other(1),
           dnldConfig(2),
           dnldImg(3),
           upldConfig(4),
           upldImg(5)
           }

    ACCESS read-write
    STATUS mandatory
    DESCRIPTION
        "This object is used to download or upload a config file or
         an image file.

         In read operation, if no action taken since the boot up, it will
         return other(1). Otherwise it will return the latest action such
         as dnldConfig(2), dnldImg(3), upldConfig(4) and upldImg(5).

         In write operation, the values that can be written are:

            dnldConfig(2) ... download a config file to a device. The new
                              config file will not take effect until the
                              next boot cycle of the device.
            dnldImg(3) ...... download an image to a device.
            upldConfig(4) ... upload a config file to a server from
                              a device. The config file contains the current                              MIB object values of the device.
            upldImg(5) ...... upload a image from a device to a server"

    ::= {s5AgentGbl 24}


s5AgInfoFileStatus OBJECT-TYPE
    SYNTAX INTEGER {
            other(1),
            inProgress (2),
            success (3),
            fail (4)
            }
    ACCESS  read-only
    STATUS  mandatory
    DESCRIPTION
        "This object is used to get the status of the latest action as
        shown by s5AgInfoFileAction. The values that can be read are:
 
            other(1) ......... if no action taken since the boot up
            inProgress (2) ... the operation is in progress
            success (3) ...... the operation succeeds.
            fail (4) ......... the operation is failed."

    ::= {s5AgentGbl 25}


-- Agent's Interface Information Table


s5AgMyIfTable OBJECT-TYPE
	SYNTAX	SEQUENCE OF S5AgMyIfEntry
	ACCESS	not-accessible
	STATUS	mandatory
	DESCRIPTION
		"A table that provides additional information
		about the agent's interfaces. The number of
		entries in the table is determined by the
		number of interfaces on the agent."
	::= { s5AgentInfo 2 }


s5AgMyIfEntry OBJECT-TYPE
	SYNTAX	S5AgMyIfEntry
	ACCESS	not-accessible
	STATUS	mandatory
	DESCRIPTION
		"A row in the table of additional information
		about the agent's interfaces. Entries can not
		be created or deleted via SNMP requests."
	INDEX	{ s5AgMyIfIndx }
	::= { s5AgMyIfTable 1 }


S5AgMyIfEntry ::= SEQUENCE {
	s5AgMyIfIndx INTEGER,
	s5AgMyIfNxtBootIpAddr IpAddress,
	s5AgMyIfNxtBootNetMask IpAddress,
	s5AgMyIfCfgFname DisplayString,
	s5AgMyIfLdSvrAddr IpAddress,
	s5AgMyIfImgFname DisplayString,
	s5AgMyIfValidFlag INTEGER,
	s5AgMyIfNxtBootIpxAddr IpxAddress,
        s5AgMyIfBootRouterAddr IpAddress,
        s5AgMyIfMacAddr MacAddress
	}



s5AgMyIfIndx OBJECT-TYPE
	SYNTAX	INTEGER 
	ACCESS	read-only
	STATUS	mandatory
	DESCRIPTION
		"The index of the interface. This has the same
		value as ifIndex for the interface."
	::= { s5AgMyIfEntry 1 }

s5AgMyIfNxtBootIpAddr OBJECT-TYPE
	SYNTAX	IpAddress
	ACCESS	read-write
	STATUS	mandatory
	DESCRIPTION
		"For the next boot, the IP address of the
		the interface. If not used, then the
		value is 0.0.0.0. (NOTE: the current IP
		address for the interface is found in table
		ipAddrTable and in table s5AgOthIfTable.)"
	::= { s5AgMyIfEntry 2 }

s5AgMyIfNxtBootNetMask OBJECT-TYPE
	SYNTAX	IpAddress
	ACCESS	read-write
	STATUS	mandatory
	DESCRIPTION
		"For the next boot, the subnet mask for
		the interface. If not used, then the
		value is 0.0.0.0. (NOTE: the current subnet
		mask for the interface is found in table
		ipAddrTable.)"
	::= { s5AgMyIfEntry 3 }

s5AgMyIfCfgFname OBJECT-TYPE
	SYNTAX	DisplayString (SIZE (0..64))
	ACCESS	read-write
	STATUS	mandatory
	DESCRIPTION
		"Name of the configuration file currently
		associated with the interface. When not
		used, the value is a zero length string."
	::= { s5AgMyIfEntry 4 }

s5AgMyIfLdSvrAddr OBJECT-TYPE
	SYNTAX	IpAddress
	ACCESS	read-write
	STATUS	mandatory
	DESCRIPTION
		"The IP address of the load server for the
		configuration file and/or the image file.
		If not used, then the value is 0.0.0.0"
	::= { s5AgMyIfEntry 5 }

s5AgMyIfImgFname OBJECT-TYPE
	SYNTAX	DisplayString (SIZE (0..128))
	ACCESS	read-write
	STATUS	mandatory
	DESCRIPTION
		"Name of the image file(s) currently associated
		with the interface. Some agents in special
		situations may support a value which contains
		multiple file names instead of a single file
		name. Multiple names are specified as a list
		of file names separated by semicolons (;).
		When the object is not used, the value is a
		zero length string."
	::= { s5AgMyIfEntry 6 }

s5AgMyIfValidFlag OBJECT-TYPE
	SYNTAX	INTEGER {
		valid(1),
		invalid(2)
		}
	ACCESS	read-only
	STATUS	mandatory
	DESCRIPTION
		"Indicates if the configuration and/or image
		file(s) were downloaded from this interface and
		if the file names have not been changed. The
		following values can be read:
		  valid(1).....configuration and/or image file(s)
		                 downloaded from this interface
		                 are currently in use
		  invalid(2)...cfg and/or image files downloaded
		                 from this interface are not
		                 in use (this may also mean that
		                 there are no files downloaded from
		                 this interface)."
	::= { s5AgMyIfEntry 7 }

s5AgMyIfNxtBootIpxAddr OBJECT-TYPE
	SYNTAX	IpxAddress
	ACCESS	read-only
	STATUS	mandatory
	DESCRIPTION
		"For the next boot, the IPX address of the
		the interface.  If the IPX protocol is not used,
		then the value is 00000000:000000000000.

		NOTE: The current IPX address for the 
		      interface is found in table s5AgOthIfTable."
	::= { s5AgMyIfEntry 8 }


s5AgMyIfBootRouterAddr OBJECT-TYPE
        SYNTAX  IpAddress
        ACCESS  read-write
        STATUS  mandatory
        DESCRIPTION
                "The IP address of the boot router for the
                 configuration file and/or the image file.
                 If not used, then the value is 0.0.0.0"
        ::= { s5AgMyIfEntry 9 }

s5AgMyIfMacAddr OBJECT-TYPE
        SYNTAX MacAddress
        ACCESS read-only
        STATUS mandatory
        DESCRIPTION
                "The MAC address of the interface.  The value
                 is 00:00:00:00:00:00 if there is no interface."
        ::= { s5AgMyIfEntry 10}



-- Other Agents' Interface Information Table

s5AgOthIfTable OBJECT-TYPE
	SYNTAX	SEQUENCE OF S5AgOthIfEntry
	ACCESS	not-accessible
	STATUS	mandatory
	DESCRIPTION
		"A table that provides information about
		each interface for each agent in the chassis.
		The number of entries in the table is determined
		by the number of agents in the chassis and their
		configuration."
	::= { s5AgentInfo 3 }

s5AgOthIfEntry OBJECT-TYPE
	SYNTAX	S5AgOthIfEntry
	ACCESS	not-accessible
	STATUS	mandatory
	DESCRIPTION
		"A row in the table of information about interface
		information for all agents in the chassis. Entries
		can not be created or deleted via SNMP requests."
	INDEX	{ s5AgOthIfGrpIndx,
		  s5AgOthIfComIndx,
		  s5AgOthIfIndx }
	::= { s5AgOthIfTable 1 }

S5AgOthIfEntry ::= SEQUENCE {
	s5AgOthIfGrpIndx INTEGER,
	s5AgOthIfComIndx INTEGER,
	s5AgOthIfIndx INTEGER,
	s5AgOthIfIpAddr IpAddress,
	s5AgOthIfIpxAddr IpxAddress
	}

s5AgOthIfGrpIndx OBJECT-TYPE
	SYNTAX	INTEGER (1..32767)
	ACCESS	read-only
	STATUS	mandatory
	DESCRIPTION
		"The index of the group containing the component
		containing the agent."
	::= { s5AgOthIfEntry 1 }

s5AgOthIfComIndx OBJECT-TYPE
	SYNTAX	INTEGER (1..32767)
	ACCESS	read-only
	STATUS	mandatory
	DESCRIPTION
		"The index of the component in the group
		containing the agent."
	::= { s5AgOthIfEntry 2 }

s5AgOthIfIndx OBJECT-TYPE
	SYNTAX	INTEGER 
	ACCESS	read-only
	STATUS	mandatory
	DESCRIPTION
		"The index of the interface. This is the same
		value as ifIndex."
	::= { s5AgOthIfEntry 3 }

s5AgOthIfIpAddr OBJECT-TYPE
	SYNTAX	IpAddress
	ACCESS	read-write
	STATUS	mandatory
	DESCRIPTION
		"The IP address of the interface. If not used,
		then the value is 0.0.0.0."
	::= { s5AgOthIfEntry 4 }

s5AgOthIfIpxAddr OBJECT-TYPE
	SYNTAX	IpxAddress
	ACCESS	read-write
	STATUS	mandatory
	DESCRIPTION
		"The IPX address of the interface.  If the IPX
		protocol is not used,  then the value is
		00000000:000000000000."
	::= { s5AgOthIfEntry 5 }



-- IP Router Aging And Default Router Selection Information

s5AgIpRtrDefaultTimeToLive OBJECT-TYPE
	SYNTAX	TimeIntervalSec (60..3600)
	ACCESS	read-write
	STATUS	mandatory
	DESCRIPTION
		"The lifetime of IP router entries in seconds. 
		The maximum length of time that a IP router 
		is to be considered alive in the absence of 
		further positive advice. The default lifetime 
		is used for routers learned through IP router 
		protocols that do not specify a lifetime (e.g. 
		statically  configured, ICMP redirects)."
	DEFVAL { 540 }  -- 9 minutes
	::= { s5AgentInfo 4 }

s5AgIpDefaultRtrSelectionMode OBJECT-TYPE
	SYNTAX	INTEGER {
		other(1),
		config(2),
		static(3),
		dynamic(4)
		}
	ACCESS	read-write
	STATUS	mandatory
	DESCRIPTION
		"The method used to select a default IP router.
		The following value is read-only:
		  other(1).......not applicable or other case
		The following values are read-write:
		  config(2).....use configured primary default 
				router. If no primary default router 
				is specified, there will be no 
				default IP route.
		  static(3).....A default router will be chose from 
				the routers known to be up and that 
				have been configured.
		  dynamic(4)....ICMP router discovery as per RFC 
				1256 is performed and the router 
				with the highest preference level is 
				chosen as default router."
	DEFVAL { dynamic }
	::= { s5AgentInfo 5 }

s5AgIpRtrDiscoverySolicitMode OBJECT-TYPE
	SYNTAX	INTEGER {
		multicast(1),
		broadcast(2)
		}
	ACCESS	read-write
	STATUS	mandatory
	DESCRIPTION
		"The router discovery solicitation mode to use
		when the default router selection mode is 
		dynamic. This solicitation mode determines 
		the IP address for ICMP router solicitations 
		(see RFC 1256):
		  multicast(1)..router solicitations are sent to 
				the all-routers multicast address 
				(224.0.0.2)
		  broadcast(2)..router solicitations are sent to 
				the limited broadcast address 
				(255.255.255.255)."
	DEFVAL { broadcast}
	::= { s5AgentInfo 6 }



-- Agent's Data Collection Table

s5AgDataCollectTable OBJECT-TYPE
	SYNTAX	SEQUENCE OF S5AgDataCollectEntry 
	ACCESS	not-accessible
	STATUS	mandatory
	DESCRIPTION
		"A table of control information and statistics
		for the data collection (promiscuous data
		capturing) per source of detection."
	::= { s5AgentInfo 7 }

s5AgDataCollectEntry OBJECT-TYPE
	SYNTAX	S5AgDataCollectEntry 
	ACCESS	not-accessible
	STATUS	mandatory
	DESCRIPTION
		"A row in the data collection table.
		Entries can not be created or deleted
		via SNMP."
	INDEX	{ s5AgDataCollectIfIndex }
	::= { s5AgDataCollectTable 1 }

S5AgDataCollectEntry ::= SEQUENCE {
	s5AgDataCollectIfIndex INTEGER,
	s5AgDataCollectSnTimeStamp TimeTicks,
	s5AgDataCollectNetworkAddrStatus INTEGER
	}

s5AgDataCollectIfIndex OBJECT-TYPE
	SYNTAX	INTEGER (0..255)
	ACCESS	read-only
	STATUS	mandatory
	DESCRIPTION
		"An integer value representing the source
		that collects data from the network. A value
		greater than zero is the index of the agent's
		interface on the NMM. This is the same value 
		as ifIndex for the interface. A value of zero
		indicates data collection via best available 
		efforts (other than NMM's interfaces)."
	::= { s5AgDataCollectEntry 1 }

s5AgDataCollectSnTimeStamp OBJECT-TYPE
	SYNTAX	TimeTicks
	ACCESS	read-only
	STATUS	mandatory
	DESCRIPTION
		"The value of sysUpTime at the last time
		a node was added or deleted from the
		Show Node table."
	::= { s5AgDataCollectEntry 2 }


s5AgDataCollectNetworkAddrStatus OBJECT-TYPE
	SYNTAX	INTEGER {
		alwaysOff(1),
		on(2),
		off(3)
		}
	ACCESS	read-write
	STATUS	mandatory
	DESCRIPTION
		"A switch to enable or disable the collecting of 
		network layer addresses for the network address
		mapping table (s5CmNetAddrTable ).
		The following value is read-only:
		  alwaysOff(1)..data source is not capable of
				  collecting or decoding network
				  addresses

		The following values are read-write if the data
		source is capable of collecting network addresses:
		  on(2).........packet decoding is enabled
		  off(3)........packet decoding is disabled
				  or not supported."
	DEFVAL { on } -- if packet collection is possible
	::= { s5AgDataCollectEntry 3 }



-- Authentication Trap VarBinds


s5AgUnAuthIpAddr OBJECT-TYPE
	SYNTAX	IpAddress
	ACCESS	read-only
	STATUS	mandatory
	DESCRIPTION
		"This object contains the IP address of the last
		station that tried to access this agent with an
		invalid community string. This object is used as
		a VarBind in an Authentication Trap PDU. A get
		request will return the last value used, and will
		return the null address 0.0.0.0 if no IP
		authentication traps have been sent."
	::= { s5AgentInfo 8 }

s5AgUnAuthIpxAddr OBJECT-TYPE
	SYNTAX	IpxAddress
	ACCESS	read-only
	STATUS	mandatory
	DESCRIPTION
		"This object contains the IPX address of the last
		station that tried to access this agent with an
		invalid community string. This object is used as
		a VarBind in an Authentication Trap PDU. A get
		request will return the last value used, and will
		return the null address of all zeros if no IPX
		authentication traps have been sent."
	::= { s5AgentInfo 9 }

s5AgUnAuthComm OBJECT-TYPE
	SYNTAX	OCTET STRING (SIZE(0..20))
	ACCESS	read-only
	STATUS	mandatory
	DESCRIPTION
		"This object contains the community string of the
		last unauthenticated attempt to access this agent.
		This object is used as a VarBind in an Authentication
		Trap PDU. A get request will return the last value used,
		and will return the null string if no authentication
		traps have been sent."
	::= { s5AgentInfo 10 }

s5AgTrapFilterTable OBJECT-TYPE
	SYNTAX  SEQUENCE OF S5AgTrapFilterEntry
        ACCESS  not-accessible
        STATUS  mandatory
        DESCRIPTION
                "Agent Trap filter configuration table."
        ::= { s5AgentInfo 11 }
 
s5AgTrapFilterEntry OBJECT-TYPE
        SYNTAX   S5AgTrapFilterEntry
        ACCESS   not-accessible
        STATUS   mandatory
        DESCRIPTION
                "A list of trap filter entries that determine the
                filtering of traps. For example, an instance of the
                s5AgtTrapFilterStatus will be named s5AgTrapFilterStatus.8"
        INDEX   { s5AgTrapFilterIndex }
        ::= { s5AgTrapFilterTable  1 }

S5AgTrapFilterEntry ::= SEQUENCE {
        s5AgTrapFilterIndex          INTEGER,
      	s5AgTrapFilterTrapOID        OBJECT IDENTIFIER,
        s5AgTrapFilterTrapInitiator1 INTEGER,
        s5AgTrapFilterTrapInitiator2 INTEGER,
        s5AgTrapFilterTrapInitiator3 INTEGER,
        s5AgTrapFilterStatus         INTEGER,
        s5AgTrapFilterDelayTime      INTEGER,
        s5AgTrapEntryStatus          INTEGER
        }

s5AgTrapFilterIndex OBJECT-TYPE
        SYNTAX  INTEGER
        ACCESS  read-only
        STATUS  mandatory
        DESCRIPTION
                "An index that uniquely identifies an entry in the
                s5AgTrapFilterTable."
        ::= { s5AgTrapFilterEntry 1 }
 
s5AgTrapFilterTrapOID OBJECT-TYPE
        SYNTAX  OBJECT IDENTIFIER
        ACCESS  read-write
        STATUS  mandatory
        DESCRIPTION
                "The OID of the trap.

                This variable is requried for row creation."    
        ::= { s5AgTrapFilterEntry  2 }

s5AgTrapFilterTrapInitiator1 OBJECT-TYPE
        SYNTAX  INTEGER
        ACCESS  read-write
        STATUS  mandatory
        DESCRIPTION
                "A value that determines the first condition for 
                filtering a trap.This entry is the value of the 
                first varbind for a particular trap in most cases.

                We need to specify every initiator that represents 
                the corresponding trap variable for each trap. 
                If the value of this initiator is 0 (wildcard or 
                don't care), it means that it can represent all 
                possible values for this initiator. The trap-filter 
                design and functional spec. provides a more detailed 
                explanation on this subject."
        ::= { s5AgTrapFilterEntry 3 }

s5AgTrapFilterTrapInitiator2 OBJECT-TYPE
        SYNTAX  INTEGER
        ACCESS  read-write
        STATUS  mandatory
        DESCRIPTION
                "A value that determines the second condition for 
                filtering a trap. This entry is the value of the 
                second varbind for most traps. If the value of 
                this initiator is 0 (wildcard or don't care), 
                it means that it can represent all possible values 
                for this initiator. If a trap has only one varbind, 
	        this entry should be set to 0."
        ::= { s5AgTrapFilterEntry 4 }

s5AgTrapFilterTrapInitiator3 OBJECT-TYPE
        SYNTAX  INTEGER
        ACCESS  read-write
        STATUS  mandatory
        DESCRIPTION
                "A value that determines the third condition for 
                filtering a trap. This entry is the value of the 
                third varbind for most traps. If the value of this 
                initiator is 0(wildcard or don't care), it means 
                that it can represent all possible values for this 
                initiator. If a trap has only one or two varbinds, 
                this entry should be set to 0."
        ::= { s5AgTrapFilterEntry 5 }
 
s5AgTrapFilterStatus OBJECT-TYPE
        SYNTAX  INTEGER {
                enabled(1),
                disabled(2)
                }    
        ACCESS  read-write
        STATUS      mandatory
        DESCRIPTION
                "Indicates whether this trap is enabled or not. 
                enabled(1) indicates that if this type of event 
                occurs, a trap that is generated will be queued 
                for transmit. disabled(2) indicates that if this 
                trap if generated, it will not be queued for 
                transmit and s5AgTrapFilterDelayTime is not valid."
        ::= { s5AgTrapFilterEntry  6 }
 
 
s5AgTrapFilterDelayTime OBJECT-TYPE
        SYNTAX  INTEGER
        ACCESS  read-write
        STATUS  mandatory
        DESCRIPTION
                "The time delay period required to be met, between 
                each consecutive occurences of this event. Traps 
                recieved within this period will be dropped."
        ::= { s5AgTrapFilterEntry  7 }
 
s5AgTrapEntryStatus  OBJECT-TYPE
        SYNTAX  INTEGER {
                valid(1),
                createRequest(2),
                underCreation(3),
                invalid(4)
                }
        ACCESS  read-write
        STATUS  mandatory
        DESCRIPTION
                "A manager is restricted to change the state of an
                entry  base on the following table:
              
                                       create   under
                To:             valid  Request  Creation  invalid
                From:
                valid             OK       NO        OK       OK
                createRequest    N/A      N/A       N/A      N/A
                underCreation     OK       NO        OK       OK
                invalid           NO       NO        NO       OK
                nonExistent       NO       OK        NO       OK
              
                In the table above, it is not applicable to change 
                the state from createRequest to any other states.

                When the status of a table entry is set to the value 
                of invalid(4), the entry will be removed from the table. 
                If an entry has been in the underCreation(3) state for 
                more than 10 minutes, it will be set to invalid(4) and 
	        subsequently removed from the table. 

                This variable is requried for row creation."    
        ::= { s5AgTrapFilterEntry 8 }
 
 
s5AgTrapFilterGlobalStatus    OBJECT-TYPE
        SYNTAX  INTEGER{
                enable_all(1),
                disable_all(2),
                enable_all_and_use_table(3),
                disable_all_and_use_table(4)
                }
        ACCESS  read-write
        STATUS  mandatory
        DESCRIPTION
                "This value is the status of all the traps that 
                supported by this trap-filter system.

                If the value is 1 (enable all) , all traps in the 
                system are enabled. If the value is 2 (disable all), 
                all traps in the system are disabled. If the value 
                is 3 (enable_all_and_use_table) all traps are enabled 
                except for traps that are disabled in the 
                s5AgTrapFilterTable are disabled. If the value is 4 
                (disable_all_and_use_table) all traps are disabled 
                except for traps that are enabled in the 
                s5AgTrapFilterTable are enabled."
        ::= { s5AgentInfo 12 }
 



-- Trap Receiver Table

s5AgTrpRcvrMaxEnt OBJECT-TYPE
	SYNTAX	INTEGER (0..255)
	ACCESS	read-only
	STATUS	mandatory
	DESCRIPTION
		"The maximum number of rows in the trap
		receiver table."
	::= { s5AgentMgmt 1 }

s5AgTrpRcvrCurEnt OBJECT-TYPE
	SYNTAX	INTEGER (0..255)
	ACCESS	read-only
	STATUS	mandatory
	DESCRIPTION
		"The current number of rows in the trap
		receiver table."
	::= { s5AgentMgmt 2 }

s5AgTrpRcvrNext OBJECT-TYPE
	SYNTAX	INTEGER (0..255)
	ACCESS	read-only
	STATUS	mandatory
	DESCRIPTION
		"The index of the next available row to be
		created in the trap receiver table. A value
		of zero means that the table is full and no
		more rows can be added."
	::= { s5AgentMgmt 3 }

s5AgTrpRcvrTable OBJECT-TYPE
	SYNTAX	SEQUENCE OF S5AgTrpRcvrEntry
	ACCESS	not-accessible
	STATUS	mandatory
	DESCRIPTION
		"A table of managers which to send traps."
	::= { s5AgentMgmt 4 }

s5AgTrpRcvrEntry OBJECT-TYPE
	SYNTAX	S5AgTrpRcvrEntry
	ACCESS	not-accessible
	STATUS	mandatory
	DESCRIPTION
		"A row in the trap receiver table.
		The column s5AgTrpRcvrStatus is used to create
		and delete rows in the table. Creation requires
		a SET PDU with objects s5AgTrpRcvrStatus,
		s5AgTrpRcvrAddrType, s5AgTrpRcvrNetAddr,
		and s5AgTrpRcvrComm for the new row."
	INDEX	{ s5AgTrpRcvrIndx }
	::= { s5AgTrpRcvrTable 1 }

S5AgTrpRcvrEntry ::= SEQUENCE {
	s5AgTrpRcvrIndx INTEGER,
	s5AgTrpRcvrStatus INTEGER,
	s5AgTrpRcvrAddrType INTEGER,
	s5AgTrpRcvrNetAddr OCTET STRING,
	s5AgTrpRcvrComm OCTET STRING,
	s5AgTrpRcvrAgeTime TimeIntervalSec
	}

s5AgTrpRcvrIndx OBJECT-TYPE
	SYNTAX	INTEGER (1..255)
	ACCESS	read-only
	STATUS	mandatory
	DESCRIPTION
		"The index of the row in the table."
	::= { s5AgTrpRcvrEntry 1 }

s5AgTrpRcvrStatus OBJECT-TYPE
	SYNTAX	INTEGER {
		other(1),
		valid(2),
		ignore(3),
		delete(4),
		create(5)
		}
	ACCESS	read-write
	STATUS	mandatory
	DESCRIPTION
		"This object is used to create and
		delete rows in the table and control
		if they are used. The values
		that can be written are:
		  valid(2)....makes an existing row
		                valid - can only be
		                written to change the
		                value from ignore(3)
		  ignore(3)...don't use this entry to
		                send traps to at this time
		  delete(4)...deletes the row
		  create(5)...creates a new row - only
		                value that can be used to
		                create a row in the table

		If the row exists, then a SET with
		value of create(5) returns error
		'badValue'. Deleted rows go away
		immediately. The following values
		can be returned on reads:
		  other(1)....some other case
		  valid(2)....the row exists and is valid
		  ignore(3)...don't use this entry to
		                send traps to at this time"
	::= { s5AgTrpRcvrEntry 2 }

s5AgTrpRcvrAddrType OBJECT-TYPE
	SYNTAX	INTEGER {
		ip(1),
		ipx(2)
		}
	ACCESS	read-write
	STATUS	mandatory
	DESCRIPTION
		"The type of address that is stored in
		the object s5AgTrpRcvrNetAddr. The
		value is:
		  ip(1)....IP address
		  ipx(2)...IPX address.

		Note:   When changing the value of this object
		        with an SNMP SET request, the SET PDU
 		        must also specify a value for the
		        s5AgTrpRcvrNetAddr object."
	::= { s5AgTrpRcvrEntry 3 }

s5AgTrpRcvrNetAddr OBJECT-TYPE
	SYNTAX	OCTET STRING
	ACCESS	read-write
	STATUS	mandatory
	DESCRIPTION
		"The network address (in network order) for
		SNMP manager that is to receive the trap."
	::= { s5AgTrpRcvrEntry 4 }

s5AgTrpRcvrComm OBJECT-TYPE
	SYNTAX	OCTET STRING (SIZE(0..20))
	ACCESS	read-write
	STATUS	mandatory
	DESCRIPTION
		"Community string to use."
	::= { s5AgTrpRcvrEntry 5 }

s5AgTrpRcvrAgeTime OBJECT-TYPE
	SYNTAX	TimeIntervalSec
	ACCESS	read-write
	STATUS	mandatory
	DESCRIPTION
		"The time interval used to age entries out
		of the trap receiver table. The default
		value if not specified will be 0, or infinite,
		never to be aged out."
	DEFVAL { 0 }
	::= { s5AgTrpRcvrEntry 6 }


-- Last Remote Login Management 

s5AgRemoteLoginMgmt OBJECT IDENTIFIER ::= { s5AgentMgmt 5 }

s5AgRemoteLoginIp OBJECT-TYPE
	SYNTAX	IpAddress
	ACCESS	read-only
	STATUS	mandatory
	DESCRIPTION
		"This value indicates the last IP address remote login to this system.  "
	::= { s5AgRemoteLoginMgmt 1 }

s5AgRemoteLoginStatus OBJECT-TYPE
	SYNTAX	INTEGER {
               statusUnknown (1),
               successful (2),
               passwordFail (3),
               loginTimeout (4),
               loginInactivityTimeout(5),
               telnetSessionExisted (6),
               nonAllowedIPaddr (7),
               localConsoleBusy (8),
               excessiveLoginFail (9),
               accessPermissionOff (10),
	       loginLogout (11)
            } 
	ACCESS	read-only
	STATUS	mandatory
	DESCRIPTION
		"This value indicates the status of remote login to this system.  "
	::= { s5AgRemoteLoginMgmt 2 }

END
-- SECTION 1: Top Level Definitions

S5-COMMON-STATS-MIB DEFINITIONS ::= BEGIN


-- 5000 Common Statistics MIB Release 1.1.2
-- Revision 04/18/94

-- Copyright 1993-94 SynOptics Communications, Inc.
-- All rights reserved.
-- This SynOptics SNMP Management Information Base Specification
-- (Specification) embodies SynOptics' confidential and
-- proprietary intellectual property. SynOptics retains all
-- title and ownership in the Specification, including any
-- revisions.

-- This Specification is supplied "AS IS," and SynOptics makes
-- no warranty, either express or implied, as to the use,
-- operation, condition, or performance of the Specification.


-- Imports

IMPORTS
	OBJECT-TYPE
		FROM RFC-1212
	TimeTicks
		FROM RFC1155-SMI
	s5Com
		FROM S5-ROOT-MIB
	MacAddress
		FROM S5-TCS-MIB;


-- Groups

-- Statistics
s5CmStat	OBJECT IDENTIFIER ::= { s5Com 1 }


-- SECTION 2: MIB Objects


-- Show Nodes Table

s5CmSNodeTable OBJECT-TYPE
	SYNTAX	SEQUENCE OF S5CmSNodeEntry
	ACCESS	not-accessible
	STATUS	mandatory
	DESCRIPTION
		"A Table of MAC addresses of active nodes, which are
		detected to be connected to the concentrator.
		These nodes may be directly connected to the
		concentrator or may be indirectly connected via
		an interconnect port, bridge or switch.  The definition
		of active node is provided by s5CmSNodeStatus.

		The object s5CmSNodeIfIndex specifies the
		source that is used to detect MAC addresses.  When the
		source is not an interface, the agent uses best effort to
		detect entries.  These entries may, but are not required
		to be, MACs from media types other than the interfaces
		for the agent.

		This table is indexed by source of the detection,
		board, port, and MAC address of the node.  This 
		table is indexed differently from the FindNodes
		table which uses only the source of the detection
		and MAC address of the node.  Note: a MAC
		address could appear multiple times in this
		table (on different board and port)."
	::= { s5CmStat 1 }

s5CmSNodeEntry OBJECT-TYPE
	SYNTAX	S5CmSNodeEntry
	ACCESS	not-accessible
	STATUS	mandatory
	DESCRIPTION
		"A row in the Show Node table.
		Entries can not be created or deleted via
		SNMP."
	INDEX	{ s5CmSNodeIfIndx,
		  s5CmSNodeBrdIndx,
		  s5CmSNodePortIndx,
		  s5CmSNodeMacAddr }
	::= { s5CmSNodeTable 1 }

S5CmSNodeEntry ::= SEQUENCE {
	s5CmSNodeIfIndx INTEGER,
	s5CmSNodeBrdIndx INTEGER,
	s5CmSNodePortIndx INTEGER,
	s5CmSNodeMacAddr MacAddress,
	s5CmSNodeStatus INTEGER
	}

s5CmSNodeIfIndx OBJECT-TYPE
	SYNTAX	INTEGER(0..65535)
	ACCESS	read-only
	STATUS	mandatory
	DESCRIPTION
		"An integer value representing the source
		that detected the active node.  A value greater
		than zero is the index of the agent's interface
		in the NMM.  This is the same value as ifIndex 
		for the interface.  A value of zero indicates
		that the agent detected the node information via
		best available efforts.  The nodes may be, but are
		note required to be, from media types other than
		the interfaces for the agent."
	::= { s5CmSNodeEntry 1 }

s5CmSNodeBrdIndx OBJECT-TYPE
	SYNTAX	INTEGER (1..255)
	ACCESS	read-only
	STATUS	mandatory
	DESCRIPTION
		"The index of the board. This corresponds to
		the index of the slot containing the board."
	::= { s5CmSNodeEntry 2 }

s5CmSNodePortIndx OBJECT-TYPE
	SYNTAX	INTEGER (1..255)
	ACCESS	read-only
	STATUS	mandatory
	DESCRIPTION
		"The index of the port on the board. Its
		value ranges between 1 and index of the last
		manageable port on the board."
	::= { s5CmSNodeEntry 3 }

s5CmSNodeMacAddr OBJECT-TYPE
	SYNTAX	MacAddress
	ACCESS	read-only
	STATUS	mandatory
	DESCRIPTION
		"The MAC address of the station."
	::= { s5CmSNodeEntry 4 }

s5CmSNodeStatus OBJECT-TYPE
	SYNTAX	INTEGER {
		other(1),
		active(2),
		inactive(3)
		}
	ACCESS	read-only
	STATUS	mandatory
	DESCRIPTION
		"The status of the MAC address for a station.
		The meaning varies depending on the media type
		of the NMM reporting the status. The values are:
		  other(1)......unknown or other
		  active(2).....the station is actively sending
		                  and receiving, or
		                  participating
		                  in the ring poll
		  inactive(3)...the station is idle

		For Ethernet, active(2) means that the station
		has sent a frame in the last N seconds and
		inactive(3) means the station has not sent a
		frame in the last N seconds. N is specified by
		the s5EnNodeInactInterval object, which is
		defined in the 5000 Ethernet MIB.  The status of
		other(3) is reported when the current status of
		the station is unknown.

		For Token Ring and FDDI, the status of a station
		will always be reported as active(2) since it is
		based on being in the ring poll.  When no longer
		in the ring poll, a station is removed from the
		table."
	::= { s5CmSNodeEntry 5 }


-- Find Nodes Table

s5CmFNodeTable OBJECT-TYPE
	SYNTAX	SEQUENCE OF S5CmFNodeEntry
	ACCESS	not-accessible
	STATUS	mandatory
	DESCRIPTION
		"A Table of MAC addresses of active nodes, which are
		detected to be connected to the concentrator.
		These nodes may be directly connected to the
		concentrator or may be indirectly connected via
		an interconnect port, bridge or switch.  The definition
		of active node is provided by s5CmSNodeStatus.

		The object s5CmSNodeIfIndex specifies the
		source that is used to detect MAC addresses.  When the
		source is not an interface, the agent uses best effort to
		detect entries.  These entries may, but are not required
		to be, MACs from media types other than the interfaces
		for the agent.

		This table is indexed by source of the detection
		and MAC address of the node.  This 
		table is indexed differently from the ShowNodes
		table which uses the source of the detection,
		board, port, and MAC address of the node.

		Note: The same MAC may be detected at several
		locations.  The entry in this table is the last 
		detected location.  In addition, more than one
		MAC address could appear on the same board
		and port."
	::= { s5CmStat 2 }

s5CmFNodeEntry OBJECT-TYPE
	SYNTAX	S5CmFNodeEntry
	ACCESS	not-accessible
	STATUS	mandatory
	DESCRIPTION
		"A row in the Find Node table.
		Entries can not be created or deleted via
		SNMP."
	INDEX	{ s5CmFNodeIfIndx,
		  s5CmFNodeMacAddr }
	::= { s5CmFNodeTable 1 }

S5CmFNodeEntry ::= SEQUENCE {
	s5CmFNodeIfIndx INTEGER,
	s5CmFNodeMacAddr MacAddress,
	s5CmFNodeBrdIndx INTEGER,
	s5CmFNodePortIndx INTEGER
	}

s5CmFNodeIfIndx OBJECT-TYPE
	SYNTAX	INTEGER(0..65535)
	ACCESS	read-only
	STATUS	mandatory
	DESCRIPTION
		"An integer value representing the source
		that detected the active node.  A value greater
		than zero is the index of the agent's interface
		in the NMM.  This is the same value as ifIndex 
		for the interface.  A value of zero indicates
		that the agent detected the node information via
		best available efforts.  The nodes may be, but are
		note required to be, from media types other than
		the interfaces for the agent."
	::= { s5CmFNodeEntry 1 }

s5CmFNodeMacAddr OBJECT-TYPE
	SYNTAX	MacAddress
	ACCESS	read-only
	STATUS	mandatory
	DESCRIPTION
		"MAC address of the station."
	::= { s5CmFNodeEntry 2 }

s5CmFNodeBrdIndx OBJECT-TYPE
	SYNTAX	INTEGER (0..255)
	ACCESS	read-only
	STATUS	mandatory
	DESCRIPTION
		"The index of the board.  This corresponds to
		the index of the slot containing the board.  The
		value of zero has the special meaning that the
		true board index value is currently unknown.
		Note that the syntax of this object is not
		identical to s5CmSNodeBrdIndx."
	::= { s5CmFNodeEntry 3 }

s5CmFNodePortIndx OBJECT-TYPE
	SYNTAX	INTEGER (0..255)
	ACCESS	read-only
	STATUS	mandatory
	DESCRIPTION
		"The index of the port on the board.  This
		corresponds to the index of one of the
		manageable ports on the board.  The value of
		zero has the special meaning that the true port
		index value is currently unknown.
		Note that the syntax of this object is not
		identical to s5CmSNodePortIndx."
	::= { s5CmFNodeEntry 4 }


-- Per-port Network to MAC Address Mapping Table

s5CmNetAddrTable OBJECT-TYPE
	SYNTAX	SEQUENCE OF S5CmNetAddrEntry
	ACCESS	not-accessible
	STATUS	mandatory
	DESCRIPTION
		"A table of network layer addresses associated
		with MAC addresses of active nodes, which are
		detected to be connected to the concentrator.

		This table is indexed by the interface it was
		detected, the board and port the node is connected,
		the MAC address of the node and an integer index 
		(enumerating multiple network addresses).

		Note:
		Only a small implementation determined number of 
		network addresses are stored. The oldest one is 
		discarded, so that the most recent one may be
		retained.  When packet decoding is switched off
		entries in the network address mapping table may
		remain present for some time, but no new addresses
		are added.  An network address could appear multiple
		times in this table (on different board and port)
		and can appear under different s5CmNetAddrNetIndx
		over time."
	::= { s5CmStat 3 }

s5CmNetAddrEntry OBJECT-TYPE
	SYNTAX	S5CmNetAddrEntry
	ACCESS	not-accessible
	STATUS	mandatory
	DESCRIPTION
		"A row in the network address mapping table.
		Entries can not be created or deleted
		via SNMP."
	INDEX	{ s5CmNetAddrIfIndex, 
		  s5CmNetAddrBrdIndx, 
		  s5CmNetAddrPortIndx, 
		  s5CmNetAddrMacAddr, 
		  s5CmNetAddrNetIndx }
	::= { s5CmNetAddrTable 1 }

S5CmNetAddrEntry ::= SEQUENCE {
	s5CmNetAddrIfIndex INTEGER,
	s5CmNetAddrBrdIndx INTEGER,
	s5CmNetAddrPortIndx INTEGER,
	s5CmNetAddrMacAddr MacAddress,
	s5CmNetAddrNetIndx INTEGER,
	s5CmNetAddrType INTEGER,
	s5CmNetAddrAddr OCTET STRING,
	s5CmNetAddrLastSeen TimeTicks
	}

s5CmNetAddrIfIndex OBJECT-TYPE
	SYNTAX	INTEGER (1..65535)
	ACCESS	read-only
	STATUS	mandatory
	DESCRIPTION
		"The index of the interface on the NMM on 
		which the address was detected. This is the 
		same as the ifIndex."
	::= { s5CmNetAddrEntry 1 }


s5CmNetAddrBrdIndx OBJECT-TYPE
	SYNTAX	INTEGER (1..255)
	ACCESS	read-only
	STATUS	mandatory
	DESCRIPTION
		"The index of the board. This corresponds to
		the index of the slot containing the board."
	::= { s5CmNetAddrEntry 2 }


s5CmNetAddrPortIndx OBJECT-TYPE
	SYNTAX	INTEGER (1..255)
	ACCESS	read-only
	STATUS	mandatory
	DESCRIPTION
		"The index of the port on the board."
	::= { s5CmNetAddrEntry 3 }

s5CmNetAddrMacAddr OBJECT-TYPE
	SYNTAX	MacAddress
	ACCESS	read-only
	STATUS	mandatory
	DESCRIPTION
		"The MAC address of the station."
	::= { s5CmNetAddrEntry 4 }

s5CmNetAddrNetIndx OBJECT-TYPE
	SYNTAX	INTEGER (1..255)
	ACCESS	read-only
	STATUS	mandatory
	DESCRIPTION
		"The sequence number of the network address."
	::= { s5CmNetAddrEntry 5 }

s5CmNetAddrType OBJECT-TYPE
	SYNTAX	INTEGER {
		ip(1)
		}
	ACCESS	read-only
	STATUS	mandatory
	DESCRIPTION
		"The type of network layer address:
		  ip(1).....an IP address as defined in RFC 791."
	::= { s5CmNetAddrEntry 6 }

s5CmNetAddrAddr OBJECT-TYPE
	SYNTAX	OCTET STRING
	ACCESS	read-only
	STATUS	mandatory
	DESCRIPTION
		"The network layer address of the station represented
		in network byte-order"
	::= { s5CmNetAddrEntry 7 }

s5CmNetAddrLastSeen OBJECT-TYPE
	SYNTAX	TimeTicks
	ACCESS	read-only
	STATUS	mandatory
	DESCRIPTION
		"The value of sysUpTime at the time this network
		address was last seen on this interface/board/port/MAC."
	::= { s5CmNetAddrEntry 8 }


END

-- SECTION 1: Top Level Definitions

S5-CHASSIS-TRAP-MIB DEFINITIONS ::= BEGIN


-- 5000 Chassis Trap MIB Release 1.1.0
-- Revision 11/15/93

-- Copyright 1993 SynOptics Communications, Inc.
-- All rights reserved.
-- This SynOptics SNMP Management Information Base Specification
-- (Specification) embodies SynOptics' confidential and
-- proprietary intellectual property. SynOptics retains all
-- title and ownership in the Specification, including any
-- revisions.

-- This Specification is supplied "AS IS," and SynOptics makes
-- no warranty, either express or implied, as to the use,
-- operation, condition, or performance of the Specification.


-- Imports

IMPORTS
	TRAP-TYPE	FROM RFC-1215
	s5ChaTrap	FROM S5-ROOT-MIB
	s5ChasComType, s5ChasComOperState
			FROM S5-CHASSIS-MIB;



-- SECTION 2: SynOptics 5000 Chassis Trap Definitions

-- All chassis traps are numbered uniquely with ENTERPRISE
-- field value of s5ChaTrap.

s5CtrHotSwap TRAP-TYPE
	ENTERPRISE	s5ChaTrap
	VARIABLES	{ s5ChasComType,
			  s5ChasComOperState }
--	STATUS		mandatory
	DESCRIPTION
		"A component or sub-component was inserted or
		deinserted in the chassis. This trap is sent only
		once when the condition is first detected. The
		following values are returned:
		  s5ChasComType........the type of the component
		    (or sub-component) that was inserted or
		    deinserted, with the instance identifying
		    the group, component, and sub-component.
		  s5ChasComOperState...the operational status of
		    the component or sub-component, with the
		    instance identifying the group, component,
		    and sub-component. The value is removed(3)
		    when the item is removed."
	::= 1	-- 0x01


s5CtrProblem TRAP-TYPE
	ENTERPRISE	s5ChaTrap
	VARIABLES	{ s5ChasComType,
			  s5ChasComOperState }
--	STATUS		mandatory
	DESCRIPTION
		"A component or sub-component has a problem
		condition, either warning, nonfatal, or fatal.
		This trap is sent only once when the condition
		is first detected. The following values are
		returned:
		  s5ChasComType........the type of the component
		    (or sub-component) that has the problem
		    condition, with the instance identifying
		    the group, component, and sub-component.
		  s5ChasComOperState...the operational status of
		    the component or sub-component, with the
		    instance identifying the group, component,
		    and sub-component."
	::= 2	-- 0x02


END
-- SECTION 1: Top Level Definitions

S5-TOK-TOPOLOGY-MIB DEFINITIONS ::= BEGIN


-- 5000 Token Ring Topology MIB Release 1.1.5
-- Revision 10/14/98

-- Copyright 1995 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	IpAddress, TimeTicks
		FROM RFC1155-SMI
	OBJECT-TYPE
		FROM RFC-1212
	SnpxChassisType, SnpxBackplaneType
		FROM SYNOPTICS-ROOT-MIB
	s5TrTop
		FROM S5-ROOT-MIB
	MacAddress
		FROM S5-TCS-MIB;



-- SECTION 2: MIB Objects


-- Interface Topology table


s5TrTopIfTable OBJECT-TYPE
	SYNTAX	SEQUENCE OF S5TrTopIfEntry
	ACCESS	not-accessible
	STATUS	mandatory
	DESCRIPTION
		"A table with topology status and control
		for each token ring interface on the NMM. The
		number of entries is determined by the number
		of token ring interfaces on the NMM."
	::= { s5TrTop 1 }

s5TrTopIfEntry OBJECT-TYPE
	SYNTAX	S5TrTopIfEntry
	ACCESS	not-accessible
	STATUS	mandatory
	DESCRIPTION
		"A row in the table of topology status and
		control for each token ring interface on the
		NMM. Entries in the table can not be created
		or deleted via SNMP."
	INDEX	{ s5TrTopIfIpAddr }
	::= { s5TrTopIfTable 1 }


S5TrTopIfEntry ::= SEQUENCE {
	s5TrTopIfIpAddr IpAddress,
	s5TrTopIfNum INTEGER,
	s5TrTopIfStatus INTEGER,
	s5TrTopIfNmmLstChg TimeTicks,
	s5TrTopIfBdgLstChg TimeTicks,
	s5TrTopIfRingNmmLstChg TimeTicks,
	s5TrTopIfNmmMaxNum INTEGER,
	s5TrTopIfNmmCurNum INTEGER,
	s5TrTopIfBdgMaxNum INTEGER,
	s5TrTopIfBdgCurNum INTEGER,
	s5TrTopIfRingNmmMaxNum INTEGER,
	s5TrTopIfRingNmmCurNum INTEGER,
	s5TrTopIfTopSpeed INTEGER
	}


s5TrTopIfIpAddr OBJECT-TYPE
	SYNTAX	IpAddress
	ACCESS	read-only
	STATUS	mandatory
	DESCRIPTION
		"The IP address of the interface."
	::= { s5TrTopIfEntry 1 }

s5TrTopIfNum OBJECT-TYPE
	SYNTAX	INTEGER
	ACCESS	read-only
	STATUS	mandatory
	DESCRIPTION
		"The value of ifIndex for the interface."
	::= { s5TrTopIfEntry 2 }

s5TrTopIfStatus OBJECT-TYPE
	SYNTAX	INTEGER {
		topOn(1),
		topOff(2)
		}
	ACCESS	read-write
	STATUS	mandatory
	DESCRIPTION
		"Indicates if the interface is participating
		in topology. The values are:
		  topOn(1)....topology is on
		  topOff(2)...topology is off
		When the value is topOff(2) the status
		of entries associated with the interface
		is undefined. However, the agent should
		make its best attempt when the value is
		changed to topOff(2) to remove all
		existing instances of topology MIB objects
		for the interface. The agent must save
		the setting of this object in nonvolatile
		memory (i.e., save across reboots)."
	::= { s5TrTopIfEntry 3 }

s5TrTopIfNmmLstChg OBJECT-TYPE
	SYNTAX	TimeTicks
	ACCESS	read-only
	STATUS	mandatory
	DESCRIPTION
		"The value of sysUpTime when the last
		addition or deletion of an NMM topology
		table entry associated with the interface
		was done. If none have been done since
		cold/warm start of the agent, then the
		value is zero."
	::= { s5TrTopIfEntry 4 }

s5TrTopIfBdgLstChg OBJECT-TYPE
	SYNTAX	TimeTicks
	ACCESS	read-only
	STATUS	mandatory
	DESCRIPTION
		"The value of sysUpTime when the last
		addition or deletion of a bridge
		topology table entry associated with the
		interface was done. If none have been
		done since cold/warm start of the
		agent, then the value is zero."
	::= { s5TrTopIfEntry 5 }

s5TrTopIfRingNmmLstChg OBJECT-TYPE
	SYNTAX	TimeTicks
	ACCESS	read-only
	STATUS	mandatory
	DESCRIPTION
		"The value of sysUpTime when the last
		addition or deletion of a Ring NMM
		topology table entry associated with
		the interface was done. If none have
		been done since cold/warm start
		of the agent, then the value is zero."
	::= { s5TrTopIfEntry 6 }

s5TrTopIfNmmMaxNum OBJECT-TYPE
	SYNTAX	INTEGER (0..65535)
	ACCESS	read-only
	STATUS	mandatory
	DESCRIPTION
		"The maximum number of entries for the
		interface in the NMM topology table."
	::= { s5TrTopIfEntry 7 }

s5TrTopIfNmmCurNum OBJECT-TYPE
	SYNTAX	INTEGER (0..65535)
	ACCESS	read-only
	STATUS	mandatory
	DESCRIPTION
		"The current number of entries for the
		interface in the NMM topology table."
	::= { s5TrTopIfEntry 8 }

s5TrTopIfBdgMaxNum OBJECT-TYPE
	SYNTAX	INTEGER (0..65535)
	ACCESS	read-only
	STATUS	mandatory
	DESCRIPTION
		"The maximum number of entries for the
		interface in the bridge topology table."
	::= { s5TrTopIfEntry 9 }

s5TrTopIfBdgCurNum OBJECT-TYPE
	SYNTAX	INTEGER (0..65535)
	ACCESS	read-only
	STATUS	mandatory
	DESCRIPTION
		"The current number of entries for the
		interface in the bridge topology table."
	::= { s5TrTopIfEntry 10 }

s5TrTopIfRingNmmMaxNum OBJECT-TYPE
	SYNTAX	INTEGER (0..255)
	ACCESS	read-only
	STATUS	mandatory
	DESCRIPTION
		"The maximum number of entries for the
		interface in the Ring NMM topology table."
	::= { s5TrTopIfEntry 11 }

s5TrTopIfRingNmmCurNum OBJECT-TYPE
	SYNTAX	INTEGER (0..255)
	ACCESS	read-only
	STATUS	mandatory
	DESCRIPTION
		"The current number of entries for the
		interface in the Ring NMM topology table."
	::= { s5TrTopIfEntry 12 }

s5TrTopIfTopSpeed OBJECT-TYPE
	SYNTAX	INTEGER {
		other(1),
		topFast(2),
		topSlow(3)
		}
	ACCESS	read-write
	STATUS	mandatory
	DESCRIPTION
		"The Token Ring topology message (SONMP frame)
		transmit speed. The values that are read/write are:
		  topFast(2)...short interval between transmitting
		  topSlow(3)...long interval between transmitting

		The value that is readonly is:
		  other(1)...speed unknown, or other value

		In fast mode, the SONMP frame transmit interval
		is 10 seconds for all SONMP frames except
		for ring master which is 5 seconds.

		In slow mode, the interval is 15 seconds for ring
		master SONMP frames, 50 seconds for concentrator
		profile SONMP frames, 60 seconds for master NMM
		announcement SONMP frames, and 70 seconds for
		adjacent SONMP frames."
	::= { s5TrTopIfEntry 13 }



-- Network Management Module (NMM) Topology Table


s5TrTopNmmTable OBJECT-TYPE
	SYNTAX	SEQUENCE OF S5TrTopNmmEntry
	ACCESS	not-accessible
	STATUS	mandatory
	DESCRIPTION
		"A table of topology information for each
		Network Management Module (NMM) with a Token
		Ring interface on the same 'flat network'
		as the reporting NMM. The number of entries
		is determined by the number of detected
		(and active) NMMs. Entries in the table are
		created by reception of a topology message
		with information about a 'new' NMM. An entry
		is removed from the table when an NMM is
		not present in the topology message from
		a ring, or when no topology messages are
		received from a ring in the required time
		interval."
	::= { s5TrTop 2 }

s5TrTopNmmEntry OBJECT-TYPE
	SYNTAX	S5TrTopNmmEntry
	ACCESS	not-accessible
	STATUS	mandatory
	DESCRIPTION
		"A row in the table of topology information
		about Network Management Modules (NMMs) with
		a Token Ring interface on the same 'flat
		network' as the reporting NMM. Entries in the
		table can not be created or deleted via SNMP."
	INDEX	{ s5TrTopNmmIfIpAddr,
		  s5TrTopNmmIpAddr }
	::= { s5TrTopNmmTable 1 }

S5TrTopNmmEntry ::= SEQUENCE {
	s5TrTopNmmIfIpAddr IpAddress,
	s5TrTopNmmIpAddr IpAddress,
	s5TrTopNmmRingNum INTEGER,
	s5TrTopNmmRingMaster INTEGER,
	s5TrTopNmmRingSpeed INTEGER,
	s5TrTopNmmBridgeGroupIdentifier INTEGER,
	s5TrTopNmmSlotNum INTEGER,
	s5TrTopNmmPortNum INTEGER
	}

s5TrTopNmmIfIpAddr OBJECT-TYPE
	SYNTAX	IpAddress
	ACCESS	read-only
	STATUS	mandatory
	DESCRIPTION
		"The IP address of the interface on which
		the topology message was received."
	::= { s5TrTopNmmEntry 1 }

s5TrTopNmmIpAddr OBJECT-TYPE
	SYNTAX	IpAddress
	ACCESS	read-only
	STATUS	mandatory
	DESCRIPTION
		"The IP address of an NMM contained in
		a topology message."
	::= { s5TrTopNmmEntry 2 }

s5TrTopNmmRingNum OBJECT-TYPE
	SYNTAX	INTEGER (0..4095)
	ACCESS	read-only
	STATUS	mandatory
	DESCRIPTION
		"The ring number on which an NMM from a
		topology message is located."
	::= { s5TrTopNmmEntry 3 }

s5TrTopNmmRingMaster OBJECT-TYPE
	SYNTAX	INTEGER {
		normal(1),
		master(2)
		}
	ACCESS	read-only
	STATUS	mandatory
	DESCRIPTION
		"The classification of an NMM from
		a topology message. The values are:
		  normal(1)...not a master NMM
		  master(2)...a master NMM"
	::= { s5TrTopNmmEntry 4 }

s5TrTopNmmRingSpeed OBJECT-TYPE
	SYNTAX	INTEGER (0..255)
	ACCESS	read-only
	STATUS	mandatory
	DESCRIPTION
		"The speed of the ring (in units of Mbits)
		on which an NMM from a topology message is
		located. The expected values are:
		   4....4 Mbps
		  16...16 Mbps"
	::= { s5TrTopNmmEntry 5 }

s5TrTopNmmBridgeGroupIdentifier OBJECT-TYPE
        SYNTAX  INTEGER
        ACCESS  read-only
        STATUS  mandatory
        DESCRIPTION
                "The forwarding domain identification -- 
                VLAN ID, if applicable, of the port on 
                which the SONMP message for this entry 
                was heard. The value shall be zero if 
                the entry is local, or if the port number 
                cannot be resolved."
       ::= {s5TrTopNmmEntry 6}
 
s5TrTopNmmSlotNum OBJECT-TYPE
        SYNTAX  INTEGER
        ACCESS  read-only
        STATUS  mandatory
        DESCRIPTION
                "The slot number of the port on which the SONMP
                 message for this entry was heard.  The value shall
                 be zero if the port number cannot be resolved."
        ::= {s5TrTopNmmEntry 7}
 
s5TrTopNmmPortNum OBJECT-TYPE
        SYNTAX  INTEGER
        ACCESS  read-only
        STATUS  mandatory
        DESCRIPTION
                "The port number of the port on which the SONMP
                 message for this entry was heard.  The value shall
                 be zero if the port number cannot be resolved."
       ::= {s5TrTopNmmEntry 8}
 

-- Bridge Topology Table


s5TrTopBdgTable OBJECT-TYPE
	SYNTAX	SEQUENCE OF S5TrTopBdgEntry
	ACCESS	not-accessible
	STATUS	mandatory
	DESCRIPTION
		"A table that lists each known bridge 
		with a Token Ring interface on the same
		'flat net' as the reporting NMM. The
		number of entries is determined by
		the number of detected (and active)
		bridges. Entries are added by reception of
		a topology message from a bridge or reception
		of a topology message from an master NMM that
		was forwarded by a source routing bridge.
		An entry is removed from the table when
		no topology messaged are received from
		bridge in the required time interval."
	::= { s5TrTop 3 }

s5TrTopBdgEntry OBJECT-TYPE
	SYNTAX	S5TrTopBdgEntry
	ACCESS	not-accessible
	STATUS	mandatory
	DESCRIPTION
		"A row in the table of known bridges
		with a Token Ring interface on the same
		'flat net' as the reporting NMM. Entries
		in the table can not be created or deleted
		via SNMP."
	INDEX	{ s5TrTopBdgIfIpAddr,
		  s5TrTopBdgIndx }
	::= {s5TrTopBdgTable 1 }

S5TrTopBdgEntry ::= SEQUENCE {
	s5TrTopBdgIfIpAddr IpAddress,
	s5TrTopBdgIndx INTEGER,
	s5TrTopBdgNum INTEGER,
	s5TrTopBdgOwnRingNum INTEGER,
	s5TrTopBdgAdjRingNum INTEGER,
	s5TrTopBdgAdjMasterNmmIpAddr IpAddress,
	s5TrTopBdgMacAddr MacAddress,
	s5TrTopBdgIpAddr IpAddress,
	s5TrTopBdgType INTEGER,
	s5TrTopBdgSlotNum INTEGER,
	s5TrTopBdgPortNum INTEGER,
	s5TrTopBdgNumPort INTEGER,
	s5TrTopBdgHelloPortNum INTEGER,
	s5TrTopBdgHelloPortStatus INTEGER,
	s5TrTopBdgMonPortStatus INTEGER,
	s5TrTopBdgHelloType INTEGER
	}

s5TrTopBdgIfIpAddr OBJECT-TYPE
	SYNTAX	IpAddress
	ACCESS	read-only
	STATUS	mandatory
	DESCRIPTION
		"The IP address of the interface on which
		the topology message was received."
	::= { s5TrTopBdgEntry 1 }

s5TrTopBdgIndx OBJECT-TYPE
	SYNTAX	INTEGER (1..65535)
	ACCESS	read-only
	STATUS	mandatory
	DESCRIPTION
		"The index of the entry in the table
		for the interface."
	::= { s5TrTopBdgEntry 2 }

s5TrTopBdgNum OBJECT-TYPE
	SYNTAX	INTEGER (0..15)
	ACCESS	read-only
	STATUS	mandatory
	DESCRIPTION
		"The IEEE 802.5 'bridge number' for
		the bridge."
	::= { s5TrTopBdgEntry 3 }

s5TrTopBdgOwnRingNum OBJECT-TYPE
	SYNTAX	INTEGER (0..4095)
	ACCESS	read-only
	STATUS	mandatory
	DESCRIPTION
		"The ring number for the reporting NMM.
		NOTE: this will be the same value for all
		table entries for each interface."
	::= { s5TrTopBdgEntry 4 }

s5TrTopBdgAdjRingNum OBJECT-TYPE
	SYNTAX	INTEGER (0..4095)
	ACCESS	read-only
	STATUS	mandatory
	DESCRIPTION
		"The ring number of the adjacent ring
		that is joined by the bridge. The value
		is zero if this entry in the table was
		created due to the receipt of a topology
		message from another NMM on a different
		ring and the bridge connecting the rings
		was a transparent only bridge and it does
		not generate topology messages."
	::= { s5TrTopBdgEntry 5 }

s5TrTopBdgAdjMasterNmmIpAddr OBJECT-TYPE
	SYNTAX	IpAddress
	ACCESS	read-only
	STATUS	mandatory
	DESCRIPTION
		"If this entry was created (and/or validated)
		by a topology message from a master NMM,
		then the value is its IP address. If the
		value of object s5TrTopBdgNum is non-zero,
		then the master NMM is on an adjacent ring.
		If the value of s5TrTopBdgNum is zero, then
		the master NMM may be adjacent, or several
		rings away, separated by one or more
		transparent bridges.

		The value for this object is 0.0.0.0 when the
		bridge generates a topology message and
		there is no master NMM on the adjacent ring
		nor one connected to the adjacent ring through
		one or more transparent bridges."
	::= { s5TrTopBdgEntry 6 }

s5TrTopBdgMacAddr OBJECT-TYPE
	SYNTAX	MacAddress
	ACCESS	read-only
	STATUS	mandatory
	DESCRIPTION
		"The MAC address of the bridge port sending
		the topology message. The value is
		00:00:00:00:00:00 if the bridge does not
		transmit topology messages."
	::= { s5TrTopBdgEntry 7 }

s5TrTopBdgIpAddr OBJECT-TYPE
	SYNTAX	IpAddress
	ACCESS	read-only
	STATUS	mandatory
	DESCRIPTION
		"IP address of the bridge sending the topology
		message. The value is 0.0.0.0 if the bridge
		does not transmit topology messages."
	::= { s5TrTopBdgEntry 8 }

s5TrTopBdgType OBJECT-TYPE
	SYNTAX	INTEGER {
		other(1),
		t3522Syn2Port(2),
		t2722Syn2Port(3),
		tCenTillionTrSwitch(4)
		}
	ACCESS	read-only
	STATUS	mandatory
	DESCRIPTION
		"The kind of bridge this entry represents.
		The values come from the topology messages
		generated by the bridge. The values are:
		  other(1)...........bridge does not send topology
		                       messages or is not a
		                       defined type
		  t3522Syn2Port(2)...SynOptics 2 port bridge in
		                       a modular concentrator
		  t2722Syn2Port(3)...SynOptics 2 port stand-alone
		                       bridge
		  tCenTillionTrSwitch(4)...Centillion multi-port
		                             TR switch"
	::= { s5TrTopBdgEntry 9 }

s5TrTopBdgSlotNum OBJECT-TYPE
	SYNTAX	INTEGER (0..255)
	ACCESS	read-only
	STATUS	mandatory
	DESCRIPTION
		"The slot that the reporting NMM received the
		topology message from the bridge. The value
		zero is used to indicate that the bridge does
		not transmit topology messages or the slot
		from which the message was received can not be
		determined."
	::= { s5TrTopBdgEntry 10 }

s5TrTopBdgPortNum OBJECT-TYPE
	SYNTAX	INTEGER (0..255)
	ACCESS	read-only
	STATUS	mandatory
	DESCRIPTION
		"The port that the reporting NMM received the
		topology message from the bridge. The value
		zero is used to indicate that the bridge does
		not transmit topology messages or the port
		from which the message was received can not
		be determined."
	::= { s5TrTopBdgEntry 11 }

s5TrTopBdgNumPort OBJECT-TYPE
	SYNTAX	INTEGER (0..255)
	ACCESS	read-only
	STATUS	mandatory
	DESCRIPTION
		"The total number of ports installed on the
		bridge. The value zero is used to indicate that
		the bridge does not transmit topology messages."
	::= { s5TrTopBdgEntry 12 }

s5TrTopBdgHelloPortNum OBJECT-TYPE
	SYNTAX	INTEGER (0..255)
	ACCESS	read-only
	STATUS	mandatory
	DESCRIPTION
		"The port on the bridge from which the topology
		message was sent. The value zero is used to
		indicate that the bridge does not transmit
		topology messages."
	::= { s5TrTopBdgEntry 13 }

s5TrTopBdgHelloPortStatus OBJECT-TYPE
	SYNTAX	INTEGER {
		other(1),
		tranAct(2),
		tranStnBy(3),
		srSrsOn(4),
		srSrsOff(5),
		srSrsOnTranAct(6),
		srSrsOffTranAct(7),
		srSrsOnStnBy(8),
		srSrsOffStnBy(9)
		}
	ACCESS	read-only
	STATUS	mandatory
	DESCRIPTION
		"The status of the port on Bridge from which
		the topology message was sent. The values are:
		  other(1).............bridge does not send topology
		                         messages or port not in
		                         defined status
		  tranAct(2)...........Transparent active
		  tranStnBy(3).........Transparent standby
		  srSrsOn(4)...........Source routing single route
		                         spanning is on
		  srSrsOff(5)..........Source routing single route
		                         spanning is off
		  srSrsOnTranAct(6)....Source routing single route
		                         spanning is on, and
		                         transparent active
		  srSrsOffTranAct(7)...Source routing single route
		                         spanning is off, and
		                         transparent active
		  srSrsOnStnBy(8)......Source routing single route
		                         spanning is on, and
		                         transparent standby
		  srSrsOffStnBy(9).....Source routing single route
		                         spanning is off, and
		                         transparent standby"
	::= { s5TrTopBdgEntry 14 }

s5TrTopBdgMonPortStatus OBJECT-TYPE
	SYNTAX	INTEGER {
		other(1),
		phantomOff(2),
		phantomOn(3),
		phantomOffWrapped(4),
		phantomOnWrapped(5),
		wrongSpeedWrap(6)
		}
	ACCESS	read-only
	STATUS	mandatory
	DESCRIPTION
		"The status of the 'monitor' port on Bridge from
		which the topology message was sent.
		The values are:
		  other(1)...............bridge does not send topology
		                           messages or the status of
		                           the monitor port is unknown
		                           or the bridge does not have
		                           a monitor port, or some other
		                           condition.
		  phantomOff(2)..........phantom status is off
		  phantomOn(3)...........phantom status is on
		  phantomOffWrapped(4)...phantom off and port wrapped
		  phantomOnWrapped(5)....phantom on and port wrapped
		  wrongSpeedWrap(6)......port wrapped for wrong speed"
	::= { s5TrTopBdgEntry 15 }

s5TrTopBdgHelloType OBJECT-TYPE
	SYNTAX	INTEGER {
		other(1),
		synoptics(2),
		ibm(3)
		}
	ACCESS	read-only
	STATUS	mandatory
	DESCRIPTION
		"The type of topology message received from the
		bridge. The values are:
		  other..........bridge does not send any of the
		                   recognizable topology message
		                   types
		  synoptics(2)...bridge sends SynOptics' topology
		                   message"
	::= { s5TrTopBdgEntry 16 }



-- Same Ring NMM Topology Table


s5TrTopRingNmmTable OBJECT-TYPE
	SYNTAX	SEQUENCE OF S5TrTopRingNmmEntry
	ACCESS	not-accessible
	STATUS	mandatory
	DESCRIPTION
		"A table listing all the Network Management
		Modules (NMMs) with a Token Ring interface
		on the same ring as the reporting NMM. The
		number of entries is determined by the number
		of detected (and active) NMMs. Entries are
		created by reception of a topology message from
		a 'new' NMM. An entry is removed from the table
		when no topology messages are received from the
		NMM in the required time interval."
	::= { s5TrTop 4 }

s5TrTopRingNmmEntry OBJECT-TYPE
	SYNTAX	S5TrTopRingNmmEntry
	ACCESS	not-accessible
	STATUS	mandatory
	DESCRIPTION
		"A row in the table of Network Management
		Modules (NMMs) with a Token Ring interface
		on the same ring as the reporting NMM.
		Entries in the table can not be created
		or deleted via SNMP."
	INDEX	{ s5TrTopRingNmmIfIpAddr,
		  s5TrTopRingNmmIpAddr }
	::= {s5TrTopRingNmmTable 1 }

S5TrTopRingNmmEntry ::= SEQUENCE {
	s5TrTopRingNmmIfIpAddr IpAddress,
	s5TrTopRingNmmIpAddr IpAddress,
	s5TrTopRingNmmMacAddr MacAddress,
	s5TrTopRingNmmChassisType SnpxChassisType,
	s5TrTopRingNmmBkplType SnpxBackplaneType,
	s5TrTopRingNmmSlotNum INTEGER,
	s5TrTopRingNmmUnaIpAddr IpAddress
	}

s5TrTopRingNmmIfIpAddr OBJECT-TYPE
	SYNTAX	IpAddress
	ACCESS	read-only
	STATUS	mandatory
	DESCRIPTION
		"The IP address of the interface on which
		the topology message was received."
	::= { s5TrTopRingNmmEntry 1 }

s5TrTopRingNmmIpAddr OBJECT-TYPE
	SYNTAX	IpAddress
	ACCESS	read-only
	STATUS	mandatory
	DESCRIPTION
		"The IP address of the NMM that sent
		the topology message."
	::= { s5TrTopRingNmmEntry 2 }

s5TrTopRingNmmMacAddr OBJECT-TYPE
	SYNTAX	MacAddress
	ACCESS	read-only
	STATUS	mandatory
	DESCRIPTION
		"The MAC address of the NMM that sent
		the topology message."
	::= { s5TrTopRingNmmEntry 3 }

s5TrTopRingNmmChassisType OBJECT-TYPE
	SYNTAX	SnpxChassisType
	ACCESS	read-only
	STATUS	mandatory
	DESCRIPTION
		"The type of chassis containing the NMM
		that sent the topology message."
	::= { s5TrTopRingNmmEntry 4 }

s5TrTopRingNmmBkplType OBJECT-TYPE
	SYNTAX	SnpxBackplaneType
	ACCESS	read-only
	STATUS	mandatory
	DESCRIPTION
		"The type of backplane in the chassis
		containing the NMM that sent the topology
		message."
	::= { s5TrTopRingNmmEntry 5 }

s5TrTopRingNmmSlotNum OBJECT-TYPE
	SYNTAX	INTEGER (0..255)
	ACCESS	read-only
	STATUS	mandatory
	DESCRIPTION
		"The slot containing the NMM that sent the
		topology message."
	::= { s5TrTopRingNmmEntry 6 }

s5TrTopRingNmmUnaIpAddr OBJECT-TYPE
	SYNTAX	IpAddress
	ACCESS	read-only
	STATUS	mandatory
	DESCRIPTION
		"The IP address of the next upstream NMM
		of the NMM that sent the topology message."
	::= { s5TrTopRingNmmEntry 7 }



-- Encoded Octet Strings for NMM Topology Table


s5TrTopNmmEosSize OBJECT-TYPE
	SYNTAX	INTEGER (0..1400)
	ACCESS	read-only
	STATUS	mandatory
	DESCRIPTION
		"The current size of a 'row' in the table
		s5TrTopNmmEosTable. This allows applications
		to be able to break apart 'rows' in the table."
	::= { s5TrTop 5 }

s5TrTopNmmEosTable OBJECT-TYPE
	SYNTAX	SEQUENCE OF S5TrTopNmmEosEntry
	ACCESS	not-accessible
	STATUS	mandatory
	DESCRIPTION
		"A table of encoded octet strings of
		entries in table s5TrTopNmmTable.
		The number of entries is determined by the
		packing of 'rows' from s5TrTopNmmTable."
	::= { s5TrTop 6 }

s5TrTopNmmEosEntry OBJECT-TYPE
	SYNTAX	S5TrTopNmmEosEntry
	ACCESS	not-accessible
	STATUS	mandatory
	DESCRIPTION
		"A row in the table of encoded octet
		strings for table s5TrTopNmmTable.
		Instance returned in Response PDU:
		  On GETs: instance specified is the
		             instance returned.
		  On GET-NEXTs: instance returned is the
		                  instance of the last record
		                  contained in the octet string.
		Entries in the table can not be created
		or deleted via SNMP."
	INDEX	{ s5TrTopNmmIfIpAddr,
		  s5TrTopNmmIpAddr }
	::= { s5TrTopNmmEosTable 1 }

S5TrTopNmmEosEntry ::= SEQUENCE {
	s5TrTopNmmEos OCTET STRING
	}

s5TrTopNmmEos OBJECT-TYPE
	SYNTAX	OCTET STRING (SIZE(0..1400))
	ACCESS	read-only
	STATUS	mandatory
	DESCRIPTION
		"An encoded octet string. On reads it contains
		an integral number of 'rows' from table
		s5TrTopNmmTable. All 'rows' are the same size
		which is defined by object s5TrTopNmmEosSize."
	::= { s5TrTopNmmEosEntry 1 }



-- Encoded Octet Strings for Bridge Topology Table 


s5TrTopBdgEosSize OBJECT-TYPE
	SYNTAX	INTEGER (0..1400)
	ACCESS	read-only
	STATUS	mandatory
	DESCRIPTION
		"The current size of a 'row' in the table
		s5TrTopBdgEosTable. This allows applications
		to be able to break apart 'rows' in the table."
	::= { s5TrTop 7 }

s5TrTopBdgEosTable OBJECT-TYPE
	SYNTAX	SEQUENCE OF S5TrTopBdgEosEntry
	ACCESS	not-accessible
	STATUS	mandatory
	DESCRIPTION
		"A table of encoded octet strings of
		entries in table s5TrTopBdgTable.
		The number of entries is determined by the
		packing of 'rows' from s5TrTopBdgTable."
	::= { s5TrTop 8 }

s5TrTopBdgEosEntry OBJECT-TYPE
	SYNTAX	S5TrTopBdgEosEntry
	ACCESS	not-accessible
	STATUS	mandatory
	DESCRIPTION
		"A row in the table of encoded octet
		strings for table s5TrTopBdgTable.
		Instance returned in Response PDU:
		  On GETs: instance specified is the
		             instance returned.
		  On GET-NEXTs: instance returned is the
		                  instance of the last record
		                  contained in the octet string.
		Entries in the table can not be created
		or deleted via SNMP."
	INDEX	{ s5TrTopBdgIfIpAddr,
		  s5TrTopBdgIndx }
	::= { s5TrTopBdgEosTable 1 }

S5TrTopBdgEosEntry ::= SEQUENCE {
	s5TrTopBdgEos OCTET STRING
	}

s5TrTopBdgEos OBJECT-TYPE
	SYNTAX	OCTET STRING (SIZE(0..1400))
	ACCESS	read-only
	STATUS	mandatory
	DESCRIPTION
		"An encoded octet string. On reads it contains
		an integral number of 'rows' from table
		s5TrTopBdgEntry. All 'rows' are the same size
		which is defined by object s5TrTopBdgEosSize."
	::= { s5TrTopBdgEosEntry 1 }



-- Encoded Octet Strings for Same Ring NMM Topology Table

s5TrTopRingNmmEosSize OBJECT-TYPE
	SYNTAX	INTEGER (0..1400)
	ACCESS	read-only
	STATUS	mandatory
	DESCRIPTION
		"The current size of a 'row' in the table
		s5TrTopRingNmmEosTable. This allows applications
		to be able to break apart 'rows' in the table."
	::= { s5TrTop 9 }

s5TrTopRingNmmEosTable OBJECT-TYPE
	SYNTAX	SEQUENCE OF S5TrTopRingNmmEosEntry
	ACCESS	not-accessible
	STATUS	mandatory
	DESCRIPTION
		"A table of encoded octet strings of
		entries in table s5TrTopRingNmmTable.
		The number of entries is determined by the
		packing of 'rows' from s5TrTopRingNmmTable."
	::= { s5TrTop 10 }

s5TrTopRingNmmEosEntry OBJECT-TYPE
	SYNTAX	S5TrTopRingNmmEosEntry
	ACCESS	not-accessible
	STATUS	mandatory
	DESCRIPTION
		"A row in the table of encoded octet
		strings for table s5TrTopRingNmmTable.
		Instance returned in Response PDU:
		  On GETs: instance specified is the
		             instance returned.
		  On GET-NEXTs: instance returned is the
		                  instance of the last record
		                  contained in the octet string.
		Entries in the table can not be created
		or deleted via SNMP."
	INDEX	{ s5TrTopRingNmmIfIpAddr,
		  s5TrTopRingNmmIpAddr }
	::= { s5TrTopRingNmmEosTable 1 }

S5TrTopRingNmmEosEntry ::= SEQUENCE {
	s5TrTopRingNmmEos OCTET STRING
	}

s5TrTopRingNmmEos OBJECT-TYPE
	SYNTAX	OCTET STRING (SIZE(0..1400))
	ACCESS	read-only
	STATUS	mandatory
	DESCRIPTION
		"An encoded octet string. On reads it contains
		an integral number of 'rows' from table
		s5TrTopRingNmmTable. All 'rows' are the same size
		which is defined by object s5TrTopNmmEosSize."
	::= { s5TrTopRingNmmEosEntry 1 }

END
-- SECTION 1: Top Level Definitions

S5-TOKENRING-MIB DEFINITIONS ::= BEGIN


-- 5000 Token Ring MIB Release 1.2.1
-- Revision 04/05/95

-- Copyright 1995 Bay Networks, Inc.
-- All rights reserved.
-- This SynOptics SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	Counter, TimeTicks
		FROM RFC1155-SMI
	OBJECT-TYPE
		FROM RFC-1212
	s5Tok
		FROM S5-ROOT-MIB
	MacAddress, TimeIntervalSec, TimeIntervalHrd, SrcIndx
		FROM S5-TCS-MIB;



-- Token Ring Groups

-- Configuration
s5TrCfg		OBJECT IDENTIFIER ::= { s5Tok 1 }

-- Statistics
s5TrStat	OBJECT IDENTIFIER ::= { s5Tok 2 }

-- Ring and Station
s5TrRing	OBJECT IDENTIFIER ::= { s5Tok 3 }

-- Test Path Group
s5TrTest	OBJECT IDENTIFIER ::= { s5Tok 4 }



-- SECTION 2: Ring and Station Information



-- Ring Info table

s5TrRingInfoTable OBJECT-TYPE
	SYNTAX	SEQUENCE OF S5TrRingInfoEntry
	ACCESS	not-accessible
	STATUS	mandatory
	DESCRIPTION
		"A table containing information
		about selected rings. The entries
		in the table may come from
		several different data sources.
		The number of entries is determined
		by the number of sources that can
		provide the information."
	::= { s5TrRing 1 }


s5TrRingInfoEntry OBJECT-TYPE
	SYNTAX	S5TrRingInfoEntry
	ACCESS	not-accessible
	STATUS	mandatory
	DESCRIPTION
		"A row in Token Ring information
		table. Entries can not be created
		or deleted via SNMP."
	INDEX	{ s5TrRingInfoSrcIndx }
	::= { s5TrRingInfoTable 1 }


S5TrRingInfoEntry ::= SEQUENCE {
	s5TrRingInfoSrcIndx SrcIndx,

	s5TrRingInfoRingNum INTEGER,
	s5TrRingInfoStaTableOperSize INTEGER,
	s5TrRingInfoActiveStations INTEGER,
	s5TrRingInfoDeletes Counter,
	s5TrRingInfoLastDeleteTime TimeTicks,
	s5TrRingInfoAgeInterval TimeIntervalSec,
	s5TrRingInfoMonTime TimeTicks,

	s5TrRingInfoRingState INTEGER,
	s5TrRingInfoBeaconSender MacAddress,
	s5TrRingInfoBeaconNaun MacAddress,
	s5TrRingInfoBeaconType INTEGER,
	s5TrRingInfoLastBeaconTime TimeTicks,
	s5TrRingInfoActiveMonitor MacAddress,
	s5TrRingInfoChanges Counter,

	s5TrRingInfoRingPurgeEvents Counter,
	s5TrRingInfoBeaconEvents Counter,
	s5TrRingInfoBeaconTime TimeIntervalHrd,
	s5TrRingInfoMonitorContentionEvents Counter,
	s5TrRingInfoNaunChanges Counter,
	s5TrRingInfoRingPollEvents Counter
	}


s5TrRingInfoSrcIndx OBJECT-TYPE
	SYNTAX	SrcIndx
	ACCESS	read-only
	STATUS	mandatory
	DESCRIPTION
		"The index of the entry in the table.
		This index identifies the source of the
		information. Only those sources that provide
		these statistics are in this table."
	::= { s5TrRingInfoEntry 1 }

s5TrRingInfoRingNum OBJECT-TYPE
	SYNTAX	INTEGER (0..4095)
	ACCESS	read-only
	STATUS	mandatory
	DESCRIPTION
		"The ring number of the ring that is being
		monitored. Each ring in a multiple ring network
		is assigned a unique number. Together, a ring and
		bridge number form a route designator. The ring
		number is obtained by an NMM during the
		initialization process.
		Section 3.8.1 of IEEE 802.5 specification. "
	::= { s5TrRingInfoEntry 2 }

s5TrRingInfoStaTableOperSize OBJECT-TYPE
	SYNTAX	INTEGER (1..300)
	ACCESS	read-only
	STATUS	mandatory
	DESCRIPTION
		"The operational size of the station info
		table (i.e., table s5TrStaInfoTable). This
		size is the maximum number of stations for
		which information can be collected. (Note: 
		a ring is limited to a maximum 256 active
		stations.) The station table may also contain
		entries for inactive stations. The station
		table may have any combination of active
		and inactive stations (except the number of
		active is limited to 256) up to the current
		value of this object. For example if the value
		of this object is 112, the station table could
		contain 100 inactive and 12 active stations."
	::= { s5TrRingInfoEntry 3 }

s5TrRingInfoActiveStations OBJECT-TYPE
	SYNTAX	INTEGER (1..256)
	ACCESS	read-only
	STATUS	mandatory
	DESCRIPTION
		"The number of active stations on the
		ring that is being monitored. This is the
		number of active stations in the station
		info table (i.e., table s5TrStaInfoTable)."
	::= { s5TrRingInfoEntry 4 }

s5TrRingInfoDeletes OBJECT-TYPE
	SYNTAX	Counter
	ACCESS	read-only
	STATUS	mandatory
	DESCRIPTION
		"The number of times stations were removed
		from table s5TrStaInfoTable due to either
		aging out or table overflow."
	::= { s5TrRingInfoEntry 5 }

s5TrRingInfoLastDeleteTime OBJECT-TYPE
	SYNTAX	TimeTicks
	ACCESS	read-only
	STATUS	mandatory
	DESCRIPTION
		"The value of sysUpTime when the last
		station was removed from table
		s5TrStaInfoTable. If this has not
		occurred, then the value is zero."
	::= { s5TrRingInfoEntry 6 }

s5TrRingInfoAgeInterval OBJECT-TYPE
	SYNTAX	TimeIntervalSec
	ACCESS	read-write
	STATUS	mandatory
	DESCRIPTION
		"The amount of time used to age stations
		from table s5TrStaInfoTable. If a station
		has had a status of inactive in the last
		time interval, it may be removed from
		table s5TrStaInfoTable. A value of zero
		means no aging is to occur."
	DEFVAL { 0 }
	::= { s5TrRingInfoEntry 7 }

s5TrRingInfoMonTime OBJECT-TYPE
	SYNTAX	TimeTicks
	ACCESS	read-only
	STATUS	mandatory
	DESCRIPTION
		"The length of time that the ring has been
		monitored by the current source."
	::= { s5TrRingInfoEntry 8 }

s5TrRingInfoRingState OBJECT-TYPE
	SYNTAX	INTEGER {
		normalOperation(1),
		ringPurge(2),
		monitorContention(3),
		beaconFrameStreaming(4),
		beaconBitStreaming(5),
		beaconRingSignalLoss(6),
		beaconSetRecoveryMode(7)
		}
	ACCESS	read-only
	STATUS	mandatory
	DESCRIPTION
		"The current status of this ring.
		The states are:
		  normalOperation(1).........ring operating without
		        any interruption.
		  ringPurge(2)...............Active monitor enters
		        the ring purge state whenever a token error
		        is detected.
		  monitorContention(3).......ring enters in monitor
		        contention state whenever the ring stations
		        need to establish an active monitor.
		  beaconFrameStreaming(4)....station which participates
		        in monitor contention and has monitor
		        contention timeout expired, receives multiple
		        claim tokens and cannot solve the contention
		        within one second.
		  beaconBitStreaming(5)......station which participates
		        in monitor contention, has 'monitor timeout'
		        and does not receive any claim token.
		  beaconRingSignalLoss(6)....station which has
		        'contention timeout' and participates in monitor
		        contention and detects the loss of incoming
		        signal.
		  beaconSetRecoveryMode(7)...station before acting as a
		        recovery station sends out beacon frame with a
		        recovery mode bit set."
	::= { s5TrRingInfoEntry 9 }

s5TrRingInfoBeaconSender OBJECT-TYPE
	SYNTAX	MacAddress
	ACCESS	read-only
	STATUS	mandatory
	DESCRIPTION
		"The MAC address of the sender of the
		last beacon frame detected on the ring.
		If no beacon frame has been detected,
		then the value is equal to six octets
		of zero."
	::= { s5TrRingInfoEntry 10 }

s5TrRingInfoBeaconNaun OBJECT-TYPE
	SYNTAX	MacAddress
	ACCESS	read-only
	STATUS	mandatory
	DESCRIPTION
		"The MAC address of the NAUN (next active
		upstream neighbor) in the last beacon frame
		detected on the ring. If no beacon frame has
		been detected, then the value is equal to six
		octets of zero."
	::= { s5TrRingInfoEntry 11 }

s5TrRingInfoBeaconType OBJECT-TYPE
	SYNTAX	INTEGER {
		other(1),
		recovery(2),
		signalLoss(3),
		bitStreaming(4),
		contentionStreaming(5)
		}
	ACCESS	read-only
	STATUS	mandatory
	DESCRIPTION
		"The type of the last beacon frame detected
		on the ring. The values are:
		  other(1).................No beacon seen or
		        some other type
		  recovery(2)..............station before acting
		        as a recovery station sends out a beacon
		        frame with a recovery mode bit set.
		  signalLoss(3)............station which has
		        'contention timeout' and participates in
		        monitor contention and detects the loss
		        of incoming signal.
		  bitStreaming(4)..........station which participates
		        in monitor contention, has monitor timeout
		        and does not receive any claim token.
		  contentionStreaming(5)...station which participates
		        in monitor contention and has monitor
		        contention timeout expired, receives multiple
		        claim tokens and cannot solve the contention
		        within one second."
	::= { s5TrRingInfoEntry 12 }

s5TrRingInfoLastBeaconTime OBJECT-TYPE
	SYNTAX	TimeTicks
	ACCESS	read-only
	STATUS	mandatory
	DESCRIPTION
		"The value of sysUpTime when the last beacon
		frame was detected on the ring. If one has not
		been detected, then the value is zero."
	::= { s5TrRingInfoEntry 13 }

s5TrRingInfoActiveMonitor OBJECT-TYPE
	SYNTAX	MacAddress
	ACCESS	read-only
	STATUS	mandatory
	DESCRIPTION
		"The MAC address of the Active Monitor
		on the ring. If this address is unknown,
		then the value is equal to six octets
		of zero."
	::= { s5TrRingInfoEntry 14 }

s5TrRingInfoChanges OBJECT-TYPE
	SYNTAX	Counter
	ACCESS	read-only
	STATUS	mandatory
	DESCRIPTION
		"The number of add and delete events in the
		station info table associated with
		this ring. If no changes have occurred,
		then the value is zero."
	::= { s5TrRingInfoEntry 15 }

s5TrRingInfoRingPurgeEvents OBJECT-TYPE
	SYNTAX	Counter
	ACCESS	read-only
	STATUS	mandatory
	DESCRIPTION
		"The total number of times that the ring has
		entered the ring purge state from the normal ring
		state. The ring purge state that comes from the
		monitor contention or beacon state is not counted."
	::= { s5TrRingInfoEntry 16 }

s5TrRingInfoBeaconEvents OBJECT-TYPE
	SYNTAX	Counter
	ACCESS	read-only
	STATUS	mandatory
	DESCRIPTION
		"The total number of times that the ring has
		entered the beaconing state."
	::= { s5TrRingInfoEntry 17 }

s5TrRingInfoBeaconTime OBJECT-TYPE
	SYNTAX	TimeIntervalHrd
	ACCESS	read-only
	STATUS	mandatory
	DESCRIPTION
		"The total amount of time that the ring has been
		in the beaconing state. This beacon time is
		updated anytime whenever the ring enters a
		beaconing state."
	::= { s5TrRingInfoEntry 18 }

s5TrRingInfoMonitorContentionEvents OBJECT-TYPE
	SYNTAX	Counter
	ACCESS	read-only
	STATUS	mandatory
	DESCRIPTION
		"The total number of times that the ring has
		entered the monitor contention state from the
		normal ring state or ring purge state. The
		monitor contention state that comes from the
		beacon state is not counted."
	::= { s5TrRingInfoEntry 19 }

s5TrRingInfoNaunChanges OBJECT-TYPE
	SYNTAX	Counter
	ACCESS	read-only
	STATUS	mandatory
	DESCRIPTION
		"The total number of NAUN (Nearest Active
		Upstream Neighbor) changes that have been
		measured. This is determined by the number
		of Report SUA change MAC frames that have
		been detected."
	::= { s5TrRingInfoEntry 20 }

s5TrRingInfoRingPollEvents OBJECT-TYPE
	SYNTAX	Counter
	ACCESS	read-only
	STATUS	mandatory
	DESCRIPTION
		"The total number of ring poll events that have
		been detected."
	::= { s5TrRingInfoEntry 21 }



-- Station Info Table

s5TrStaInfoTable OBJECT-TYPE
	SYNTAX	SEQUENCE OF S5TrStaInfoEntry
	ACCESS	not-accessible
	STATUS	mandatory
	DESCRIPTION
		"A table containing information about
		the stations on selected rings. The
		number of rings is determined by the
		number of data sources. The number of
		stations is determined by the number
		on each ring limited by the configured
		maximum number. An entry will exist
		for each station that is now or has
		previously been detected on the ring.
		This table extends each row in the
		s5TrRingInfoTable with station
		information."
	::= { s5TrRing 2 }

s5TrStaInfoEntry OBJECT-TYPE
	SYNTAX	S5TrStaInfoEntry
	ACCESS	not-accessible
	STATUS	mandatory
	DESCRIPTION
		"A row in the station info table.
		Entries can not be created or
		deleted via SNMP."
	INDEX	{ s5TrStaInfoSrcIndx,
		  s5TrStaInfoAddr }
	::= { s5TrStaInfoTable 1 }

S5TrStaInfoEntry ::= SEQUENCE {
	s5TrStaInfoSrcIndx SrcIndx,
	s5TrStaInfoAddr MacAddress,
	s5TrStaInfoLastNaun MacAddress,
	s5TrStaInfoStationStatus INTEGER,
	s5TrStaInfoFirstEnterTime TimeTicks,
	s5TrStaInfoLastEnterTime TimeTicks,
	s5TrStaInfoLastExitTime TimeTicks,
	s5TrStaInfoDupAddrErrs Counter,
	s5TrStaInfoInLineErrs Counter,
	s5TrStaInfoOutLineErrs Counter,
	s5TrStaInfoInternalErrs Counter,
	s5TrStaInfoInBurstErrs Counter,
	s5TrStaInfoOutBurstErrs Counter,
	s5TrStaInfoInACErrs Counter,
	s5TrStaInfoOutACErrs Counter,
	s5TrStaInfoAbortErrs Counter,
	s5TrStaInfoLostFrameErrs Counter,
	s5TrStaInfoCongestionErrs Counter,
	s5TrStaInfoFrameCopiedErrs Counter,
	s5TrStaInfoFrequencyErrs Counter,
	s5TrStaInfoTokenErrs Counter,
	s5TrStaInfoInBeaconErrs Counter,
	s5TrStaInfoOutBeaconErrs Counter,
	s5TrStaInfoInsertions Counter
	}

s5TrStaInfoSrcIndx OBJECT-TYPE
	SYNTAX	SrcIndx
	ACCESS	read-only
	STATUS	mandatory
	DESCRIPTION
		"The index of the associated entry in
		table s5TrRingInfoTable.
		This index identifies the source of the
		information. Only those sources that provide
		these statistics are in this table."
	::= { s5TrStaInfoEntry 1 }

s5TrStaInfoAddr OBJECT-TYPE
	SYNTAX	MacAddress
	ACCESS	read-only
	STATUS	mandatory
	DESCRIPTION
		"The MAC address of the station."
	::= { s5TrStaInfoEntry 2 }

s5TrStaInfoLastNaun OBJECT-TYPE
	SYNTAX	MacAddress
	ACCESS	read-only
	STATUS	mandatory
	DESCRIPTION
		"The MAC address of the last known NAUN (Next
		Active Upstream Neighbor) of this station."
	::= { s5TrStaInfoEntry 3 }

s5TrStaInfoStationStatus OBJECT-TYPE
	SYNTAX	INTEGER {
		active(1),
		notInRingPoll(2),
		inactive(3),
		forcedRemoval(4)
		}
	ACCESS	read-only
	STATUS	mandatory
	DESCRIPTION
		"The insertion status of the station
		on the ring. The values are:
		  active(1)..........Actively participating in
		                       ring poll
		  notInRingPoll(2)...Detected on the ring, but
		                       not currently participating
		                       in the ring poll
		  inactive(3)........No longer on the ring
		  forcedRemoval(4)...Forced off the ring by
		                       network management"
	::= { s5TrStaInfoEntry 4 }

s5TrStaInfoFirstEnterTime OBJECT-TYPE
	SYNTAX	TimeTicks
	ACCESS	read-only
	STATUS	mandatory
	DESCRIPTION
		"The value of sysUpTime at the time the station
		first entered the ring. If the time is unknown,
		the value shall be zero."
	::= { s5TrStaInfoEntry 5 }

s5TrStaInfoLastEnterTime OBJECT-TYPE
	SYNTAX	TimeTicks
	ACCESS	read-only
	STATUS	mandatory
	DESCRIPTION
		"The value of sysUpTime at the time the station
		last entered the ring. If the time is unknown,
		the value shall be zero."
	::= { s5TrStaInfoEntry 6 }

s5TrStaInfoLastExitTime OBJECT-TYPE
	SYNTAX	TimeTicks
	ACCESS	read-only
	STATUS	mandatory
	DESCRIPTION
		"The value of sysUpTime at the time the station
		last exited the ring. If the time is unknown,
		the value shall be zero."
	::= { s5TrStaInfoEntry 7 }

s5TrStaInfoDupAddrErrs OBJECT-TYPE
	SYNTAX	Counter
	ACCESS	read-only
	STATUS	mandatory
	DESCRIPTION
		"The number of times the station experienced
		a duplicate address error. This error is reported
		by a station via a Report Monitor Error MAC frame.
		Section 3.8.8 of IEEE 802.5 specificatiuon."
	::= { s5TrStaInfoEntry 8 }

s5TrStaInfoInLineErrs OBJECT-TYPE
	SYNTAX	Counter
	ACCESS	read-only
	STATUS	mandatory
	DESCRIPTION
		"Total number of line errors reported by
		by the station in error report frames
		and detected on the ring.
		Section 3.8.1 of IEEE 802.5 specification."
	::= { s5TrStaInfoEntry 9 }

s5TrStaInfoOutLineErrs OBJECT-TYPE
	SYNTAX	Counter
	ACCESS	read-only
	STATUS	mandatory
	DESCRIPTION
		"Total number of line errors reported by
		by the nearest active downstream neighbor
		of the station in error report frames
		and detected on the ring.
		Section 3.8.1 of IEEE 802.5 specification."
	::= { s5TrStaInfoEntry 10 }

s5TrStaInfoInternalErrs OBJECT-TYPE
	SYNTAX	Counter
	ACCESS	read-only
	STATUS	mandatory
	DESCRIPTION
		"Total number of adapter internal errors
		reported by the station in error report
		frames and detected on the ring.
		Section 3.8.2 of IEEE 802.5 specification."
	::= { s5TrStaInfoEntry 11 }

s5TrStaInfoInBurstErrs OBJECT-TYPE
	SYNTAX	Counter
	ACCESS	read-only
	STATUS	mandatory
	DESCRIPTION
		"Total number of burst errors reported by
		the station in error report frames
		and detected on the ring.
		Section 3.8.3 of IEEE 802.5 specification."
	::= { s5TrStaInfoEntry 12 }

s5TrStaInfoOutBurstErrs OBJECT-TYPE
	SYNTAX	Counter
	ACCESS	read-only
	STATUS	mandatory
	DESCRIPTION
		"Total number of burst errors reported by
		the nearest active downstream neighbor of
		the station in error report frames and
		detected on the ring.
		Section 3.8.3 of IEEE 802.5 specification."
	::= { s5TrStaInfoEntry 13 }

s5TrStaInfoInACErrs OBJECT-TYPE
	SYNTAX	Counter
	ACCESS	read-only
	STATUS	mandatory
	DESCRIPTION
		"Total number of AC (Address Copied) errors
		reported by the station in error report frames
		and detected on the ring.
		Section 3.8.4 of IEEE 802.5 specification."
	::= { s5TrStaInfoEntry 14 }

s5TrStaInfoOutACErrs OBJECT-TYPE
	SYNTAX	Counter
	ACCESS	read-only
	STATUS	mandatory
	DESCRIPTION
		"Total number of AC (Address Copied) errors
		reported by the nearest active downstream
		neighbor of the station in error report frames
		and detected on the ring.
		Section 3.8.4 of IEEE 802.5 specification."
	::= { s5TrStaInfoEntry 15 }

s5TrStaInfoAbortErrs OBJECT-TYPE
	SYNTAX	Counter
	ACCESS	read-only
	STATUS	mandatory
	DESCRIPTION
		"Total number of abort delimiter transmitted
		errors reported by the station in error report
		frames and detected on the ring.
		Section 3.8.5 of IEEE 802.5 specification."
	::= { s5TrStaInfoEntry 16 }

s5TrStaInfoLostFrameErrs OBJECT-TYPE
	SYNTAX	Counter
	ACCESS	read-only
	STATUS	mandatory
	DESCRIPTION
		"Total number of frames lost errors reported
		by the station in error report frames and
		detected on the ring.
		Section 3.8.6 of IEEE 802.5 specification."
	::= { s5TrStaInfoEntry 17 }

s5TrStaInfoCongestionErrs OBJECT-TYPE
	SYNTAX	Counter
	ACCESS	read-only
	STATUS	mandatory
	DESCRIPTION
		"Total number of receive congestion errors
		reported by the station in error report
		frames and detected on the ring.
		Section 3.8.7 of IEEE 802.5 specification."
	::= { s5TrStaInfoEntry 18 }

s5TrStaInfoFrameCopiedErrs OBJECT-TYPE
	SYNTAX	Counter
	ACCESS	read-only
	STATUS	mandatory
	DESCRIPTION
		"Total number of frame copied errors reported
		by the station in error report frames and
		detected on the ring.
		Section 3.8.8 of IEEE 802.5 specification."
	::= { s5TrStaInfoEntry 19 }

s5TrStaInfoFrequencyErrs OBJECT-TYPE
	SYNTAX	Counter
	ACCESS	read-only
	STATUS	mandatory
	DESCRIPTION
		"Total number of frequency errors reported
		by the station in error report frames
		and detected on the ring.
		Section 3.8.9 of IEEE 802.5 specification."
	::= { s5TrStaInfoEntry 20 }

s5TrStaInfoTokenErrs OBJECT-TYPE
	SYNTAX	Counter
	ACCESS	read-only
	STATUS	mandatory
	DESCRIPTION
		"Total number of token errors reported by
		the station in error report frames and
		detected on the ring.
		Section 3.8.10 of IEEE 802.5 specification."
	::= { s5TrStaInfoEntry 21 }

s5TrStaInfoInBeaconErrs OBJECT-TYPE
	SYNTAX	Counter
	ACCESS	read-only
	STATUS	mandatory
	DESCRIPTION
		"Total number of beacon frames sent by the
		station and detected on the ring."
	::= { s5TrStaInfoEntry 22 }

s5TrStaInfoOutBeaconErrs OBJECT-TYPE
	SYNTAX	Counter
	ACCESS	read-only
	STATUS	mandatory
	DESCRIPTION
		"Total number of beacon frames detected on the
		ring that name the station as the NAUN."
	::= { s5TrStaInfoEntry 23 }

s5TrStaInfoInsertions OBJECT-TYPE
	SYNTAX	Counter
	ACCESS	read-only
	STATUS	mandatory
	DESCRIPTION
		"The number of times that the station
		was detected inserting onto the ring."
	::= { s5TrStaInfoEntry 24 }



-- Station Control Table

s5TrStaCtlTable OBJECT-TYPE
	SYNTAX	SEQUENCE OF S5TrStaCtlEntry
	ACCESS	not-accessible
	STATUS	mandatory
	DESCRIPTION
		"A table containing control objects
		and addition information about the
		stations on selected rings. The
		number of rings is determined by the
		number of data sources.
		This table extends each row in table
		s5TrStaInfoTable with additional information
		and control objects."
	::= { s5TrRing 3 }

s5TrStaCtlEntry OBJECT-TYPE
	SYNTAX	S5TrStaCtlEntry
	ACCESS	not-accessible
	STATUS	mandatory
	DESCRIPTION
		"A row in the station control table.
		Entries can not be created or
		deleted via SNMP."
	INDEX	{ s5TrStaCtlSrcIndx,
		  s5TrStaCtlAddr }
	::= { s5TrStaCtlTable 1 }

S5TrStaCtlEntry ::= SEQUENCE {
	s5TrStaCtlSrcIndx SrcIndx,
	s5TrStaCtlAddr MacAddress,
	s5TrStaCtlRemove INTEGER,
	s5TrStaCtlUpdateStats INTEGER,
	s5TrStaCtlUpdateTime TimeTicks,
	s5TrStaCtlProductId OCTET STRING,
	s5TrStaCtlNodeVersion OCTET STRING,
	s5TrStaCtlPhysDrop OCTET STRING,
	s5TrStaCtlFuncAddr MacAddress,
	s5TrStaCtlAuthFuncClass OCTET STRING,
	s5TrStaCtlAuthAccPriority OCTET STRING,
	s5TrStaCtlStationId MacAddress,
	s5TrStaCtlNumGrpAddr MacAddress
	}

s5TrStaCtlSrcIndx OBJECT-TYPE
	SYNTAX	SrcIndx
	ACCESS	read-only
	STATUS	mandatory
	DESCRIPTION
		"The first index of the associated entry
		in table s5TrStaInfoTable.
		This index identifies the source of the
		information. Only those sources that provide
		these statistics are in this table."
	::= { s5TrStaCtlEntry 1 }

s5TrStaCtlAddr OBJECT-TYPE
	SYNTAX	MacAddress
	ACCESS	read-only
	STATUS	mandatory
	DESCRIPTION
		"The second index of the associated entry
		in table s5TrStaInfoTable. This index is
		the MAC address of the station."
	::= { s5TrStaCtlEntry 2 }

s5TrStaCtlRemove OBJECT-TYPE
	SYNTAX	INTEGER {
		stable(1),
		remove(2)
		}
	ACCESS	read-write
	STATUS	mandatory
	DESCRIPTION
		"This is an action object to send a Remove
		Station MAC frame to the station. The following
		value can be written:
		  remove(2)...causes a frame to be sent

		The following values can be read:
		  stable(1)...a frame is not currently
		                being sent
		  remove(2)...in progress of sending a frame."
	::= { s5TrStaCtlEntry 3 }

s5TrStaCtlUpdateStats OBJECT-TYPE
	SYNTAX	INTEGER {
		other(1),
		inactive(2),
		stable(3),
		update(4)
		}
	ACCESS	read-write
	STATUS	mandatory
	DESCRIPTION
		"This is an action object used to cause
		configuration information for the station
		to be updated. The following value can
		be written:
		  update(4)...causes update to be attempted

		The following values can be read:
		  other(1)......configuration information not
		                  currently valid
		  inactive(2)...the station is currently inactive
		  stable(3).....configuration information is
		                  currently valid
		  update(4).....updating configuration info
		The object s5TrStaCtlUpdateTime has the
		time that the configuration was last updated.
		If a station is currently not on the ring,
		the value inactive(2) will be returned.
		A SET with value update(4) to an inactive station
		will result in a value of inactive(2)."
	::= { s5TrStaCtlEntry 4 }

s5TrStaCtlUpdateTime OBJECT-TYPE
	SYNTAX	TimeTicks
	ACCESS	read-only
	STATUS	mandatory
	DESCRIPTION
		"The value of sysUpTime at the time the
		configuration information was last updated
		(completely). If the information has never
		been gotten, then the value is zero. The
		config info is updated whenever a station
		is first detected on the ring."
	::= { s5TrStaCtlEntry 5 }

s5TrStaCtlProductId OBJECT-TYPE
	SYNTAX	OCTET STRING (SIZE(0..18))
	ACCESS	read-only
	STATUS	mandatory
	DESCRIPTION
		"A brief string describing the product specified
		by the vendor. The value is a zero length string
		when not valid (or available).

		Section 3.3.2.14 of IEEE 802.5 specification.

		NOTE: The characters in the string are represented
		in EBCDIC for IBM products, in ASCII for others."
	::= { s5TrStaCtlEntry 6 }

s5TrStaCtlNodeVersion OBJECT-TYPE
	SYNTAX	OCTET STRING (SIZE(0..10))
	ACCESS	read-only
	STATUS	mandatory
	DESCRIPTION
		"A string that represents the version of the
		station software. The value is a zero length
		string when not valid (or available).

		Section 3.3.2.17 of IEEE 802.5 specification.

		NOTE: The characters in the string are represented
		in EBCDIC for IBM products, in ASCII for others.
		The octet string is represented in the following
		format for IBM products:
		    octets from 0 to 4 : Feature Code
		    octets from 5 to 9 : EC level."
	::= { s5TrStaCtlEntry 7 }

s5TrStaCtlPhysDrop OBJECT-TYPE
	SYNTAX	OCTET STRING (SIZE(4))
	ACCESS	read-only
	STATUS	mandatory
	DESCRIPTION
		"The physical location of the station on the
		ring. The value is 4 octets of zero when not
		valid (or available).

		Section 3.3.2.13 of IEEE 802.5 specification."
	::= { s5TrStaCtlEntry 8 }

s5TrStaCtlFuncAddr OBJECT-TYPE
	SYNTAX	MacAddress
	ACCESS	read-only
	STATUS	mandatory
	DESCRIPTION
		"The functional addresses used by the station.
		The value is 6 octets of zero when not valid
		(or available).

		Section 3.3.2.8 of IEEE 802.5 specification."
	::= { s5TrStaCtlEntry 9 }

s5TrStaCtlAuthFuncClass OBJECT-TYPE
	SYNTAX	OCTET STRING (SIZE(2))
	ACCESS	read-only
	STATUS	mandatory
	DESCRIPTION
		"The functional classes that are allowed to
		be active in the station.  The value is 2
		octets of zero when not valid (or available).

		Section 3.3.2.3 of IEEE 802.5 specification."
	::= { s5TrStaCtlEntry 10 }

s5TrStaCtlAuthAccPriority OBJECT-TYPE
	SYNTAX	OCTET STRING (SIZE(2))
	ACCESS	read-only
	STATUS	mandatory
	DESCRIPTION
		"The maximum priority this station is allowed
		to use. The value is 2 octets of zero when
		not valid (or available).

		Section 3.3.2.2 of IEEE 802.5 specification."
	::= { s5TrStaCtlEntry 11 }

s5TrStaCtlStationId OBJECT-TYPE
	SYNTAX	MacAddress
	ACCESS	read-only
	STATUS	mandatory
	DESCRIPTION
		"This string is used to uniquely identify
		the station. It may be equal to the station's
		MAC address. The value is 6 octets of zero
		when not valid (or available).

		Section 3.3.2.21 of IEEE 802.5 specification."
	::= { s5TrStaCtlEntry 12 }

s5TrStaCtlNumGrpAddr OBJECT-TYPE
	SYNTAX	MacAddress
	ACCESS	read-only
	STATUS	mandatory
	DESCRIPTION
		"The group address for the station.
		The value is zero if not valid or
		no group address has been assigned.

		Section 3.3.2.9 of IEEE 802.5 specification."
	::= { s5TrStaCtlEntry 13 }



-- Test Path Group

s5TrTestPathTestTimer OBJECT-TYPE
	SYNTAX	TimeIntervalHrd
	ACCESS	read-write
	STATUS	mandatory
	DESCRIPTION
		"This is the timeout, in units of hundredths of a second,
		that the agent will wait for a reply to an LLC TEST
		command PDU caused by doing a SNMP SET to the object
		s5TrAgentTpStart with the value startTestSourceRoute(2)
		or startTestTransparent(3). This timer applies to all
		entries in table s5TrTestPathTable."
	DEFVAL { 400 }  -- 4 seconds
	::={s5TrTest 1}

s5TrTestPathAgeTimer OBJECT-TYPE
	SYNTAX	TimeIntervalSec (0..65535)
	ACCESS	read-write
	STATUS	mandatory
	DESCRIPTION
		"The amount of time, in units of seconds, that
		an entry remains in table s5TrTestPathTable before
		it is automatically removed. This value must be larger
		than the value of s5TrTestPathTimer. This timer
		applies to all entries in table s5TrTestPathTable.
		When the value is 0, no entry will be aged out."
	DEFVAL { 300 } -- 5 minutes
	::={s5TrTest 2}

s5TrTestPathTable OBJECT-TYPE
	SYNTAX	SEQUENCE OF S5TrTestPathEntry
	ACCESS	not-accessible
	STATUS	mandatory
	DESCRIPTION
		"This table is used to initiate a 'path test' between
		the agent and a station in the flatnet.  To start a
		path test, a SNMP SET operation is attempted with the
		value of the object s5TrTestTpStart set to
		startTestSourceRoute(2) or startTestTransparent(3).

		There can only be one test active between the
		agent and a particular station at any time. 

		The table size has an implementation limit. It is
		determined by the agent.

		Note:  Performing a path test on a destination station
		       which does not recognize or reply to 802.2 TEST
		       command PDU will result in a 'test-failed'."
	::={s5TrTest 3}

s5TrTestPathEntry OBJECT-TYPE
	SYNTAX	S5TrTestPathEntry
	ACCESS	not-accessible
	STATUS	mandatory
	DESCRIPTION
		"A row in the test path table. Entries can be created
		with a SNMP SET request by setting the object
		s5TrTestTpStart to either startTestSourceRoute(2) or
		startTestTransparent(3) or by setting the object 
		s5TrTestTpRoute to some specific route string, with the 
		index portion of the object specifying the source 
		(s5TrTestTpIfIndex) and destination MAC address
		(s5TrTestTpAddrTo).

		If s5TrTestTpRoute is set to some specific route string 
		and s5TrTestTpStart is not startTestSourceRoute(2), 
		startTestTransparent(3), retryTestSourceRoute(4), 
		retryTestTransparent(5), or clearTest(6), the agent will
		set s5TrTestTpStart to startTestSourceRoute(2).
 		
		After the entry is created, it will live in the table until it
		is aged out by the value of s5TrTestPathAgeTimer or
		until it is removed by setting s5TrTestTpStart to
		clearTest(6)."
	INDEX	{ s5TrTestTpIfIndex, s5TrTestTpAddrTo }
	::={s5TrTestPathTable 1}

S5TrTestPathEntry ::= SEQUENCE {
	s5TrTestTpIfIndex INTEGER,
	s5TrTestTpAddrTo OCTET STRING,
	s5TrTestTpStart  INTEGER,
	s5TrTestTpStatus INTEGER,
	s5TrTestTpRoute OCTET STRING,
	s5TrTestTpDuration TimeIntervalHrd,
	s5TrTestTpTimeStamp TimeTicks
}

s5TrTestTpIfIndex OBJECT-TYPE
	SYNTAX	INTEGER (1..65535)
	ACCESS	read-only
	STATUS	mandatory
	DESCRIPTION
		"The index from the ifTable of a token ring interface.
		This is the source of the TEST command PDU."
	::={s5TrTestPathEntry 1}

s5TrTestTpAddrTo OBJECT-TYPE
	SYNTAX	OCTET STRING (SIZE (6))
	ACCESS	read-only
	STATUS	mandatory
	DESCRIPTION
		"The destination MAC address to be used for the
		testpath operation."
	::={s5TrTestPathEntry 2}

s5TrTestTpStart OBJECT-TYPE
	SYNTAX INTEGER {
		other(1),
		startTestSourceRoute(2),
		startTestTransparent(3),
		retryTestSourceRoute(4),
		retryTestTransparent(5),
		clearTest(6)
		}
	ACCESS	read-write
	STATUS	mandatory
	DESCRIPTION
		"This object is used to start or retry a test or delete an 
		entry.  The possible values that can be written
		are:

		  startTestSourceRoute(2)...Start a path test for
		                            networks using source
		                            routing bridging.
		  startTestTransparent(3)...Start a path test for
		                            networks using
		                            transparent bridging.
		  retryTestSourceRoute(4)...Retry the path test for
		                            networks using source
		                            routing bridging.
		  retryTestTransparent(5)...Retry the path test for
		                            networks using
		                            transparent bridging.
		  clearTest(6)..........Delete an entry.

		The possible values that can be read are:
		  other(1)            none of the following.
		  startTestSourceRoute(2)...Indicates a path test for
		                            networks using source
		                            routing bridging has
		                            been started.
		  startTestTransparent(3)...Indicates a path test for
		                            networks using
		                            transparent bridging has
		                            been started.
		  retryTestSourceRoute(4)...Indicates the path test for
		                            networks using source
		                            routing bridging has
		                            been retried.
		  retryTestTransparent(5)...Indicates the path test for
		                            networks using
		                            transparent bridging has
		                            been retried.
		 
		If s5TrTestTpStart is set to startTestTransparent(3) or
		retryTestTransparent(5), the value of s5TrTestTpRoute is
 		ignored.  A TEST command PDU without source routing
		information will be sent by the agent.

		If s5TrTestTpStart is set to startTestSourceRoute(2) or
 		retryTestSourceRoute(5) and the value 
		s5TrTestTpRoute is a zero length string, a single-route
		broadcast TEST command PDU will be sent to explore the
		route from the agent to s5TrTestTpAddrTo.  If
		s5TrTestTpRoute contains some specific route, the agent
		will send a  nonbroadcast TEST command PDU to check
		this route.

		If a test between the station identified by the 
		object s5TrTestTpStart and the agent has already been
		started (so the s5TrTestTpStatus has value  
		testInProgress(2)),  the agent will return 'no 
		error' to the SNMP SET request of a start or retry value.
		However, the agent will not initiate a new TEST
		command PDU.

		If the test cannot be started because of errors
		in the SET request, or because of some limitations
		on the agent side (e.g., the table limit has been
		exceeded), then the response to the SET request will
		be SNMP 'bad value' or 'general' error.

		For both start-test and retry-test the age-out time for 
		the entry will be refreshed (i.e., as if the entry was just 
		created)."
	DEFVAL { startTestSourceRoute }
	::={s5TrTestPathEntry 3}

s5TrTestTpStatus OBJECT-TYPE
	SYNTAX INTEGER {
		other(1),
		testInProgress(2),
		testPassed(3),
		testFailed(4)
		}
	ACCESS	read-only
	STATUS	mandatory
	DESCRIPTION
		"The current status of the test.  The possible values
		are :

		  testInProgress(2)...The path test is currently in progress.
		  testPassed(3).......The path test passed.
		  testFailed(4).......The path test failed.

		If the interval of time between the agent's request
		and the station's response is less than s5TrTestPathTimer,
		then the value will be testPassed(3).  If the interval is
		longer, the value will be testFailed(4). While the
		agent is waiting for a response, the value will be
		testInProgress(2)."
	::={s5TrTestPathEntry 4}

s5TrTestTpRoute OBJECT-TYPE
	SYNTAX	OCTET STRING (SIZE(0..15))
	ACCESS	read-write
	STATUS	mandatory
	DESCRIPTION
		"When this object is written via SNMP it specifies
		the path to be tested.  If this object is not written
		when the row is created, it is filled in by the agent
		when the path test is completed.

		This object is an encoded octet string that specifies
		the source route path.  The first octet represents the
		length in octets of the route string that follows.  
		Each two octets that follow specify a ring number/bridge
		number pair representing an entry for a hop. The 
		encoding is 3 nibbles for the ring number, and 1 nibble 
		for bridge number. The maximum size of this path 
		represents 7 hops (14 Octets).

		To initiate a test, write to this object with the
		appropriate route.  If the corresponding table entry
		s5TrTestTpStart is not set, the agent will set
		s5TrTestTpStart to startTestSourceRoute(2) and start
		the test.

		If the agent and the station are both on the same
		ring, the length octet will be set to zero by agent.

		If a 'Transparent path test' succeeds and the route passes
		through transparent bridges, then length octet will be
		set to 1 by agent.  This is to differentiate from the case 
		that the station and the agent are on the same ring."
	DEFVAL { "" }  -- Zero length string
	::={s5TrTestPathEntry 5}

s5TrTestTpDuration OBJECT-TYPE
	SYNTAX	TimeIntervalHrd
	ACCESS	read-only
	STATUS	mandatory
	DESCRIPTION
		"This specifies the round trip time of a successful
		test in units of hundreds of a second. This object will be
		equal to the value of s5TrTestPathTimer if the
		test has failed"
	::={s5TrTestPathEntry 6}

s5TrTestTpTimeStamp OBJECT-TYPE
	SYNTAX	TimeTicks
	ACCESS	read-only
	STATUS	mandatory
	DESCRIPTION
		"This is the time stamp (i.e., sysUpTime) of the last
		time that the path test was run successfully."
	::={s5TrTestPathEntry 7}


END
-- SECTION 1: Top Level Definitions

S5-TOKENRING-COMMON-MIB DEFINITIONS ::= BEGIN


-- 5000 Token Ring Common MIB Release 1.1.7
-- Revision 08/01/96

-- Copyright 1996 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	Counter, TimeTicks
		FROM RFC1155-SMI
	OBJECT-TYPE
		FROM RFC-1212
	DisplayString
		FROM RFC1213-MIB
	s5TrCfg, s5TrStat
		FROM S5-TOKENRING-MIB
	MacAddress, TimeIntervalSec, SrcIndx
		FROM S5-TCS-MIB;




-- SECTION 2: Configuration information

-- Port Table

s5TrPortTable OBJECT-TYPE
	SYNTAX	SEQUENCE OF S5TrPortEntry
	ACCESS	not-accessible
	STATUS	mandatory
	DESCRIPTION
		"A table containing information about each
		port on a board. The number of entries
		is determined by the number of manageable
		ports. Those boards that do not have any
		manageable ports do not have
		any entries in this table."
	::= { s5TrCfg 1 }

s5TrPortEntry OBJECT-TYPE
	SYNTAX	S5TrPortEntry
	ACCESS	not-accessible
	STATUS	mandatory
	DESCRIPTION
		"A row in Token Ring port table. Entries
		can not be created or deleted via SNMP."
	INDEX	{ s5TrPortBrdIndx,
		  s5TrPortIndx }
	::= { s5TrPortTable 1 }

S5TrPortEntry ::= SEQUENCE {
	s5TrPortBrdIndx INTEGER,
	s5TrPortIndx INTEGER,
	s5TrPortWrapStatus INTEGER,
	s5TrPortWrapTime TimeIntervalSec,
	s5TrPortInsrtStatus INTEGER,
	s5TrPortPhanStatus INTEGER,
	s5TrPortPhanChngs Counter,
	s5TrPortTrnkAccMthdStrap INTEGER,
	s5TrPortTrnkAccMthd INTEGER,
	s5TrPortClass INTEGER,
	s5TrPortMedia INTEGER,
	s5TrPortConnector INTEGER,
	s5TrPortSoftwareInsertion INTEGER,
        s5TrPortAFD INTEGER
	}

s5TrPortBrdIndx OBJECT-TYPE
	SYNTAX	INTEGER (1..255)
	ACCESS	read-only
	STATUS	mandatory
	DESCRIPTION
		"The index of the board. This corresponds to
		the index of the slot containing the board."
	::= { s5TrPortEntry 1 }

s5TrPortIndx OBJECT-TYPE
	SYNTAX	INTEGER (1..255)
	ACCESS	read-only
	STATUS	mandatory
	DESCRIPTION
		"The index of the port on the board.  Its value
		ranges between 1 and the number of manageable
		ports on the board."
	::= { s5TrPortEntry 2 }

s5TrPortWrapStatus OBJECT-TYPE
	SYNTAX	INTEGER {
		other(1),
		wrap(2),
		connect(3),
		timedWrap(4),
		nmmBeaconWrap(5),
		wrongSpeedWrap(6),
		permBeaconWrap(7),
		hostBecaonWrap (8)
		}
	ACCESS	read-write
	STATUS	mandatory
	DESCRIPTION
		"The wrap status of the port. The following
		values can be written:
		  wrap(2)........wrap the port
		  connect(3).....unwrap the port
		  timedWrap(4)...time wrap port (uses value
		                   from s5TrPortWrapTime)

		The following values reflect the wrap
		status of the port:
		  other(1)............wrap status unknown
		  wrap(2).............port is wrapped
		  connect(3)..........port is not wrapped
		  timedWrap(4)........port is timed wrapped
		                        (see value of
		                        s5TrPortWrapTime)
		  nmmBeaconWrap(5)....beaconing station
		                        automatically removed
		                        by an NMM
		  wrongSpeedWrap(6)...station with wrong speed
		                        automatically removed
		  permBeaconWrap(7)...station permanently removed
		                        by an NMM since it attempted
		                        to deinsert and insert in the
		                        ring at a high rate while it
		                        beacons the ring.
		On GETs with port status of timeWrap(4), if
		the time remaining before the wrap is undone
		is available, it will be reported in object
		s5TrPortWrapTime as a positive value. If not
		available, the value of s5TrPortWrapTime will
		be zero. When changing a port to timedWrap(4),
		the SET request must also contain the value
		for object s5TrPortWrapTime. Only value
		wrap(2) will survive resets of the host card."
	::= { s5TrPortEntry 3 }

s5TrPortWrapTime OBJECT-TYPE
	SYNTAX	TimeIntervalSec
	ACCESS	read-write
	STATUS	mandatory
	DESCRIPTION
		"The length of time to keep the port
		wrapped when a timed wrap is done to the
		board. This object can only be written
		in the same request that sets s5TrPortWrapStatus
		to timedWrap(4). Afterwards, it indicates
		the amount of time left before the timed
		wrap is completed, at which time
		s5TrPortWrapStatus is changed to connect(3).
		This object has the value of zero if the
		port is not timed wrapped, and also if the
		amount of time is not available."
	::= { s5TrPortEntry 4 }

s5TrPortInsrtStatus OBJECT-TYPE
	SYNTAX	INTEGER {
		other(1),
		notInserted(2),
		inserted(3)
		}
	ACCESS	read-only
	STATUS	mandatory
	DESCRIPTION
		"The port insertion status. The values are:
		  other(1).........status unknown
		  notInserted(2)...port is not inserted
		  inserted(3)......port inserted into the ring"
	::= { s5TrPortEntry 5 }

s5TrPortPhanStatus OBJECT-TYPE
	SYNTAX	INTEGER {
		other(1),
		noPhantom(2),
		phantom(3),
		softwarePhantom(4)
		}
	ACCESS	read-only
	STATUS	mandatory
	DESCRIPTION
		"The port phantom status. The values are:
		  other(1).............status unknown
		  noPhantom(2).........no phantom signal
		  phantom(3)...........phantom signal is on
		  softwarePhantom(4)...phantom signal is on by
		                         turning on software
		                         insertion (see
		                         s5TrPortSoftwareInsertion
		                         for more details)

		Note: for RI/RO ports, this signal is
		driven by the 'lowlight' detector. For
		RI/RO ports that have the value of
		none(3) for s5TrPortTrnkAccMthd,
		this value will always be phantom(3)."
	::= { s5TrPortEntry 6 }

s5TrPortPhanChngs OBJECT-TYPE
	SYNTAX	Counter
	ACCESS	read-only
	STATUS	mandatory
	DESCRIPTION
		"A counter of changes of s5TrPortPhanStatus
		from noPhantom(2) to phantom(3)."
	::= { s5TrPortEntry 7 }

s5TrPortTrnkAccMthdStrap OBJECT-TYPE
	SYNTAX	INTEGER {
		notSupported(1),
		synoptics(2),
		none(3)
		}
	ACCESS	read-only
	STATUS	mandatory
	DESCRIPTION
		"The strap (hardware jumper) setting for
		the RI/RO port trunk validation method.
		The values are:
		  notSupported(1)...a fiber port, or
		                      not a RI/RO port
		  synoptics(2)......use SynOptics method
		  none(3)...........no validation done
		The operational method used is indicated
		by the value of s5TrPortTrnkAccMthd."
	::= { s5TrPortEntry 8 }

s5TrPortTrnkAccMthd OBJECT-TYPE
	SYNTAX	INTEGER {
		notSupported(1),
		synoptics(2),
		none(3)
		}
	ACCESS	read-write
	STATUS	mandatory
	DESCRIPTION
		"The operational setting for the
		RI/RO port trunk validation method.
		The following values can be written:
		  synoptics(2)...use SynOptics method
		  none(3)........no validation done

		The following values can be read:
		  notSupported(1)...not a RI/RO port, or
		                      a fiber port
		  synoptics(2)......use SynOptics method
		  none(3)...........do no validation"
	::= { s5TrPortEntry 9 }

s5TrPortClass OBJECT-TYPE
	SYNTAX	INTEGER {
		other(1),
		ri(2),
		ro(3),
		lobe(4),
		internal(5)
		}
	ACCESS	read-only
	STATUS	mandatory
	DESCRIPTION
		"The port class. The values are:
		  other(1)......unknown or some other type
		  ri(2).........Ring In port
		  ro(3).........Ring Out port
		  lobe(4).......Lobe port
		  internal(5)...Internal port which may be
		                  connected to a backplane ring"
	::= { s5TrPortEntry 10 }

s5TrPortMedia OBJECT-TYPE
	SYNTAX	INTEGER {
		other(1),
		synFiber(2),
		stdFiber(3),
		copperActive(4),
		copperPassive(5),
		mac(6),
		specialProc(7)
		}
	ACCESS	read-only
	STATUS	mandatory
	DESCRIPTION
		"The port media type. The values are:
		  other(1)...........unknown or some other type
		  synFiber(2)........SynOptics Fiber
		  stdFiber(3)........Standard Fiber
		  copperActive(4)....Active copper
		  copperPassive(5)...Passive copper
		  mac(6).............Internal MAC
		  specialProc(7).....Internal special processor"
	::= { s5TrPortEntry 11 }

s5TrPortConnector OBJECT-TYPE
	SYNTAX	INTEGER {
		other(1),
		internal(2),
		db9(3),
		rj45(4),
		fiberST(5)
		}
	ACCESS	read-only
	STATUS	mandatory
	DESCRIPTION
		"The port connector type. The values are:
		  other(1)......unknown or some other type
		  internal(2)...no external connector
		  db9(3)........DB9
		  rj45(4).......RJ-45
		  fiberST(5)....fiber ST"
	::= { s5TrPortEntry 12 }

s5TrPortSoftwareInsertion OBJECT-TYPE
	SYNTAX	INTEGER {
		notCapableOfSoftwareInsertion(1),
		capableAndSoftwareInsertionOn(2),
		capableAndSoftwareInsertionOff(3)
		}
	ACCESS	read-write
	STATUS	mandatory
	DESCRIPTION
		"This object reflects the capability for a port
		to connect to the Ring-In (RI) or Ring-Out (RO)
		port of a MAU by software controlled phantom
		insertion.

		The following values can be read:
		  notCapableOfSoftwareInsertion(1)...
		                 The port is incapable of
		                   software insertion and
		                   therefore cannot connect
		                   to the RI or RO port 
		                   of a MAU
		  capableAndSoftwareInsertionOn(2)...
		                 The port is capable of
		                   software insertion,
		                   and software insertion
		                   is on
		  capableAndSoftwareInsertionOff(3)...
		                 The port is capable of
		                   software insertion,
		                   and software insertion
		                   is off

		The following values can be written:
		  capableAndSoftwareInsertionOn(2)...
		                 Turns on the software
		                   insertion (see note)
		  capableAndSoftwareInsertionOff(3)...
		                 Turns off the software
		                   insertion (see note)

		Note:  The values capableAndSoftwareInsertionOn(2)
		       and capableAndSoftwareInsertionOff(3)
		       are only valid for writing if the port
		       has the capability of software insertion."
	::= {s5TrPortEntry 13}

s5TrPortAFD OBJECT-TYPE
        SYNTAX  INTEGER {
                notCapableOfAFDDisable(1),
                capableAndAFDEnabled(2),
                capableAndAFDDisabled(3)
                }
        ACCESS  read-write
        STATUS  mandatory
        DESCRIPTION
                "This object reflects the capability for a port
                to disable AFD, Automatic Frequency Detection.

                The following values can be read:
                  notCapableOfAFDDisable(1)...
                                 The port is incapable of
                                   AFD disable.
                  capableAndAFDEnabled(2)...
                                 The port is capable of
                                   AFD disable and the
                                   current AFD is enabled.
                  capableAndAFDDisabled(3)...
                                 The port is capable of
                                   AFD disable and the
                                   current AFD is disabled.

                The following values can be written:
                  capableAndAFDEnabled(2)...
                                 Enable the AFD.
                  capableAndAFDDisabled(3)...
                                 Disable the AFD.

                Note:  The values capableAndAFDEnabled(2)
                       and capableAndAFDDisabled(3)
                       are only valid for writing if the port
                       has the capability of AFD disable."
        ::= {s5TrPortEntry 14}

-- FPU Table

s5TrFpuTable OBJECT-TYPE
	SYNTAX	SEQUENCE OF S5TrFpuEntry
	ACCESS	not-accessible
	STATUS	mandatory
	DESCRIPTION
		"A table containing information about each
		FPU (Frame Processing Unit) on a board."
	::= { s5TrCfg 2 }

s5TrFpuEntry OBJECT-TYPE
	SYNTAX	S5TrFpuEntry
	ACCESS	not-accessible
	STATUS	mandatory
	DESCRIPTION
		"A row in the Token Ring FPU table. Entries
		can not be created or deleted via SNMP."
	INDEX	{ s5TrFpuBrdIndx,
		  s5TrFpuIndx }
	::= { s5TrFpuTable 1 }

S5TrFpuEntry ::= SEQUENCE {
	s5TrFpuBrdIndx INTEGER,
	s5TrFpuIndx INTEGER,
	s5TrFpuType INTEGER,
	s5TrFpuTypeIndx INTEGER,
	s5TrFpuVer DisplayString,
	s5TrFpuCapabilites INTEGER,
	s5TrFpuRunningMode INTEGER
	}

s5TrFpuBrdIndx OBJECT-TYPE
	SYNTAX	INTEGER (1..255)
	ACCESS	read-only
	STATUS	mandatory
	DESCRIPTION
		"The index of the board. This corresponds to
		the index of the slot containing the board."
	::= { s5TrFpuEntry 1 }

s5TrFpuIndx OBJECT-TYPE
	SYNTAX	INTEGER (1..255)
	ACCESS	read-only
	STATUS	mandatory
	DESCRIPTION
		"The index of the FPU on the board. The
		value ranges between 1 and the number
		of FPUs on the board."
	::= { s5TrFpuEntry 2 }

s5TrFpuType OBJECT-TYPE
	SYNTAX	INTEGER {
		other(1),
		cluster(2),
		port(3),
		roving(4)
		}
	ACCESS	read-only
	STATUS	mandatory
	DESCRIPTION
		"The type of FPU. The values are:
		  other(1).....other or unknown
		  cluster(2)...FPU is associated with
		                 a cluster
		  port(3)......FPU is associated with
		                 a port
		  roving(4)....FPU is a virtual one due
		                 to roving embedded
		                 management FPU.  The
		                 type index s5TrFpuTypeIndx
		                 specifies port number in
		                 this case.

		This describes at what point an FPU
		is connected so that it can collect
		information."
	::= { s5TrFpuEntry 3 }

s5TrFpuTypeIndx OBJECT-TYPE
	SYNTAX	INTEGER (0..255)
	ACCESS	read-only
	STATUS	mandatory
	DESCRIPTION
		"The index of the cluster or port
		that the FPU is associated with. The
		object s5TrFpuType type specifies the
		type."
	::= { s5TrFpuEntry 4 }

s5TrFpuVer OBJECT-TYPE
	SYNTAX	DisplayString (SIZE(0..32))
	ACCESS	read-only
	STATUS	obsolete
	DESCRIPTION
		"The version of the FPU. If not available,
		then the value is a zero length string."
	::= { s5TrFpuEntry 5 }

s5TrFpuCapabilites OBJECT-TYPE
	SYNTAX	INTEGER {
		other(1),
		coreStatistics(2),
		embeddedManagement(3)
		}
	ACCESS	read-only
	STATUS	mandatory
	DESCRIPTION
		"The capabilities of the FPU.

		The values are:
		  other (1)...............Other or unknown
		  coreStatistics(2).......Core statistics FPU
		  embeddedManagement(3)...FPU capable of core
		                            statistics and roving;
		                            both features are
		                            mutually exclusive."
	::= { s5TrFpuEntry 6 }

s5TrFpuRunningMode OBJECT-TYPE
	SYNTAX	INTEGER {
		other(1),
		coreStatistics(2),
		rovingFPU(4),
		securityRoving(5)
		}
	ACCESS	read-write
	STATUS	mandatory
	DESCRIPTION
		"The running mode of the FPU. These values
		are for both read and write with the exception
		of other(1) which is for read only.

		The values are:
		  other(1).......................Other or unknown
		  coreStatistics(2)..............FPU running in core
		                                   statistics mode.
		  roving(4)......................FPU running in roving mode;
		                                   Note: core statistics is
		                                   unavailable in this mode.
		  securityRoving(5)..............FPU running in roving mode
		                                   due to authorized nodes
		                                   security being turned on."
	::= { s5TrFpuEntry 7 }



-- Token Ring Extensions to the Chassis MIB


s5TrAttTable OBJECT-TYPE
	SYNTAX	SEQUENCE OF S5TrAttEntry
	ACCESS	not-accessible
	STATUS	mandatory
	DESCRIPTION
		"A table containing information about each
		Token Ring attachment point on a board. This
		table extends table s5ChasAttTable for Token
		Ring Boards."
	::= { s5TrCfg 3 }

s5TrAttEntry OBJECT-TYPE
	SYNTAX	S5TrAttEntry
	ACCESS	not-accessible
	STATUS	mandatory
	DESCRIPTION
		"A row in Token Ring attachment table. Entries
		can not be created or deleted via SNMP."
	INDEX	{ s5TrAttBrdIndx,
		  s5TrAttIndx }
	::= { s5TrAttTable 1 }

S5TrAttEntry ::= SEQUENCE {
	s5TrAttBrdIndx INTEGER,
	s5TrAttIndx INTEGER,
	s5TrAttDfltSpeed INTEGER,
	s5TrAttCurSpeed INTEGER,
	s5TrAttFault INTEGER
	}

s5TrAttBrdIndx OBJECT-TYPE
	SYNTAX	INTEGER (1..255)
	ACCESS	read-only
	STATUS	mandatory
	DESCRIPTION
		"The index of the board. This corresponds to
		the index of the slot containing the board."
	::= { s5TrAttEntry 1 }

s5TrAttIndx OBJECT-TYPE
	SYNTAX	INTEGER (1..255)
	ACCESS	read-only
	STATUS	mandatory
	DESCRIPTION
		"The index of the attachment point on the board."
	::= { s5TrAttEntry 2 }

s5TrAttDfltSpeed OBJECT-TYPE
	SYNTAX	INTEGER {
		other(1),
		s4Mbit(2),
		s16Mbit(3)
		}
	ACCESS	read-only
	STATUS	mandatory
	DESCRIPTION
		"The default speed setting for the attachment
		point. The values are:
		  other(1).....unknown or other speed
		  s4Mbit(2)....4Mbit
		  s16Mbit(3)...16Mbit"
	::= { s5TrAttEntry 3 }

s5TrAttCurSpeed OBJECT-TYPE
	SYNTAX	INTEGER {
		other(1),
		s4Mbit(2),
		s16Mbit(3)
		}
	ACCESS	read-write
	STATUS	mandatory
	DESCRIPTION
		"The current speed setting for the attachment
		point. The read-only value is:
		  other(1).....unknown or other speed

		The read-write values are:
		  s4Mbit(2)....4Mbit
		  s16Mbit(3)...16Mbit"
	::= { s5TrAttEntry 4 }

s5TrAttFault OBJECT-TYPE
	SYNTAX	INTEGER {
		other(1),
		nofault(2),
		fault(3)
		}
	ACCESS	read-only
	STATUS	mandatory
	DESCRIPTION
		"A fault indicator for the attachment point.
		The values are:
		  other(1).....not connected to a backplane network
		                 or value is unknown
		  nofault(2)...no fault detected
		  fault(3).....fault detected."
	::= { s5TrAttEntry 5 }

s5TrBkDiv OBJECT-TYPE
	SYNTAX	INTEGER {
		other(1),
		split(2),
		join(3)
		}
	ACCESS	read-write
	STATUS	mandatory
	DESCRIPTION
		"Setting of the Token Ring backplane divider.
		The value that can only be read is:
		  other(1)...unknown or other state

		Values that can be read and written are:
		  split(2)...split the backplane
		  join(3)....join the backplane"
	::= { s5TrCfg 4 }



-- Ring Extension Table

s5TrRingExt OBJECT IDENTIFIER ::=  { s5TrCfg 5 }

-- Ring Extension Table Highlight

s5TrRingExtLastChange OBJECT-TYPE
	SYNTAX	TimeTicks
	ACCESS	read-only
	STATUS	mandatory
	DESCRIPTION
		"The value of sysUpTime when the last change
		of any Ring Extension table entry within the 
		chassis was detected."
	::= { s5TrRingExt 1}

s5TrRingExtCurNum OBJECT-TYPE
	SYNTAX	INTEGER (0..65535)
	ACCESS	read-only
	STATUS	mandatory
	DESCRIPTION
		"The current number of entries in the Ring
		Extension Table."
	::= { s5TrRingExt 2 }

-- Ring Extension Table Details

s5TrRingExtTable OBJECT-TYPE
	SYNTAX	SEQUENCE OF S5TrRingExtEntry
	ACCESS	not-accessible
	STATUS	mandatory
	DESCRIPTION
		"A table containing information about each
		RI/RO (Ring In / Ring Out) pair on a board. 
		The number of entries is determined by the 
		number of existing RI/RO pairs. Those boards 
		that do not have any RI/RO do not have any 
		entries in this table."
	::= { s5TrRingExt 3 }

s5TrRingExtEntry OBJECT-TYPE
	SYNTAX	S5TrRingExtEntry
	ACCESS	not-accessible
	STATUS	mandatory
	DESCRIPTION
		"A row in the Ring Extension table.
		Entries can not be created or deleted via
		SNMP."
	INDEX { s5TrRingExtBoardIndx,
		s5TrRingExtExtensionIndx }
	::= { s5TrRingExtTable 1 }

S5TrRingExtEntry ::= SEQUENCE {
	s5TrRingExtBoardIndx 		INTEGER,
	s5TrRingExtExtensionIndx 	INTEGER,
	s5TrRingExtRingNumber 		INTEGER,
	s5TrRingExtRingInUna 		MacAddress,
	s5TrRingExtRingOutUna 		MacAddress,
	s5TrRingExtSecUna 		MacAddress,
	s5TrRingExtRingInPhanStatus 	INTEGER,
	s5TrRingExtRingOutPhanStatus 	INTEGER,
	s5TrRingExtRingInWrapStatus 	INTEGER,
	s5TrRingExtRingOutWrapStatus 	INTEGER,
	s5TrRingExtClusterNumber 	INTEGER,
	s5TrRingExtRingInPortNumber 	INTEGER,
	s5TrRingExtRingOutPortNumber 	INTEGER
	}

s5TrRingExtBoardIndx OBJECT-TYPE
	SYNTAX	INTEGER (1..255)
	ACCESS	read-only
	STATUS	mandatory
	DESCRIPTION
		"The index of the board which has RI/RO.
		This corresponds to the index of the slot 
		containing the board."
	::= { s5TrRingExtEntry 1 }

s5TrRingExtExtensionIndx OBJECT-TYPE
	SYNTAX	INTEGER (1..255)
	ACCESS	read-only
	STATUS	mandatory
	DESCRIPTION
		"The index of the RI/RO extension pair 
		on the board. The value ranges between 1 
		and the number of RI/RO pairs on the board."
	::= { s5TrRingExtEntry 2 }

s5TrRingExtRingNumber OBJECT-TYPE
	SYNTAX	INTEGER (0..4095)
	ACCESS	read-only
	STATUS	mandatory
	DESCRIPTION
		"The logical ring number of the ring
		that RI/RO connects to." 
	::= { s5TrRingExtEntry 3 }

s5TrRingExtRingInUna OBJECT-TYPE
	SYNTAX	MacAddress
	ACCESS	read-only
	STATUS	mandatory
	DESCRIPTION
		"The upstream neighbor address to the 
		Ring In port."
	::= { s5TrRingExtEntry 4 }

s5TrRingExtRingOutUna OBJECT-TYPE
	SYNTAX	MacAddress	
	ACCESS	read-only
	STATUS	mandatory
	DESCRIPTION
		"The upstream neighbor address to the 
		Ring Out port."
	::= { s5TrRingExtEntry 5 }

s5TrRingExtSecUna OBJECT-TYPE
	SYNTAX	MacAddress	
	ACCESS	read-only
	STATUS	mandatory
	DESCRIPTION
		"The (secondary) upstream neighbor 
		address as read by the FPU that is
		located between RI and RO."
	::= { s5TrRingExtEntry 6 }

s5TrRingExtRingInPhanStatus OBJECT-TYPE
	SYNTAX	INTEGER	{
		other(1),
		noPhantom(2),
		phantom(3)
		}
	ACCESS	read-only
	STATUS	mandatory
	DESCRIPTION
		"The phantom status of the Ring In port.  
		The values are:
		  other(1).........status unknown
		  noPhantom(2).....no phantom signal
		  phantom(3).......phantom signal is on."
	::= { s5TrRingExtEntry 7 }

s5TrRingExtRingOutPhanStatus OBJECT-TYPE
	SYNTAX	INTEGER	{
		other(1),
		noPhantom(2),
		phantom(3)
		}
	ACCESS	read-only
	STATUS	mandatory
	DESCRIPTION
		"The phantom status of the Ring Out port.  
		The values are:
		  other(1).........status unknown
		  noPhantom(2).....no phantom signal
		  phantom(3).......phantom signal is on."
	::= { s5TrRingExtEntry 8 }

s5TrRingExtRingInWrapStatus OBJECT-TYPE
	SYNTAX	INTEGER	{
		other(1),
		wrap(2),
		connect(3)
		}
	ACCESS	read-only
	STATUS	mandatory
	DESCRIPTION
		"The wrap status of the Ring-In port.
		The values are:
		  other(1)............wrap status unknown
		  wrap(2).............port is wrapped
		  connect(3)..........port is unwrapped"
	::= { s5TrRingExtEntry 9 }

s5TrRingExtRingOutWrapStatus OBJECT-TYPE
	SYNTAX	INTEGER	{
		other(1),
		wrap(2),
		connect(3)
		}
	ACCESS	read-only
	STATUS	mandatory
	DESCRIPTION
		"The wrap status of the Ring-Out port.
		The values are:
		  other(1)............wrap status unknown
		  wrap(2).............port is wrapped
		  connect(3)..........port is unwrapped"
	::= { s5TrRingExtEntry 10 }

s5TrRingExtClusterNumber OBJECT-TYPE
	SYNTAX	INTEGER (1..255)
	ACCESS	read-only
	STATUS	mandatory
	DESCRIPTION
		"The cluster number where RI/RO pair is 
		located on the board."
	::= { s5TrRingExtEntry 11 }

s5TrRingExtRingInPortNumber OBJECT-TYPE
	SYNTAX	INTEGER (1..255)
	ACCESS	read-only
	STATUS	mandatory
	DESCRIPTION
		"The port number where RI is located on 
		the board."
	::= { s5TrRingExtEntry 12 }

s5TrRingExtRingOutPortNumber OBJECT-TYPE
	SYNTAX	INTEGER (1..255)
	ACCESS	read-only
	STATUS	mandatory
	DESCRIPTION
		"The port number where RO is located on
		the board."
	::= { s5TrRingExtEntry 13 }



-- Encoded Octet Strings for Ring Extension Table

s5TrRingExtEosSize OBJECT-TYPE
	SYNTAX	INTEGER (0..1400)
	ACCESS	read-only
	STATUS	mandatory
	DESCRIPTION
		"The current size of a 'row' in the table
		s5TrRingExtEosTable. This allows applications
		to be able to break apart 'rows' in the table."
	::= { s5TrRingExt 4 }

s5TrRingExtEosTable OBJECT-TYPE
	SYNTAX	SEQUENCE OF S5TrRingExtEosEntry
	ACCESS	not-accessible
	STATUS	mandatory
	DESCRIPTION
		"A table of encoded octet strings of
		entries in table s5TrRingExtTable.
		The number of entries is determined by the
		packing of 'rows' from s5TrRingExtTable."
	::= { s5TrRingExt 5 }

s5TrRingExtEosEntry OBJECT-TYPE
	SYNTAX	S5TrRingExtEosEntry
	ACCESS	not-accessible
	STATUS	mandatory
	DESCRIPTION
		"A row in the table of encoded octet
		strings for table s5TrRingExtTable.
		Instance returned in Response PDU:
		  On GETs: instance specified is the
		           instance returned.
		  On GET-NEXTs: instance returned is the
		                instance of the last record
		                contained in the octet string.
		Entries in the table can not be created
		or deleted via SNMP."
	INDEX { s5TrRingExtBoardIndx,
 		s5TrRingExtExtensionIndx }
	::= { s5TrRingExtEosTable 1 }

S5TrRingExtEosEntry ::= SEQUENCE {
	s5TrRingExtEos OCTET STRING
	}

s5TrRingExtEos OBJECT-TYPE
	SYNTAX	OCTET STRING (SIZE(0..1400))
	ACCESS	read-only
	STATUS	mandatory
	DESCRIPTION
		"An encoded octet string. On reads it contains
		an integral number of 'rows' from table
		s5TrRingExtTable. All 'rows' are the same size
		which is defined by object s5TrRingExtEosSize."
	::= { s5TrRingExtEosEntry 1 }



-- SECTION 3: Statistics


-- Basic Statistics Table

s5TrBStatTable OBJECT-TYPE
	SYNTAX	SEQUENCE OF S5TrBStatEntry
	ACCESS	not-accessible
	STATUS	mandatory
	DESCRIPTION
		"A table containing Token Ring basic
		statistics. The entries in the table
		may come from several different data
		sources including FPUs (Frame Processing
		Units) and MACs on NMMs (Network Management
		Modules). The number of entries is
		determined by the number of sources
		that can provide the information."
	::= { s5TrStat 1 }

s5TrBStatEntry OBJECT-TYPE
	SYNTAX	S5TrBStatEntry
	ACCESS	not-accessible
	STATUS	mandatory
	DESCRIPTION
		"A row in Token Ring basic statistics
		table. Entries can not be created or
		deleted via SNMP."
	INDEX	{ s5TrBStatSrcIndx }
	::= { s5TrBStatTable 1 }

S5TrBStatEntry ::= SEQUENCE {
	s5TrBStatSrcIndx SrcIndx,

	s5TrBStatTtlOctets Counter,
	s5TrBStatMacOctets Counter,
	s5TrBStatLlcOctets Counter,

	s5TrBStatTtlFrms Counter,
	s5TrBStatTtlGoodFrms Counter,
	s5TrBStatTtlBadFrms Counter,

	s5TrBStatMacFrms Counter,
	s5TrBStatLlcFrms Counter,
	s5TrBStatLlcNonUcastFrms Counter,
	s5TrBStatLlcUcastFrms Counter,

	s5TrBStatGoodErrReportFrms Counter,
	s5TrBStatBeaconFrms Counter,
	s5TrBStatRingPurgeFrms Counter,
	s5TrBStatClaimTokenFrms Counter,

	s5TrBStatUna MacAddress
	}

s5TrBStatSrcIndx OBJECT-TYPE
	SYNTAX	SrcIndx
	ACCESS	read-only
	STATUS	mandatory
	DESCRIPTION
		"The index of the entry in the table.
		This index identifies the source of the
		information. Only those sources that provide
		these statistics are in this table."
	::= { s5TrBStatEntry 1 }

s5TrBStatTtlOctets OBJECT-TYPE
	SYNTAX	Counter
	ACCESS	read-only
	STATUS	mandatory
	DESCRIPTION
		"The total number of octets of data in LLC
		frames and MAC frames (including frames with
		errors) measured on the ring (excluding
		framing bits, but including FCS octets)."
	::= { s5TrBStatEntry 2 }

s5TrBStatMacOctets OBJECT-TYPE
	SYNTAX	Counter
	ACCESS	read-only
	STATUS	mandatory
	DESCRIPTION
		"The total number of octets of data in MAC
		frames (including frames with errors) measured
		on the ring (excluding framing bits,
		but including FCS octets)."
	::= { s5TrBStatEntry 3 }

s5TrBStatLlcOctets OBJECT-TYPE
	SYNTAX	Counter
	ACCESS	read-only
	STATUS	mandatory
	DESCRIPTION
		"The total number of octets of data in LLC
		frames (including frames with errors) measured
		on the ring (excluding framing bits,
		but including FCS octets)."
	::= { s5TrBStatEntry 4 }

s5TrBStatTtlFrms OBJECT-TYPE
	SYNTAX	Counter
	ACCESS	read-only
	STATUS	mandatory
	DESCRIPTION
		"The total number of LLC frames and MAC
		frames (including frames with errors)
		detected on the ring."
	::= { s5TrBStatEntry 5 }

s5TrBStatTtlGoodFrms OBJECT-TYPE
	SYNTAX	Counter
	ACCESS	read-only
	STATUS	mandatory
	DESCRIPTION
		"The total number of LLC frames and MAC
		frames (excluding frames with errors)
		detected on the ring."
	::= { s5TrBStatEntry 6 }

s5TrBStatTtlBadFrms OBJECT-TYPE
	SYNTAX	Counter
	ACCESS	read-only
	STATUS	mandatory
	DESCRIPTION
		"The total number of LLC frames and MAC
		frames with errors detected on the ring."
	::= { s5TrBStatEntry 7 }

s5TrBStatMacFrms OBJECT-TYPE
	SYNTAX	Counter
	ACCESS	read-only
	STATUS	mandatory
	DESCRIPTION
		"The total number of MAC frames (including frames
		with errors) detected on the ring."
	::= { s5TrBStatEntry 8 }

s5TrBStatLlcFrms OBJECT-TYPE
	SYNTAX	Counter
	ACCESS	read-only
	STATUS	mandatory
	DESCRIPTION
		"The total number of LLC frames (including
		frames with errors) detected on the ring."
	::= { s5TrBStatEntry 9 }

s5TrBStatLlcNonUcastFrms OBJECT-TYPE
	SYNTAX	Counter
	ACCESS	read-only
	STATUS	mandatory
	DESCRIPTION
		"The total number of LLC frames (including
		frames with errors) detected on the ring
		that were directed to a LLC broadcast address
		(i.e., 0xFFFFFFFFFFFF or 0xC000FFFFFFFF) or
		a local or global multicast or functional
		address (i.e., 0xC000xxxxxxxx)."
	::= { s5TrBStatEntry 10 }

s5TrBStatLlcUcastFrms OBJECT-TYPE
	SYNTAX	Counter
	ACCESS	read-only
	STATUS	mandatory
	DESCRIPTION
		"The total number of LLC frames (including
		frames with errors) detected on the ring
		that were directed to a LLC unicast address."
	::= { s5TrBStatEntry 11 }

s5TrBStatGoodErrReportFrms OBJECT-TYPE
	SYNTAX	Counter
	ACCESS	read-only
	STATUS	mandatory
	DESCRIPTION
		"The total number of Soft error Report frames
		(excluding frames with errors) detected on
		the ring."
	::= { s5TrBStatEntry 12 }

s5TrBStatBeaconFrms OBJECT-TYPE
	SYNTAX	Counter
	ACCESS	read-only
	STATUS	mandatory
	DESCRIPTION
		"The total number of Beacon frames (including
		frames with errors) detected on the ring."
	::= { s5TrBStatEntry 13 }

s5TrBStatRingPurgeFrms OBJECT-TYPE
	SYNTAX	Counter
	ACCESS	read-only
	STATUS	mandatory
	DESCRIPTION
		"The total number of Ring Purge frames (including
		frames with errors) detected on the ring."
	::= { s5TrBStatEntry 14 }

s5TrBStatClaimTokenFrms OBJECT-TYPE
	SYNTAX	Counter
	ACCESS	read-only
	STATUS	mandatory
	DESCRIPTION
		"The total number of Claim Token frames (including
		frames with errors) detected on the ring."
	::= { s5TrBStatEntry 15 }

s5TrBStatUna OBJECT-TYPE
	SYNTAX	MacAddress
	ACCESS	read-only
	STATUS	mandatory
	DESCRIPTION
		"The MAC address of the next active upstream
		neighbor (NAUN) (or upstream neighbor address (UNA))
		of the ring monitoring source. If it is unknown
		or at power reset (for example, no activity on the
		ring), the value is 00:00:00:00:00:00. The old
		value of the NAUN will be held, even if the ring
		becomes inactive (i.e., it will not clear to zero
		after no activity)."
	::= { s5TrBStatEntry 16 }



-- Frame Size Statistics Table


s5TrFStatTable OBJECT-TYPE
	SYNTAX	SEQUENCE OF S5TrFStatEntry
	ACCESS	not-accessible
	STATUS	obsolete
	DESCRIPTION
		"A table containing Token Ring frame
		size distribution statistics. These
		statistics are for LLC frames.
		Counters for frames and octets can
		be found in the basic statistics table.
		The entries in this table may come from
		several different data sources.
		The number of entries is determined
		by the number of sources that can
		provide the information."
	::= { s5TrStat 2 }

s5TrFStatEntry OBJECT-TYPE
	SYNTAX	S5TrFStatEntry
	ACCESS	not-accessible
	STATUS	obsolete
	DESCRIPTION
		"A row in Token Ring frame size
		distribution statistics table.
		Entries can not be created or deleted
		via SNMP."
	INDEX	{ s5TrFStatSrcIndx }
	::= { s5TrFStatTable 1 }

S5TrFStatEntry ::= SEQUENCE {
	s5TrFStatSrcIndx SrcIndx,
	s5TrFStatDropEvents Counter,
	s5TrFStatLlcFrms18to63Octets Counter,
	s5TrFStatLlcFrms64to127Octets Counter,
	s5TrFStatLlcFrms128to255Octets Counter,
	s5TrFStatLlcFrms256to511Octets Counter,
	s5TrFStatLlcFrms512to1023Octets Counter,
	s5TrFStatLlcFrms1024to2047Octets Counter,
	s5TrFStatLlcFrms2048to4095Octets Counter,
	s5TrFStatLlcFrms4096to8191Octets Counter,
	s5TrFStatLlcFrms8192to18000Octets Counter,
	s5TrFStatLlcFrmsGreaterThan18000Octets Counter
	}

s5TrFStatSrcIndx OBJECT-TYPE
	SYNTAX	SrcIndx
	ACCESS	read-only
	STATUS	obsolete
	DESCRIPTION
		"The index of the entry in the table.
		This index identifies the source of the
		information. Only those sources that provide
		these statistics are in this table."
	::= { s5TrFStatEntry 1 }

s5TrFStatDropEvents OBJECT-TYPE
	SYNTAX	Counter
	ACCESS	read-only
	STATUS	obsolete
	DESCRIPTION
		"The total number of events in which frames
		were dropped by the data source due to
		lack of resources.

		Note that this number is not necessarily the
		number of frames dropped; it is just the number
		of times this condition has been detected."
	::= { s5TrFStatEntry 2 }

s5TrFStatLlcFrms18to63Octets OBJECT-TYPE
	SYNTAX	Counter
	ACCESS	read-only
	STATUS	obsolete
	DESCRIPTION
		"The total number of LLC frames (excluding
		frames with errors) measured on the ring
		that were between 18 and 63 octets in
		length inclusive, excluding framing bits
		but including FCS octets."
	::= { s5TrFStatEntry 3 }

s5TrFStatLlcFrms64to127Octets OBJECT-TYPE
	SYNTAX	Counter
	ACCESS	read-only
	STATUS	obsolete
	DESCRIPTION
		"The total number of LLC frames (excluding
		frames with errors) measured on the ring
		that were between 64 and 127 octets in
		length inclusive, excluding framing bits
		but including FCS octets."
	::= { s5TrFStatEntry 4 }

s5TrFStatLlcFrms128to255Octets OBJECT-TYPE
	SYNTAX	Counter
	ACCESS	read-only
	STATUS	obsolete
	DESCRIPTION
		"The total number of LLC frames (excluding
		frames with errors) measured on the ring
		that were between 128 and 255 octets in
		length inclusive, excluding framing bits
		but including FCS octets."
	::= { s5TrFStatEntry 5 }

s5TrFStatLlcFrms256to511Octets OBJECT-TYPE
	SYNTAX	Counter
	ACCESS	read-only
	STATUS	obsolete
	DESCRIPTION
		"The total number of LLC frames (excluding
		frames with errors) measured on the ring
		that were between 256 and 511 octets in
		length inclusive, excluding framing bits
		but including FCS octets."
	::= { s5TrFStatEntry 6 }

s5TrFStatLlcFrms512to1023Octets OBJECT-TYPE
	SYNTAX	Counter
	ACCESS	read-only
	STATUS	obsolete
	DESCRIPTION
		"The total number of LLC frames (excluding
		frames with errors) measured on the ring
		that were between 512 and 1023 octets in
		length inclusive, excluding framing bits
		but including FCS octets."
	::= { s5TrFStatEntry 7 }

s5TrFStatLlcFrms1024to2047Octets OBJECT-TYPE
	SYNTAX	Counter
	ACCESS	read-only
	STATUS	obsolete
	DESCRIPTION
		"The total number of LLC frames (excluding
		frames with errors) measured on the ring
		that were between 1024 and 2047 octets in
		length inclusive, excluding framing bits
		but including FCS octets."
	::= { s5TrFStatEntry 8 }

s5TrFStatLlcFrms2048to4095Octets OBJECT-TYPE
	SYNTAX	Counter
	ACCESS	read-only
	STATUS	obsolete
	DESCRIPTION
		"The total number of LLC frames (excluding
		frames with errors) measured on the ring
		that were between 2048 and 4095 octets in
		length inclusive, excluding framing bits
		but including FCS octets."
	::= { s5TrFStatEntry 9 }

s5TrFStatLlcFrms4096to8191Octets OBJECT-TYPE
	SYNTAX	Counter
	ACCESS	read-only
	STATUS	obsolete
	DESCRIPTION
		"The total number of LLC frames (excluding
		frames with errors) measured on the ring
		that were between 4096 and 8191 octets in
		length inclusive, excluding framing bits
		but including FCS octets."
	::= { s5TrFStatEntry 10 }

s5TrFStatLlcFrms8192to18000Octets OBJECT-TYPE
	SYNTAX	Counter
	ACCESS	read-only
	STATUS	obsolete
	DESCRIPTION
		"The total number of LLC frames (excluding
		frames with errors) measured on the ring
		that were between 8192 and 18000 octets in
		length inclusive, excluding framing bits
		but including FCS octets."
	::= { s5TrFStatEntry 11 }

s5TrFStatLlcFrmsGreaterThan18000Octets OBJECT-TYPE
	SYNTAX	Counter
	ACCESS	read-only
	STATUS	obsolete
	DESCRIPTION
		"The total number of LLC frames (excluding
		frames with errors) measured on the ring
		that were greater than 18000 octets in
		length, excluding framing bits but
		including FCS octets."
	::= { s5TrFStatEntry 12 }



-- Error Statistics Table

s5TrEStatTable OBJECT-TYPE
	SYNTAX	SEQUENCE OF S5TrEStatEntry
	ACCESS	not-accessible
	STATUS	mandatory
	DESCRIPTION
		"A table containing Token Ring error
		statistics. The entries in the table
		may come from several different data
		sources. The number of entries is
		determined by the number of sources
		that can provide the information. (For
		example, this table is valid only on NMMs
		when they have become a Ring Error Monitor
		(REM)."
	::= { s5TrStat 3 }

s5TrEStatEntry OBJECT-TYPE
	SYNTAX	S5TrEStatEntry
	ACCESS	not-accessible
	STATUS	mandatory
	DESCRIPTION
		"A row in Token Ring error statistics table.
		Entries can not be created or deleted via
		SNMP."
	INDEX	{ s5TrEStatSrcIndx }
	::= { s5TrEStatTable 1 }

S5TrEStatEntry ::= SEQUENCE {
	s5TrEStatSrcIndx SrcIndx,
	s5TrEStatDropEvents Counter,
	s5TrEStatLineErrs Counter,
	s5TrEStatInternalErrs Counter,
	s5TrEStatBurstErrs Counter,
	s5TrEStatACErrs Counter,
	s5TrEStatAbortErrs Counter,
	s5TrEStatLostFrameErrs Counter,
	s5TrEStatCongestionErrs Counter,
	s5TrEStatFrameCopiedErrs Counter,
	s5TrEStatFrequencyErrs Counter,
	s5TrEStatTokenErrs Counter,
	s5TrEStatSoftErrFrms Counter
	}

s5TrEStatSrcIndx OBJECT-TYPE
	SYNTAX	SrcIndx
	ACCESS	read-only
	STATUS	mandatory
	DESCRIPTION
		"The index of the entry in the table.
		This index identifies the source of the
		information. Only those sources that provide
		these statistics are in this table."
	::= { s5TrEStatEntry 1 }

s5TrEStatDropEvents OBJECT-TYPE
	SYNTAX	Counter
	ACCESS	read-only
	STATUS	obsolete
	DESCRIPTION
		"Total number of events in which frames
		were dropped by the data source due to
		lack of resources.

		Note that this number is not necessarily the
		number of frames dropped; it is just the number
		of times this condition has been detected."
	::= { s5TrEStatEntry 2 }

s5TrEStatLineErrs OBJECT-TYPE
	SYNTAX	Counter
	ACCESS	read-only
	STATUS	mandatory
	DESCRIPTION
		"Total number of line errors reported by
		all stations in error report frames
		and detected on the ring.
		Section 3.8.1 of IEEE 802.5 specification."
	::= { s5TrEStatEntry 3 }

s5TrEStatInternalErrs OBJECT-TYPE
	SYNTAX	Counter
	ACCESS	read-only
	STATUS	mandatory
	DESCRIPTION
		"Total number of adapter internal errors
		reported by all stations in error report
		frames and detected on the ring.
		Section 3.8.2 of IEEE 802.5 specification."
	::= { s5TrEStatEntry 4 }

s5TrEStatBurstErrs OBJECT-TYPE
	SYNTAX	Counter
	ACCESS	read-only
	STATUS	mandatory
	DESCRIPTION
		"Total number of burst errors reported by
		all stations in error report frames
		and detected on the ring.
		Section 3.8.3 of IEEE 802.5 specification."
	::= { s5TrEStatEntry 5 }

s5TrEStatACErrs OBJECT-TYPE
	SYNTAX	Counter
	ACCESS	read-only
	STATUS	mandatory
	DESCRIPTION
		"Total number of AC (Address Copied) errors
		reported by all stations in error report frames
		and detected on the ring.
		Section 3.8.4 of IEEE 802.5 specification."
	::= { s5TrEStatEntry 6 }

s5TrEStatAbortErrs OBJECT-TYPE
	SYNTAX	Counter
	ACCESS	read-only
	STATUS	mandatory
	DESCRIPTION
		"Total number of abort delimiter transmitted
		errors reported by all stations in error report
		frames and detected on the ring.
		Section 3.8.5 of IEEE 802.5 specification."
	::= { s5TrEStatEntry 7 }

s5TrEStatLostFrameErrs OBJECT-TYPE
	SYNTAX	Counter
	ACCESS	read-only
	STATUS	mandatory
	DESCRIPTION
		"Total number of frames lost errors reported
		by all stations in error report frames
		and detected on the ring.
		Section 3.8.6 of IEEE 802.5 specification."
	::= { s5TrEStatEntry 8 }

s5TrEStatCongestionErrs OBJECT-TYPE
	SYNTAX	Counter
	ACCESS	read-only
	STATUS	mandatory
	DESCRIPTION
		"Total number of receive congestion errors
		reported by all stations in error report
		frames and detected on the ring.
		Section 3.8.7 of IEEE 802.5 specification."
	::= { s5TrEStatEntry 9 }

s5TrEStatFrameCopiedErrs OBJECT-TYPE
	SYNTAX	Counter
	ACCESS	read-only
	STATUS	mandatory
	DESCRIPTION
		"Total number of frame copied errors reported
		by all stations in error report frames
		and detected on the ring.
		Section 3.8.8 of IEEE 802.5 specification."
	::= { s5TrEStatEntry 10 }

s5TrEStatFrequencyErrs OBJECT-TYPE
	SYNTAX	Counter
	ACCESS	read-only
	STATUS	mandatory
	DESCRIPTION
		"Total number of frequency errors reported by
		all stations in error report frames
		and detected on the ring.
		Section 3.8.9 of IEEE 802.5 specification."
	::= { s5TrEStatEntry 11 }

s5TrEStatTokenErrs OBJECT-TYPE
	SYNTAX	Counter
	ACCESS	read-only
	STATUS	mandatory
	DESCRIPTION
		"Total number of token errors reported by
		all stations in error report frames
		and detected on the ring.
		Section 3.8.10 of IEEE 802.5 specification."
	::= { s5TrEStatEntry 12 }

s5TrEStatSoftErrFrms OBJECT-TYPE
	SYNTAX	Counter
	ACCESS	read-only
	STATUS	mandatory
	DESCRIPTION
		"Total number of error report frames detected
		on the ring. (Note: this has the same count
		as object s5TrBStatGoodErrReportFrms.)"
	::= { s5TrEStatEntry 13 }


-- Port Information Table

s5TrPortInfoTable OBJECT-TYPE
	SYNTAX	SEQUENCE OF S5TrPortInfoEntry
	ACCESS	not-accessible
	STATUS	mandatory
	DESCRIPTION
		"A table containing information for each managed 
		token ring connectivity port on a board, excluding 
		ring in, ring out, and those used as cascade expansion.
		The number of entries is determined by
		the number of manageable ports and the number 
		of occupied slots in s5ChasComTable whose 
		s5ChasComType is of a token Ring type and
		 is on the same backplane ring as the NMM interface."
	::= { s5TrCfg 6 }

s5TrPortInfoEntry OBJECT-TYPE
	SYNTAX	S5TrPortInfoEntry
	ACCESS	not-accessible
	STATUS	mandatory
	DESCRIPTION
		"A row in the port information table.
   		  Entries can not be created or
       		   deleted via SNMP."
	INDEX	{ s5TrPortInfoSrcIndx,
		  s5TrPortInfoBrdIndx,
		  s5TrPortInfoPortIndx }
	::= { s5TrPortInfoTable 1 }

S5TrPortInfoEntry ::= SEQUENCE {
	s5TrPortInfoSrcIndx SrcIndx,
	s5TrPortInfoBrdIndx INTEGER,
	s5TrPortInfoPortIndx INTEGER,
	s5TrPortInfoAddr MacAddress,
	s5TrPortInfoLastNaun MacAddress,
	s5TrPortInfoStationStatus INTEGER,
	s5TrPortInfoFirstEnterTime TimeTicks,
	s5TrPortInfoLastEnterTime TimeTicks,
	s5TrPortInfoLastExitTime TimeTicks,
	s5TrPortInfoDupAddrErrs Counter,
	s5TrPortInfoLineErrs Counter,
	s5TrPortInfoInternalErrs Counter,
	s5TrPortInfoBurstErrs Counter,
	s5TrPortInfoACErrs Counter,
	s5TrPortInfoAbortErrs Counter,
	s5TrPortInfoLostFrameErrs Counter,
	s5TrPortInfoCongestionErrs Counter,
	s5TrPortInfoFrameCopiedErrs Counter,
	s5TrPortInfoFrequencyErrs Counter,
	s5TrPortInfoTokenErrs Counter,
	s5TrPortInfoBeaconErrs Counter,
	s5TrPortInfoInsertions Counter
	}

s5TrPortInfoSrcIndx OBJECT-TYPE
	SYNTAX	SrcIndx
	ACCESS	read-only
	STATUS	mandatory
	DESCRIPTION
		"This index identifies the source of the
		information. Only those sources that provide
		these statistics are in this table."
	::= { s5TrPortInfoEntry 1 }

s5TrPortInfoBrdIndx OBJECT-TYPE
	SYNTAX	INTEGER
	ACCESS	read-only
	STATUS	mandatory
	DESCRIPTION
		"The index of the board. This corresponds to 
		the index of the slot containing the board."
	::= { s5TrPortInfoEntry 2 }

s5TrPortInfoPortIndx OBJECT-TYPE
	SYNTAX	INTEGER
	ACCESS	read-only
	STATUS	mandatory
	DESCRIPTION
	       "The index of the port on the board. 
	        Its value ranges between 1 and the 
		number of manageable ports on the board."
	::= { s5TrPortInfoEntry 3 }

s5TrPortInfoAddr OBJECT-TYPE
	SYNTAX	MacAddress
	ACCESS	read-only
	STATUS	mandatory
	DESCRIPTION
		"The MAC address of the station currently/last
		 attached to the port.
		 If no station in the ring can be found 
		 attached to the port, the address should be 0"
	::= { s5TrPortInfoEntry 4 }

s5TrPortInfoLastNaun OBJECT-TYPE
	SYNTAX	MacAddress
	ACCESS	read-only
	STATUS	mandatory
	DESCRIPTION
		"The MAC address of the last known NAUN (Next
		Active Upstream Neighbor) of the station 
		currently/last  attached to the port."
	::= { s5TrPortInfoEntry 5 }

s5TrPortInfoStationStatus OBJECT-TYPE
	SYNTAX	INTEGER {
		active(1),
		notInRingPoll(2),
		inactive(3),
		forcedRemoval(4)
		}
	ACCESS	read-only
	STATUS	mandatory
	DESCRIPTION
		"The insertion status of the station currently/last
		attached to the port. The values are:
		  active(1)..........Actively participating in
		                       ring poll from this port
		  notInRingPoll(2)...Detected on the ring, but
		                       not currently participating
		                       in the ring poll from this port
		  inactive(3)........ No  longer on the ring
				 from this port
		  forcedRemoval(4)... forced off the ring from this port 
				by network management."
		                     
				  
	::= { s5TrPortInfoEntry 6 }

s5TrPortInfoFirstEnterTime OBJECT-TYPE
	SYNTAX	TimeTicks
	ACCESS	read-only
	STATUS	mandatory
	DESCRIPTION
		"The value of sysUpTime when this port first time 
		entered the ring. 
		If the time is unknown, the value shall be zero."
	::= { s5TrPortInfoEntry 7 }

s5TrPortInfoLastEnterTime OBJECT-TYPE
	SYNTAX	TimeTicks
	ACCESS	read-only
	STATUS	mandatory
	DESCRIPTION
		"The value of sysUpTime when this port last time entered 
		the ring.
		 If the time is unknown, the value shall be zero."
	::= { s5TrPortInfoEntry 8 }

s5TrPortInfoLastExitTime OBJECT-TYPE
	SYNTAX	TimeTicks
	ACCESS	read-only
	STATUS	mandatory
	DESCRIPTION
		"The value of sysUpTime when this port last 
		exited the ring. 
		If the time is unknown, the value shall be zero."
	::= { s5TrPortInfoEntry 9 }

s5TrPortInfoDupAddrErrs OBJECT-TYPE
	SYNTAX	Counter
	ACCESS	read-only
	STATUS	mandatory
	DESCRIPTION
		"Total number of duplicate address error 
		detected from this port."
	::= { s5TrPortInfoEntry 10}

s5TrPortInfoLineErrs OBJECT-TYPE
	SYNTAX	Counter
	ACCESS	read-only
	STATUS	mandatory
	DESCRIPTION
		"Total number of line errors detected 
		from this port."
	::= { s5TrPortInfoEntry 11 }

s5TrPortInfoInternalErrs OBJECT-TYPE
	SYNTAX	Counter
	ACCESS	read-only
	STATUS	mandatory
	DESCRIPTION
		"Total number of adapter internal errors
		detected from  this port. "
	::= { s5TrPortInfoEntry 12 }

s5TrPortInfoBurstErrs OBJECT-TYPE
	SYNTAX	Counter
	ACCESS	read-only
	STATUS	mandatory
	DESCRIPTION
		"Total number of burst errors detected 
		from this port. "
	::= { s5TrPortInfoEntry 13 }

s5TrPortInfoACErrs OBJECT-TYPE
	SYNTAX	Counter
	ACCESS	read-only
	STATUS	mandatory
	DESCRIPTION
		"Total number of AC (Address Copied) 
		errors detected from this port. "
	::= { s5TrPortInfoEntry 14 }

s5TrPortInfoAbortErrs OBJECT-TYPE
	SYNTAX	Counter
	ACCESS	read-only
	STATUS	mandatory
	DESCRIPTION
		"Total number of abort delimiter 
		transmitted errors detected from this port."
	::= { s5TrPortInfoEntry 15 }

s5TrPortInfoLostFrameErrs OBJECT-TYPE
	SYNTAX	Counter
	ACCESS	read-only
	STATUS	mandatory
	DESCRIPTION
		"Total number of lost frame errors detected
		from this port. "
	::= { s5TrPortInfoEntry 16 }

s5TrPortInfoCongestionErrs OBJECT-TYPE
	SYNTAX	Counter
	ACCESS	read-only
	STATUS	mandatory
	DESCRIPTION
		"Total number of receive congestion errors
		detected from this port ."
	::= { s5TrPortInfoEntry 17 }

s5TrPortInfoFrameCopiedErrs OBJECT-TYPE
	SYNTAX	Counter
	ACCESS	read-only
	STATUS	mandatory
	DESCRIPTION
		"Total number of frame copied errors detected
		from this port."
	::= { s5TrPortInfoEntry 18 }

s5TrPortInfoFrequencyErrs OBJECT-TYPE
	SYNTAX	Counter
	ACCESS	read-only
	STATUS	mandatory
	DESCRIPTION
		"Total number of frequency errors detected
		from this port."
	::= { s5TrPortInfoEntry 19 }

s5TrPortInfoTokenErrs OBJECT-TYPE
	SYNTAX	Counter
	ACCESS	read-only
	STATUS	mandatory
	DESCRIPTION
		"Total number of token errors detected
		from this port."
	::= { s5TrPortInfoEntry 20 }

s5TrPortInfoBeaconErrs OBJECT-TYPE
	SYNTAX	Counter
	ACCESS	read-only
	STATUS	mandatory
	DESCRIPTION
		"Total number of beacon frames detected 
		from this port."
	::= { s5TrPortInfoEntry 21 }

s5TrPortInfoInsertions OBJECT-TYPE
	SYNTAX	Counter
	ACCESS	read-only
	STATUS	mandatory
	DESCRIPTION
		"Total number of times that the port
		was detected inserting into the ring."
	::= { s5TrPortInfoEntry 22 }


-- Port FPU Statistics table

s5TrPortFpuStatsTable OBJECT-TYPE
	SYNTAX	SEQUENCE OF S5TrPortFpuStatsEntry
	ACCESS	not-accessible
	STATUS	mandatory
	DESCRIPTION
		"A table containing FPU statistics 
		information for each managed token ring
		connectivity port on a board. "
	::= { s5TrCfg 7 }

s5TrPortFpuStatsEntry OBJECT-TYPE
	SYNTAX	S5TrPortFpuStatsEntry
	ACCESS	not-accessible
	STATUS	mandatory
	DESCRIPTION
		"A row in the Port FPU statistics table.
		Entries can not be created or deleted via SNMP. "
	INDEX	{ s5TrPortFpuStatsBrdIndx,
		  s5TrPortFpuStatsPortIndx }
	::= { s5TrPortFpuStatsTable 1 }

S5TrPortFpuStatsEntry ::= SEQUENCE {
	s5TrPortFpuStatsBrdIndx INTEGER,
	s5TrPortFpuStatsPortIndx INTEGER,
	s5TrPortFpuStatsAddr MacAddress,
	s5TrPortFpuStatsTxOctets Counter,
	s5TrPortFpuStatsTxPkts  Counter,
	s5TrPortFpuStatsRxOctets Counter,
	s5TrPortFpuStatsRxPkts Counter
	}


s5TrPortFpuStatsBrdIndx OBJECT-TYPE
	SYNTAX	INTEGER (1..255)
	ACCESS	read-only
	STATUS	mandatory
	DESCRIPTION
		"The index of the board. This corresponds to
		the index of the slot containing the board."
	::= { s5TrPortFpuStatsEntry 1 }

s5TrPortFpuStatsPortIndx OBJECT-TYPE
	SYNTAX	INTEGER (1..255)
	ACCESS	read-only
	STATUS	mandatory
	DESCRIPTION
		"The index of the port on the board. The
		value ranges between 1 and the number
		of manageable ports on the board."
	::= { s5TrPortFpuStatsEntry 2 }


s5TrPortFpuStatsAddr OBJECT-TYPE
	SYNTAX	MacAddress
	ACCESS	read-only
	STATUS	mandatory
	DESCRIPTION
		"The MAC address of the station currently/last 
		 attached to the port.
		For ring in, ring out and cascade expansion ports, 
		this MAC address is the UNA (Upstream Neighbor
		Address) as seen by the port.
		If no station has ever been connected to this port, 
		the address should be zero."
	::= { s5TrPortFpuStatsEntry 3 }


s5TrPortFpuStatsTxOctets OBJECT-TYPE
	SYNTAX	Counter
	ACCESS	read-only
	STATUS	mandatory
	DESCRIPTION
		"Total number of octets transmitted at this port.
		 If no station is connected to the port, 
		 the counter should return the last collected value."
	::= { s5TrPortFpuStatsEntry 4 }

s5TrPortFpuStatsTxPkts OBJECT-TYPE
	SYNTAX	Counter
	ACCESS	read-only
	STATUS	mandatory
	DESCRIPTION
		"Total number of packets transmitted at this port.
		 If no station is connected to the port, 
		 the counter should return the last collected value."
	::= { s5TrPortFpuStatsEntry 5 }

s5TrPortFpuStatsRxOctets OBJECT-TYPE
	SYNTAX	Counter
	ACCESS	read-only
	STATUS	mandatory
	DESCRIPTION
		"Total number of octets received at this port.
		 If no station is connected to the port, 
		 the counter should return the last collected value."
	::= { s5TrPortFpuStatsEntry 6 }

s5TrPortFpuStatsRxPkts OBJECT-TYPE
	SYNTAX	Counter
	ACCESS	read-only
	STATUS	mandatory
	DESCRIPTION
		"The number of packets receive at this port.
		 If no station is connected to the port, 
		 the counter should return the last collected value."
	::= { s5TrPortFpuStatsEntry 7 }

END
-- SECTION 1: Top Level Definitions

SYNOPTICS-RMON-EXT-MIB DEFINITIONS ::= BEGIN


-- SynOptics RMON Extensions MIB Release 1.0.7
-- Revision 09/05/97

-- Copyright 1995 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.

---------------------------------------------------
-- This MIB was originally part of the rmonx107.mib
---------------------------------------------------


-- Imports

IMPORTS
	OBJECT-TYPE
		FROM RFC-1212
	products
		FROM SYNOPTICS-ROOT-MIB;

-- Textual Conventions

-- A textual convention for TimeFilter index used in the
-- snpxMatrixSDBulkTable.


-- RMON Extensions  Groups
snpxRmonExt		OBJECT IDENTIFIER ::= { products 8 }

snpxRmonGetTabExt       OBJECT IDENTIFIER ::= { snpxRmonExt 6 }


-- Get Table Definition
 
 
getTable    OBJECT IDENTIFIER ::= { snpxRmonGetTabExt 1 }
 
getTableTable OBJECT-TYPE
    SYNTAX  SEQUENCE OF GetTableEntry
    ACCESS  not-accessible
    STATUS  mandatory
    DESCRIPTION
        "A table of bulk GetTable entries. These entries consist of a
        header followed by several rows from the SNMP table being
        requested."
    ::= { getTable 1 }
 
getTableEntry OBJECT-TYPE
    SYNTAX  GetTableEntry
    ACCESS  not-accessible
    STATUS  mandatory
    DESCRIPTION
        "A row in the table of bulk entries for getTableTable."
    INDEX { getTableSource, getTableIndex }
    ::= { getTableTable 1 }
 
GetTableEntry ::= SEQUENCE {
        getTableSource OBJECT IDENTIFIER,
        getTableIndex  OBJECT IDENTIFIER,
        getTableData   OCTET STRING
    }
 
getTableSource OBJECT-TYPE
    SYNTAX  OBJECT IDENTIFIER
    ACCESS  not-accessible
    STATUS  mandatory
    DESCRIPTION
        "A length encoded object identifier for the SNMP table to
        retrieve. For example, the RMON2 alMatrixSD table is identified
        as the OID number 9.1.3.6.1.2.1.16.17.1, where the first 9 is
        the length of the OID."
    ::= { getTableEntry 1 }
 
getTableIndex OBJECT-TYPE
    SYNTAX  OBJECT IDENTIFIER
    ACCESS  not-accessible
    STATUS  mandatory
    DESCRIPTION
        "A length encoded object identifier consisting of the source
        table's normal index values as they are specified in the MIB
        definition for the table. Each index value is preceded by a flag
        that indicates whether the index is fixed(1) or dynamic(2).
 
        When returning table rows, the agent only increments index
        values that are dynamic(2). Any index that is fixed(1) remains
        constant for the entire set of rows returned.
 
        For the initial get request, dynamic index values are set to
        zero. It is up to the agent to determine the first value to use.
        On all subsequent requests, the request OID is the one returned
        in the response."
    ::= { getTableEntry 2 }
 
getTableData OBJECT-TYPE
    SYNTAX  OCTET STRING (SIZE(0..1200))
    ACCESS  read-only
    STATUS  mandatory
    DESCRIPTION
        "The OCTET STRING consists of a header followed by a set of data
        records. The header consists of the information:
            response packet version number (1) [Integer16]
            data record encoding -- BER (1), BigEndian(2) [Integer16]
            agent sysUpTime value [TimeTicks]
            number of records in this response [Integer32]
        The data records consist of each dynamic index for this row plus
        each row entry defined in the source table's MIB definition."
    ::= { getTableEntry 3 }
 
END
-- SECTION 1: Top Level Definitions


RAPIDCITY-VLAN-MIB DEFINITIONS ::= BEGIN


-- Rapid City VLAN MIB Release 0.0.0
-- Revision 11/25/97

-- Copyright 1997 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.

-- This MIB contains the Rapid City VLAN MIB with minor
-- adaptations for the C100/5000BH environment


-- Imports

-- %%% replace and add more
IMPORTS
	OBJECT-TYPE
	    FROM RFC-1212
    DisplayString, RowStatus, MacAddress, TruthValue
        FROM SNMPv2-TC-v1
    InterfaceIndex
        FROM IF-MIB
    enterprises, IpAddress
        FROM RFC1155-SMI;


-- Groups

-- These two belong somewhere else if we use other RC MIBs
rapidcity			OBJECT IDENTIFIER ::= { enterprises 2272 }
rapidcityfoo		OBJECT IDENTIFIER ::= { rapidcity 1 }

rcVlan              OBJECT IDENTIFIER ::= { rapidcityfoo 3 }


-- SECTION 2: VLAN Group
--
-- The VLAN group contains information pertaining to all
-- VLANs in the system.
--
-- The remainder of this file is pasted from Rapid City documents

-- VLAN Table

rcVlanNumVlans OBJECT-TYPE
	SYNTAX	      INTEGER (1..128)
        ACCESS        read-only
        STATUS        mandatory
        DESCRIPTION   "Number of VLANs currently defined"
        ::= { rcVlan 1 }

rcVlanTable OBJECT-TYPE
        SYNTAX        SEQUENCE OF RcVlanEntry
        ACCESS        not-accessible
        STATUS        mandatory
        DESCRIPTION   "A list of Virtual LAN entries.  VLAN 1 is the default."
        ::= { rcVlan 2 }

rcVlanEntry OBJECT-TYPE
        SYNTAX        RcVlanEntry
        ACCESS        not-accessible
        STATUS        mandatory
        DESCRIPTION   "Entry containing information for a particular
                      Virtual LAN."
        INDEX         { rcVlanId }
        ::= { rcVlanTable 1 }

RcVlanEntry ::= SEQUENCE {
		rcVlanId INTEGER,
		rcVlanName DisplayString,
		rcVlanColor INTEGER,
		rcVlanHighPriority TruthValue,
		rcVlanRoutingEnable TruthValue,
		rcVlanIfIndex InterfaceIndex,
		rcVlanAction INTEGER,
		rcVlanResult INTEGER,
		rcVlanStgId INTEGER,
		rcVlanType INTEGER,
		rcVlanPortMembers OCTET STRING,
		rcVlanPotentialMembers OCTET STRING,
		rcVlanStaticMembers OCTET STRING,
		rcVlanNotAllowToJoin OCTET STRING,
		rcVlanProtocolId INTEGER,
		rcVlanSubnetAddr IpAddress,
		rcVlanSubnetMask IpAddress,
                rcVlanAgingTime  INTEGER,
		rcVlanMacAddress MacAddress,
		rcVlanRowStatus RowStatus
	}

rcVlanId OBJECT-TYPE
        SYNTAX        INTEGER (1..4095)
        ACCESS        read-only
        STATUS        mandatory
        DESCRIPTION   "A value that uniquely identifies the Virtual LAN 
                      associated with this entry.  This value correspond
		      to the lower 12 bits in the IEEE VLAN field."
        ::= { rcVlanEntry 1 }

rcVlanName OBJECT-TYPE
	SYNTAX	      DisplayString (SIZE (0..20))
	ACCESS 	      read-write
	STATUS 	      mandatory
	DESCRIPTION   "VLAN Name"
	::= { rcVlanEntry 2 }

rcVlanColor OBJECT-TYPE
        SYNTAX        INTEGER (0..32)
        ACCESS        read-write
        STATUS        mandatory
        DESCRIPTION   "Color  assigned to this VLAN.  The color
		      is a proprietary number scheme used by
                      the DM to associate an integer value with a
                      particular color.  The color  is treated
                      transparently in the device." 
        ::= { rcVlanEntry 3 }

rcVlanHighPriority OBJECT-TYPE
        SYNTAX 	      TruthValue
        ACCESS 	      read-write
        STATUS 	      mandatory
        DESCRIPTION   "Control whether this VLAN should be given 
                      high priority."
	DEFVAL 	      { false }
        ::= { rcVlanEntry 4 }

rcVlanRoutingEnable OBJECT-TYPE
        SYNTAX 	      TruthValue
        ACCESS 	      read-write
        STATUS 	      mandatory
        DESCRIPTION   "Control whether routing should be enabled on this 
                      VLAN." 
	DEFVAL	      { false }
        ::= { rcVlanEntry 5 }

rcVlanIfIndex OBJECT-TYPE
        SYNTAX        InterfaceIndex 
        ACCESS        read-only
        STATUS        mandatory
        DESCRIPTION   "If rcVlanRoutingEnable is set to TRUE, then this
                      value will indicate the 'logical' ifIndex that is
                      assigned to this VLAN.  Otherwise, this value is
                      meaningless and should be set to zero."
        ::= { rcVlanEntry 6 }

rcVlanAction OBJECT-TYPE
        SYNTAX        INTEGER {
                         none(1),          -- none of the following
		         flushMacFdb(2),   -- flush MAC forwarding table
		         flushArp(3),	   -- flush ARP table
		         flushIp(4),	   -- flush IP route table
		         flushDynMemb(5),  -- flush Dynamic Members
                         all(6)		   -- flush all tables 
                      }
        ACCESS        read-write
        STATUS        mandatory
        DESCRIPTION   "Vlan related actions."
        DEFVAL        { none }
        ::= { rcVlanEntry 7 }

rcVlanResult OBJECT-TYPE
        SYNTAX        INTEGER {
                         none(1),        -- none of the following
                         inProgress(2),  -- in progress
                         success(3),     -- success
                         fail(4)         -- failure
                      }
        ACCESS        read-only
        STATUS        mandatory
        DESCRIPTION   "Result from the last Vlan action."
        DEFVAL        { none }
        ::= { rcVlanEntry 8 }

rcVlanStgId OBJECT-TYPE
        SYNTAX        INTEGER (0..128)
        ACCESS        read-write
        STATUS        mandatory
        DESCRIPTION   "Used to indicate the spanning tree group this
                      VLAN is associated it.  If this vlan is not
                      be associated with any spanning tree group, this
                      value should be set to zero(0)."
        DEFVAL        { 1 }
        ::= { rcVlanEntry 9 }

rcVlanType OBJECT-TYPE
        SYNTAX        INTEGER {
                         byPort(1),       -- VLAN by Port 
                         byIpSubnet(2),   -- VLAN by IP subnet 
                         byProtocolId(3), -- VLAN by Protocol Id
		         bySrcMac(4),	  -- VLAN by Src MAC address
		         byDstMcast(5)	  -- VLAN by Dst MultiCast
                      }
        ACCESS        read-write
        STATUS        mandatory
        DESCRIPTION   "Used to indicate the type of VLAN."
        ::= { rcVlanEntry 10 }

rcVlanPortMembers OBJECT-TYPE
        SYNTAX        OCTET STRING (SIZE(32))
        ACCESS        read-write
        STATUS        mandatory
        DESCRIPTION   "A bitfield used to identify which ports in the
                      system are members (static or dynamic) to this
                      VLAN.
 
                      The bitfield is 32 octets long representing
                      ports 0 to 255 (inclusive)."
        ::= { rcVlanEntry 11 }
 
rcVlanPotentialMembers OBJECT-TYPE
        SYNTAX        OCTET STRING (SIZE(32))
        ACCESS        read-write
        STATUS        mandatory
        DESCRIPTION   "A bitfield used to identify which ports in the
                      system are potential members to join this VLAN. 
 
                      The bitfield is 32 octets long representing
                      ports 0 to 255 (inclusive)."
        ::= { rcVlanEntry 12 }
 
rcVlanStaticMembers OBJECT-TYPE
        SYNTAX        OCTET STRING (SIZE(32))
        ACCESS        read-write
        STATUS        mandatory
        DESCRIPTION   "A bitfield used to identify how ports are 
		      members of this VLAN.

                      A one(1) value in a bit means the port is a
                      static member of this VLAN.  A zero(0) value 
		      in a bit means the port is a dynamic member 
		      of this VLAN.

                      The bitfield is 32 octets long representing
                      ports 0 to 255 (inclusive)."
        ::= { rcVlanEntry 13 }

rcVlanNotAllowToJoin OBJECT-TYPE
        SYNTAX        OCTET STRING (SIZE(32))
        ACCESS        read-write
        STATUS        mandatory
        DESCRIPTION   "A bitfield used to identify which ports are not
                      allowed to join this VLAN.
                          
                      A one(1) value in a bit means the port is not
                      allowed to join a VLAN.  A zero(0) value in a bit
                      means the port is allowed to join a VLAN.
 
                      The bitfield is 32 octets long representing
                      ports 0 to 255 (inclusive)."
        ::= { rcVlanEntry 14 }

rcVlanProtocolId OBJECT-TYPE
        SYNTAX        INTEGER {
		         none(0),
		         ip(1),
                         ipx802dot3(2),
                         ipx802dot2(3),
                         ipxSnap(4),
                         ipxEthernet2(5),
                         appleTalk(6),
                         decLat(7),
                         decOther(8),
                         sna802dot2(9),
                         snaEthernet2(10),
                         netBios(11),
                         xns(12)
	              }
        ACCESS        read-write
        STATUS        mandatory
        DESCRIPTION   "The protocol id of this VLAN.  This value 
		      is meaningful only if 'rcVlanType' is equal to 
                      'byProtocolId'."
        ::= { rcVlanEntry 15 }

rcVlanSubnetAddr OBJECT-TYPE
        SYNTAX        IpAddress
        ACCESS        read-write
        STATUS        mandatory
        DESCRIPTION   "The IP subnet address of this VLAN.  This value 
		      is meaningful only if 'rcVlanType' is equal to 
                      'byIpSubnet'."
        ::= { rcVlanEntry 16 }

rcVlanSubnetMask OBJECT-TYPE
        SYNTAX        IpAddress
        ACCESS        read-write
        STATUS        mandatory
        DESCRIPTION   "The IP subnet mask of this VLAN.  This value
		      is meaningful only if 'rcVlanType' is equal to 
		      'byIpSubnet'."
        ::= { rcVlanEntry 17 }

rcVlanAgingTime OBJECT-TYPE
        SYNTAX        INTEGER (10..1000000)
        ACCESS        read-write
        STATUS        mandatory
        DESCRIPTION   "The timeout period in seconds for aging out
                      dynamic members of policy-based VLANs."
        DEFVAL        { 600 }
        ::= { rcVlanEntry 18 }

rcVlanMacAddress OBJECT-TYPE
        SYNTAX        MacAddress
        ACCESS        read-only
        STATUS        mandatory
        DESCRIPTION   "The MAC address assigned to this VLAN.
		      This field is only relevant when the VLAN
		      is configured for routing."
        ::= { rcVlanEntry 19 }

rcVlanRowStatus OBJECT-TYPE
	SYNTAX 	      RowStatus
	ACCESS 	      read-write
	STATUS 	      mandatory
	DESCRIPTION   "Used to create/delete entries"
	::= { rcVlanEntry 20 }


END
-- SECTION 1: Top Level Definitions
 
REMOTE-LOGIN-TRAP-MIB DEFINITIONS ::= BEGIN
 
 
-- Copyright 1998 Bay Networks, Inc.
-- All rights reserved.
-- This Bay Networks SNMP Management Information Base Specification
-- (Specification) embodies Bay Networks' confidential and
-- proprietary intellectual property. Bay Networks retains all
-- title and ownership in the Specification, including any
-- revisions.
 
-- This Specification is supplied "AS IS," and Bay Networks makes
-- no warranty, either express or implied, as to the use,
-- operation, condition, or performance of the Specification.
 
 
-- Imports
  
IMPORTS
      TRAP-TYPE   FROM RFC-1215
      remoteLoginTrap   FROM S5-ROOT-MIB
		s5AgRemoteLoginIp, s5AgRemoteLoginStatus FROM S5-AGENT-MIB;
  
  
-- SECTION 2: Remote login traps definitions
  
  
remoteLoginStatus  TRAP-TYPE
     ENTERPRISE  remoteLoginTrap
     VARIABLES   { s5AgRemoteLoginIp,
                  s5AgRemoteLoginStatus }
--   STATUS      mandatory
     DESCRIPTION
         " This trap is sent when someone login via telnet. 
           The status of login and the host ip are reported together."
     ::= 1

END

-- SECTION 1: Top Level Definitions




CENTILLION-ROOT-MIB DEFINITIONS ::= BEGIN


-- Centillion Root MIB Release 2.1.7
-- Revision 8/01/00

-- Copyright 1994-00 Nortel Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	enterprises			FROM RFC1155-SMI
	DisplayString			FROM RFC1213-MIB
	Counter32			FROM SNMPv2-SMI-v1
	OBJECT-TYPE			FROM RFC-1212;


-- Textual Conventions

--
-- All MIBs within this domain use the following textual convention
-- to describe the status of an entry in a row.
--

StatusIndicator ::=
	INTEGER {
		valid(1),
		invalid(2)
	}

-- This type is used to specify a concentrator backplane.

SsBackplaneType ::=
	INTEGER {
		other(1),		-- none of the following
		atmBus(2)		-- ATM Bus
	}

-- This type is used to specify the switch chassis.

SsChassisType ::=
	INTEGER {
		other(1),	-- none of the following
		six-slot(2),	-- 6 slot Chassis
		twelve-slot(3),	-- 12 slot Chassis
		workgroup(4),	-- Workgroup chassis (single slot)
                three-slotC50N(5),  -- 3 slot C50N Chassis
		three-slotC50T(6),  -- 3 slot C50T Chassis
		six-slotBH5005(7)   -- 6 slot BH5005 Chassis
	}

-- This type is used to specify a mother card module.
-- NOTE: this module type is OBSELETE and should not be 
--       supported in any new development. USE the
--       s5000 registration MIB instead.
SsModuleType ::=
	INTEGER {
		empty(1),		-- nothing installed
		other(2),		-- none of the following
		mTR4PC(3),		-- Token-Ring Module (4 port)
		mTRMCP4PC(4),		-- MCP with Token-Ring (4 port) Card
		mATM(5),		-- ATM 2-port Multi Mode Fiber
		mTRFiber(6),		-- Token-Ring Fiber Module
		mTRMCPFiber(7),		-- MCP Token-Ring Fiber
		mEther16PC10BT(8),	-- Ethernet Module (16 port) 10 BaseT
		mEtherMCP8PC10BT(9),	-- MCP Ethernet 8 port 10 BaseT
		mATM2PSMFiber(10),	-- ATM 2-port Single Mode Fiber
		mATM2PCopper(11),	-- ATM 2-port Copper
		mATM4PMMFiber(12),	-- ATM 4-port Multi Mode Fiber
		mATM4PSMFiber(13),	-- ATM 4-port Single Mode Fiber
		mATM4PCopper(14),	-- ATM 4-port Copper
		mATMMCP2PSMFiber(15),	-- ATM MCP 2-port Single Mode Fiber
		mATMMCP2PMMFiber(16),	-- ATM MCP 2-port Multi Mode Fiber
		mATMMCP2PCopper(17),	-- ATM MCP 2-port Copper
		mATMMCP4PSMFiber(18),	-- ATM MCP 4-port Single Mode Fiber
		mATMMCP4PMMFiber(19),	-- ATM MCP 4-port Multi Mode Fiber
		mATMMCP4PCopper(20),	-- ATM MCP 4-port Copper
		mATM2PC(21),		-- ATM 2-port card
		mATM4PC(22),		-- ATM 4-port card
		mATMMCP2PC(23),		-- ATM MCP 2-port card
		mATMMCP4PC(24),		-- ATM MCP 4-port card
        	mEther16P10BT100BTCopper(25), -- Ethernet 16 port (14 10MB, 2 10/100MB)
        	mEther14P10BT100BF(26), -- Ethernet 14 port (12 10MB, 2 100MB)
        	mEther8P10BF(27),	-- Ethernet 8 port 10BF
		mEther10P10BT100BT(28),	-- Ethernet 10 port (8 10MB, 2 10/100MB)
		mEther16P10BT100BTMixed(29),	-- Ethernet 10 port (8 10MB, 2 10/100MB)
		mEther10P10BT100BTMIX(30),	-- Ethernet 10 port (8 10MB, 2 10/100MB)
		mEther12PBFL(32),	-- 5324 12 Port BFL Enet Switch Module
		mEther16P4x4(33),	-- 5455 Ethernet 4x4 bank switching
                mTRMCP8PC(34),          -- 8 port Copper Token-Ring MCP
		mTR8PC(35),             -- 8 port UTP TokenSpeed Card
                mEther24PC(36),         -- 5328HD 24 port slave 10Mb 
		mEther24P10BT100BT(37),	-- 5625 Enet 24 port 10/100Mb
		mEther24P100BFx(38),	-- 5424 Enet 24 port 100BaseFx
                mTR8PFiber(39),         -- 5524 8 port TR Fiber
                mATM4PMDA(40),          -- 5720 4 port ATM MDA 
                mATMMCP4PMDA(41),       -- 5720M 4 port ATM MDA MCP 
                mEther4P100BT(42),      -- 5425 4 port Ethernet 100Mb 
		mTR24PC(43),		-- Token-Ring Module 24 port
		mTR16PC(44),		-- Token-Ring Module 16 port
		mATMMCP1PSMFiber(45),	-- ATM MCP 1-port Single Mode Fiber
		mATMMCP1PMMFiber(46),	-- ATM MCP 1-port Multi Mode Fiber
		mATM1PMMFiber(47),	-- ATM 1-port Multi Mode Fiber
		mATM1PVNR(48),		-- BH 5782 VNR 5000BH i int. OC3 port
		mEther24P10BT100BTx(49),   -- 5625H Enet 24 port 10/100Mb
		mEther24P100BFX(50)     -- 5424H Enet 24 port 100BaseFx
	}

SsMediaType ::=
	INTEGER {
		mediaUnkown(1),		-- none of the following
		mediaTokenRing(2),
		mediaFDDI(3),
		mediaEthernet(4),
		mediaATM(5)
	}
		

-- All representations of MAC addresses in this MIB Module
-- use, as a textual convention (i.e. this convention does
-- not affect their encoding), the data type:
 
MacAddress ::= OCTET STRING (SIZE (6))  -- a 6 octet address in
                                        -- the "canonical" order
-- defined by IEEE 802.1a, i.e., as if it were transmitted
-- least significant bit first, even though 802.5 (in
-- contrast to other 802.x protocols) requires MAC addresses
-- to be transmitted most significant bit first.
--
-- 16-bit addresses, if needed, are represented by setting
-- their upper 4 octets to all 0's, i.e., AAFF would be
-- represented as 00000000AAFF.

-- Represents a boolean value.
 
Boolean ::= INTEGER { true(1), false(2) }
 
-- Represents a single bit field.
 
BitField ::= INTEGER { clear(1), set(2) }
 
-- Port Identifier

PortId ::= INTEGER (1..65535)

-- Card Identifier

CardId ::= INTEGER (1..16)

-- System failure status indication type

FailIndicator ::= INTEGER { on(1), off(2) }


EnableIndicator ::= INTEGER { disabled(1), enabled(2) }


-- Top Branches under "centillion"

centillion		OBJECT IDENTIFIER ::=	{ enterprises 930 }

cnProducts		OBJECT IDENTIFIER ::=	{ centillion 1 }
proprietary		OBJECT IDENTIFIER ::=	{ centillion 2 }
extensions		OBJECT IDENTIFIER ::=	{ centillion 3 }
cnTemporary		OBJECT IDENTIFIER ::=	{ centillion 4 }



-- Branches under "proprietary"

cnSystem		OBJECT IDENTIFIER ::=	{ proprietary 1 }
cnATM			OBJECT IDENTIFIER ::=	{ proprietary 2 }

sysChassis		OBJECT IDENTIFIER ::=	{ cnSystem 1 }
sysConfig		OBJECT IDENTIFIER ::=	{ cnSystem 2 }
sysMonitor		OBJECT IDENTIFIER ::=	{ cnSystem 3 }
sysTrap                 OBJECT IDENTIFIER ::=   { cnSystem 4 }
sysEvtLogMgmt	OBJECT IDENTIFIER ::=	{ cnSystem 5 }
 
atmConfig		OBJECT IDENTIFIER ::=	{ cnATM 1 }
atmMonitor		OBJECT IDENTIFIER ::=	{ cnATM 2 }
--
-- LAN Emulation Extentions
--
atmLane         	OBJECT IDENTIFIER ::=   { cnATM 3 }

-- Centillion SONET/SDH MIB
--
atmSonet        	OBJECT IDENTIFIER ::=   { cnATM 4 }

--
-- Centillion unique traps
--
sysMcpRedundTrap        OBJECT IDENTIFIER ::=   {sysTrap 1}
cnPvcTraps              OBJECT IDENTIFIER ::=   {sysTrap 2}



-- Branches under "cnProducts"

-- These object identifiers are for use as values for sysObjectId.

cnCentillion100		OBJECT IDENTIFIER ::=	{ cnProducts 1 }
cnIBM8251		OBJECT IDENTIFIER ::=	{ cnProducts 2 }
cnBayStack301           OBJECT IDENTIFIER ::=   { cnProducts 3 }
cn5000BH-MCP            OBJECT IDENTIFIER ::=   { cnProducts 4 }
cnCentillion50N         OBJECT IDENTIFIER ::=   { cnProducts 5 }
cnCentillion50T         OBJECT IDENTIFIER ::=   { cnProducts 6 }
cn5005BH-MCP            OBJECT IDENTIFIER ::=   { cnProducts 7 }




-- SECTION 2: System Group
--
-- This section contains system level information.
-- System Chassis information 
--
-- Implementation of this group is mandatory for all Centillion agents.

chassisType OBJECT-TYPE
	SYNTAX	SsChassisType
	ACCESS	read-only
	STATUS	mandatory
	DESCRIPTION
		"The chassis type."
	::= { sysChassis 1 }

chassisBkplType OBJECT-TYPE
	SYNTAX	SsBackplaneType
	ACCESS	read-only
	STATUS	mandatory
	DESCRIPTION
		"The chassis backplane type."
	::= { sysChassis 2 }

chassisPs1FailStatus OBJECT-TYPE
	SYNTAX	FailIndicator
	ACCESS	read-only
	STATUS	mandatory
	DESCRIPTION
		"Power supply 1 failure indicator. A value of on (1)
		indicates a failure on power supply 1."
	::= { sysChassis 3 }

chassisPs2FailStatus OBJECT-TYPE
	SYNTAX	FailIndicator
	ACCESS	read-only
	STATUS	mandatory
	DESCRIPTION
		"Power supply 2 failure indicator. A value of on (1)
		indicates a failure on power supply 2."
	::= { sysChassis 4 }

chassisFanFailStatus OBJECT-TYPE
	SYNTAX	FailIndicator
	ACCESS	read-only
	STATUS	mandatory
	DESCRIPTION
		"System chassis fan failure indicator. A value of on (1)
		indicates a failure on one or both of the system fans."
	::= { sysChassis 5 }

chassisSerialNumber OBJECT-TYPE
	SYNTAX	OCTET STRING (SIZE (3))
	ACCESS	read-only
	STATUS	mandatory
	DESCRIPTION
		"Chassis serial number."
	::= { sysChassis 6 }

chassisPartNumber OBJECT-TYPE
	SYNTAX	OCTET STRING (SIZE (6))
	ACCESS	read-only
	STATUS	mandatory
	DESCRIPTION
		"Chassis part number."
	::= { sysChassis 7 }
	

-- Chassis Slot Configuration Table

-- This table contains information about the modules currently inserted in
-- the chassis. The information and configuration contained here is common
-- for all modules.

slotConfigTable OBJECT-TYPE
	SYNTAX	SEQUENCE OF SlotConfigEntry
	ACCESS	not-accessible
	STATUS	mandatory
	DESCRIPTION
		"The chassis slot configuration table."
	::= { sysChassis 9 }

slotConfigEntry OBJECT-TYPE
	SYNTAX	SlotConfigEntry
	ACCESS	not-accessible
	STATUS	mandatory
	DESCRIPTION
		"What type of module is in each slot of the chassis."
	INDEX	{ slotNumber }
	::= { slotConfigTable 1 }


SlotConfigEntry ::= SEQUENCE {
	slotNumber
		INTEGER,
	slotModuleType
		SsModuleType,
	slotModuleSerialNumber
		OCTET STRING,
	slotModuleHwVer
		OCTET STRING,
	slotModuleSwVer
		DisplayString,
	slotModuleStatus
		INTEGER,
	slotModuleLeds
		OCTET STRING,
	slotModuleReset
		INTEGER,
	slotConfigDelete
		Boolean,
	slotConfigMediaType
		SsMediaType,
        slotModuleMaxRAM
                INTEGER,
        slotModuleInstalledRAM
                INTEGER,
        slotModuleFlashSize
                INTEGER,
        slotModuleProductImageId
                INTEGER,
	slotModuleBaseMacAddress
		MacAddress,
        slotLastResetEPC
		Counter32,
        slotLastResetCause
		Counter32,
        slotLastResetVirtualAddress
		Counter32,
        slotLastResetTimeStamp
		Counter32,
	slotConfigAdd
		Boolean,
	slotConfigExtClockSource
		INTEGER,
	slotConfigTrafficShapingRate
		INTEGER
	}

slotNumber OBJECT-TYPE
	SYNTAX	INTEGER
	ACCESS	read-only
	STATUS	mandatory
	DESCRIPTION
		"The chassis slot number. Valid entries are system dependent
		based on the chassis type."
	::= { slotConfigEntry 1 }

slotModuleType OBJECT-TYPE
	SYNTAX	SsModuleType
	ACCESS	read-only
	STATUS	deprecated	-- 08/07/98
	DESCRIPTION
		"Module type."
	::= { slotConfigEntry 2 }

slotModuleHwVer OBJECT-TYPE
	SYNTAX	OCTET STRING (SIZE (6))
	ACCESS	read-only
	STATUS	mandatory
	DESCRIPTION
		"The hardware revision of the module."
	::= { slotConfigEntry 3 }

slotModuleSerialNumber OBJECT-TYPE
	SYNTAX	OCTET STRING (SIZE (3))
	ACCESS	read-only
	STATUS	mandatory
	DESCRIPTION
		"Module serial number. Format is 3 BCD digits."
	::= { slotConfigEntry 4 }

slotModuleSwVer OBJECT-TYPE
	SYNTAX	DisplayString
	ACCESS	read-only
	STATUS	mandatory
	DESCRIPTION
		"The software revision of the module."
	::= { slotConfigEntry 5 }

slotModuleStatus OBJECT-TYPE
	SYNTAX	INTEGER {
		ok(1),		-- good status
		fail(2)		-- bad status
		}
	ACCESS	read-only
	STATUS	mandatory
	DESCRIPTION
		"This indicates the operational status of the module."
	::= { slotConfigEntry 6 }

slotModuleLeds OBJECT-TYPE
	SYNTAX	OCTET STRING
	ACCESS	read-only
	STATUS	mandatory
	DESCRIPTION
		"Status of the module LEDs. Each LED bank is encoded
		in four	bits (nibble), one bit for each LED. The least 
		significant bit of each nibble represents the bottom LED
		of each bank. The first octet in the string, as read from 
		left to right represents the first LED banks."
	::= { slotConfigEntry 7 }

slotModuleReset OBJECT-TYPE
	SYNTAX	INTEGER {
		noReset(1),	-- not resetting
		reset(2)	-- resetting
		}
	ACCESS	read-write
	STATUS	mandatory
	DESCRIPTION
		"This indicates the reset state of the module. Writing with 
		the value reset (2) will reset the module."
	::= { slotConfigEntry 8 }

slotConfigDelete OBJECT-TYPE
	SYNTAX	Boolean
	ACCESS	read-write
	STATUS	mandatory
	DESCRIPTION
		"Setting this object causes the configuration of the
		slot to be deleted. When read, this object has a value
		of false(2)."
	::= { slotConfigEntry 9 }

slotConfigMediaType OBJECT-TYPE
	SYNTAX	SsMediaType
	ACCESS	read-only
	STATUS	mandatory
	DESCRIPTION
		"The configured card media type. In the case of a card
		mismatch, the configured media type and the module type
		will not match."
	::= { slotConfigEntry 10 }


slotModuleMaxRAM OBJECT-TYPE
        SYNTAX  INTEGER
        ACCESS  read-only
        STATUS  mandatory
        DESCRIPTION
                "This indicates maximum RAM size in KB can be installed in
                this module."
        ::= { slotConfigEntry 11 }
 
slotModuleInstalledRAM OBJECT-TYPE
        SYNTAX  INTEGER
        ACCESS  read-only
        STATUS  mandatory
        DESCRIPTION
                "This indicates installed RAM in KB of this module."
        ::= { slotConfigEntry 12 }
 
slotModuleFlashSize OBJECT-TYPE
        SYNTAX  INTEGER
        ACCESS  read-only
        STATUS  mandatory
        DESCRIPTION
                "This indicates installed flash size in KB of this module."
        ::= { slotConfigEntry 13 }
 
 
slotModuleProductImageId OBJECT-TYPE
        SYNTAX  INTEGER {
                notApplicable(1),
                noAtmLanEmulation(2),
                minAtmLanEmulation(3),
                fullAtmLanEmulation(4),
                pnnifullAtmLanEmulation(5)
	}
        ACCESS  read-only
        STATUS  mandatory
        DESCRIPTION
                "This indicates the product target image id of this module."
        ::= { slotConfigEntry 14 }


slotModuleBaseMacAddress OBJECT-TYPE
        SYNTAX  MacAddress
        ACCESS  read-only
        STATUS  mandatory
        DESCRIPTION
                "This object returns the module base Mac address. A physical
		port's default Mac address can be computed based on this address
		by using following computation:

		Port(n)MacAddress = Moudle base Mac address + Port(n); where (n)
		is the 0-based port number."

        ::= { slotConfigEntry 15 }

slotLastResetEPC OBJECT-TYPE
       	SYNTAX  Counter32
       	ACCESS  read-only
       	STATUS  mandatory
    	DESCRIPTION
           "The programe counter realated to the last reset."
  ::= { slotConfigEntry 16 }

slotLastResetVirtualAddress OBJECT-TYPE
       	SYNTAX  Counter32
      	ACCESS  read-only
     	STATUS  mandatory
    	DESCRIPTION
           "The bus address."
  ::= { slotConfigEntry 17 }

slotLastResetCause OBJECT-TYPE
        SYNTAX  Counter32
        ACCESS  read-only
        STATUS  mandatory
       	DESCRIPTION
              "Register value related to the last reset"
        ::= { slotConfigEntry 18 }
 
slotLastResetTimeStamp OBJECT-TYPE
        SYNTAX  Counter32
        ACCESS  read-only
       	STATUS  mandatory
      	DESCRIPTION
                "A integer value of the system clock since last reset."
        ::= { slotConfigEntry 19 }

slotConfigAdd OBJECT-TYPE
        SYNTAX  Boolean
        ACCESS  read-write
        STATUS  mandatory
        DESCRIPTION
                "Setting this object causes the configuration of the
                slot to be updated to match the module currently in
                the slot.  When read, this object always returns
		false(2)."
 
        ::= { slotConfigEntry 20 }

slotConfigExtClockSource OBJECT-TYPE
	SYNTAX	INTEGER
	ACCESS	read-write
	STATUS	mandatory
	DESCRIPTION
		"This field indicates the external clock source.  
		 0 = Local Oscillator, 1..N = ATM port id for 
		 external clock source.  This object only applies 
		 to ATM MDA modules with SM, MM, or UTP media types."
    	DEFVAL { 0 }
	::= { slotConfigEntry 21 }

slotConfigTrafficShapingRate OBJECT-TYPE
	SYNTAX	INTEGER
	ACCESS	read-write
	STATUS	mandatory
	DESCRIPTION
		"Configured traffic shaping rate in kilo bits per second
		 on an ATM module.  The actual rate may be different
		 from the configured rate depending upon the physical
		 interface of ports in the module."
	::= { slotConfigEntry 22 }

END
-- SECTION 1: Top Level Definitions


CENTILLION-BRIDGEGROUP-MIB DEFINITIONS ::= BEGIN


-- Centillion Bridge Group MIB Release 2.0.3
-- Revision 04/05/99

-- Copyright 1994-99 Nortel Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	OBJECT-TYPE
		FROM RFC-1212
	StatusIndicator, sysConfig, EnableIndicator
		FROM CENTILLION-ROOT-MIB;


-- Textual Conventions

-- After VLAN is introduced, the old bridge group is split into  
-- the spanning group and the VLAN. The bridge group is equivalent to  
-- a spanning tree instance, and the VLAN defines the broadcast domain.
-- In this Bridge Configuration MIB, the object identifiers are not 
-- changed. But the terminology "bridge group" is changed to "spanning  
-- tree group" both in the description and in the comments. 
--
-- C100/BH switches support multiple spanning tree groups, which 
-- are identified by a unique spanning tree group identifier as 
-- specified by this textual convention:

BridgeGroupId ::= INTEGER (1..32)


-- Groups

bridgeGroup	OBJECT IDENTIFIER ::= { sysConfig 24 }


-- SECTION 2: Bridge Group
--
-- C100/BH switches allow a multiple number of spanning tree groups to be 
-- configured. This bridge group MIB allows a management application 
-- to perform configuration across any of the spanning tree groups. 


dot1dBaseGroupIdentifier OBJECT-TYPE
	SYNTAX	BridgeGroupId
	ACCESS	read-write
	STATUS	mandatory
	DESCRIPTION
		"The spanning tree group identifier for which the standard 
                bridging MIBS apply. Modifications of the spanning tree group 
                through the standard bridging MIBs effect this spanning tree 
                group only. This object is super governed by specific SET 
                community string. For example if a network management station 
                uses SET community string setcommunitystring@bg3, all 
                related SET requests will effect spanning tree group 3 only."
	::= { bridgeGroup 1 }

bridgeGroupTable OBJECT-TYPE
	SYNTAX	SEQUENCE OF BridgeGroupEntry
	ACCESS	not-accessible
	STATUS	mandatory
	DESCRIPTION
		"A specific spanning tree group. A spanning tree group consists 
                of a number of bridging ports running the same spanning tree
		protocol."
	::= { bridgeGroup 2 }

bridgeGroupEntry OBJECT-TYPE
	SYNTAX	BridgeGroupEntry
	ACCESS	not-accessible
	STATUS	mandatory
	DESCRIPTION
		"An entry in the spanning tree group table. Spanning tree 
                groups are added by specifying a bridgeGroupIdentifier, 
                bridgeGroupBaseType, bridgeGroupStpProtocol and a 
                bridgeGroupPortType with a value of valid(1) in 
                bridgeGroupStatus. Entries may be deleted by specifying 
                an entry with an value of invalid(2) in bridgeGroupStatus."
	INDEX	{ bridgeGroupIdentifier }
	::= { bridgeGroupTable 1 }

BridgeGroupEntry ::= SEQUENCE {
	bridgeGroupIdentifier
		BridgeGroupId,
	bridgeGroupStatus
		StatusIndicator,
	bridgeGroupBaseType
		INTEGER,
	bridgeGroupStpProtocol
		INTEGER,
	bridgeGroupPortType
		INTEGER,
	bridgeGroupNextPortIndex
		INTEGER,
	bridgeGroupTbRifEnable
		EnableIndicator,
	bridgeGroupTbRifRing
		INTEGER
	}

bridgeGroupIdentifier OBJECT-TYPE
	SYNTAX	BridgeGroupId
	ACCESS	read-write
	STATUS	mandatory
	DESCRIPTION
		"The unique spanning tree group identifier of this spanning   
                tree group."
	::= { bridgeGroupEntry 1 }

bridgeGroupStatus OBJECT-TYPE
	SYNTAX	StatusIndicator
	ACCESS	read-write
	STATUS	mandatory
	DESCRIPTION
		"The current status of the spanning tree group. Spanning tree 
                groups may be added by specifiying a valid status, and removed 
                by specifying an invalid status."
	::= { bridgeGroupEntry 2 }

bridgeGroupBaseType OBJECT-TYPE
	SYNTAX	INTEGER {
		none(1),	-- no bridging
		unknown(2),	-- none of the following
		transparent-only(3),
		sourceroute-only(4),
		srt(5),
		translation(6)
		}
	ACCESS	read-write
	STATUS	mandatory
	DESCRIPTION
		"Indicates the type of bridging this spanning tree group is 
                performing.A value of none(1) implies that switching is 
                performed between ports in this spanning tree group. A value 
                of unknown(2) implies that some unknown bridging rules are 
                applied on the ports in this spanning tree group. Modifying 
                the bridgeGroupBaseType requires a complete reset of the 
                spanning tree group. This value must be specified during 
                spanning tree group creation."
	::= { bridgeGroupEntry 3 }

bridgeGroupStpProtocol OBJECT-TYPE
	SYNTAX	INTEGER {
		none(1),
		unknown(2),
		decLb100(3),
		ieee8021d(4),
		ibm(5)
		}
	ACCESS	read-write
	STATUS	mandatory
	DESCRIPTION
		"An indication of the version of the Spanning Tree Protocol
		is being run, if the value of bridgeGroupBaseType is not 
                none(1). This field may be ignored if the bridgeGroupBaseType 
                value is none(1)."
	::= { bridgeGroupEntry 4 }

bridgeGroupPortType OBJECT-TYPE
	SYNTAX	INTEGER {
		unknown(1),
		token-ring(2),
		ethernet(3)
		}
	ACCESS	read-write
	STATUS	mandatory
	DESCRIPTION
		"Indicates the type of the spanning tree group ports. This 
		value may only be altered if there are no spanning tree group 
		ports currentlyin the spanning tree group. This value must be  
                specified during spanning tree group creation."
	::= { bridgeGroupEntry 5 }

bridgeGroupNextPortIndex OBJECT-TYPE
	SYNTAX	INTEGER
	ACCESS	read-only
	STATUS	mandatory
	DESCRIPTION
		"The value of the next spanning tree group port number which 
		will be assigned by the switch. When adding spanning tree 
		group ports bridging mode, the specified bridgeGroupPortIndex
		must match this value."
	::= { bridgeGroupEntry 6 }

bridgeGroupTbRifEnable OBJECT-TYPE
    SYNTAX  EnableIndicator
    ACCESS  read-write
    STATUS  mandatory
    DESCRIPTION
		"Enables the learning of Rif's by Token Ring Transparent
		Bridging spanning tree groups and processing of LE_ARP's for 
		route descrptors."
	::= { bridgeGroupEntry 7 }

bridgeGroupTbRifRing OBJECT-TYPE
    SYNTAX  INTEGER(0..4095)
    ACCESS  read-write
    STATUS  mandatory
    DESCRIPTION
		"The value of the ring used for learning RIF's when
		bridgeGroupTbRifEnable is set."
	::= { bridgeGroupEntry 8 }


--
-- The bridgeGroupPort Table
--

bridgeGroupPortTable OBJECT-TYPE
	SYNTAX	SEQUENCE OF BridgeGroupPortEntry
	ACCESS	not-accessible
	STATUS	mandatory
	DESCRIPTION
		"A table that contains information about each port that is
		associated with this spanning tree group."
	::= { bridgeGroup 3 }

bridgeGroupPortEntry OBJECT-TYPE
	SYNTAX	BridgeGroupPortEntry
	ACCESS	not-accessible
	STATUS	mandatory
	DESCRIPTION
		"A list of information for each port of the spanning tree 
                group. These entries are created and deleted by switch."
	INDEX	{ bridgeGroupPortGroupId, bridgeGroupPortIndex }
	::= { bridgeGroupPortTable 1 }

BridgeGroupPortEntry ::= SEQUENCE {
	bridgeGroupPortGroupId
		BridgeGroupId,
	bridgeGroupPortIndex
		INTEGER,
	bridgeGroupPortStatus
		StatusIndicator,
	bridgeGroupPortIfIndex
		INTEGER,
        bridgeGroupPortSpanMode
		INTEGER,
	bridgeGroupPortFastStart
		EnableIndicator
	}

bridgeGroupPortGroupId OBJECT-TYPE
	SYNTAX	BridgeGroupId
	ACCESS	read-only
	STATUS	mandatory
	DESCRIPTION
		"The spanning tree group identifier to which this port 
                belongs."
	::= { bridgeGroupPortEntry 1 }

bridgeGroupPortIndex OBJECT-TYPE
	SYNTAX	INTEGER
	ACCESS	read-only
	STATUS	mandatory
	DESCRIPTION
		"The value of the instance of the dot1dBasePort object, 
                defined in the Bridge MIB, for the spanning tree group 
                port corresponding to this port."
	::= { bridgeGroupPortEntry 2 }

bridgeGroupPortStatus OBJECT-TYPE
	SYNTAX	StatusIndicator
	ACCESS	read-only
	STATUS	mandatory
	DESCRIPTION
		"The current status of the spanning tree group port entry. 
                Spanning tree group ports is added or deleted when a virtual 
                segment port is added to or deleted from a virtual segment."
	::= { bridgeGroupPortEntry 3 }

bridgeGroupPortIfIndex OBJECT-TYPE
	SYNTAX	INTEGER
	ACCESS	read-write
	STATUS	mandatory
	DESCRIPTION
		"The value of the instance of the ifIndex object, defined
		in MIB-II, for the interface corresponding to this port.
		Spanning tree group ports are added by specifying the 
                ifIndex instance for the spanning tree group port."
	::= { bridgeGroupPortEntry 4 }

bridgeGroupPortSpanMode OBJECT-TYPE
         SYNTAX  INTEGER {
                     auto-span(1),
                     disabled(2),
                     forced(3)
                 }
         ACCESS  read-write
         STATUS  mandatory
         DESCRIPTION
                 "In SR mode, this object determines how this port behaves 
                 when presented with a Spanning Tree Explorer frame. The 
                 value 'disabled(2)' indicates that the port will not accept 
                 or send Spanning Tree Explorer packets; any STE packets 
                 received will be silently discarded. The value 'forced(3)' 
                 indicates the port will always accept and propagate Spanning 
                 Tree Explorer frames. This allows a manually configured
                 Spanning Tree for this class of packet to be configured.  
                 Note that unlike transparent bridging, this is not 
                 catastrophic to the network if there are loops. 
                 The value 'auto-span(1)' can only be returned by a bridge 
                 that both implements the Spanning Tree Protocol and has use 
                 of the protocol enabled on this port. The behavior of the 
                 port for Spanning Tree Explorer frames is determined by the 
                 state of dot1dStpPortState. If the port is in the 'forwarding' 
                 state, the frame will be accepted or propagated.  Otherwise, 
                 it will be silently discarded. 
                 In TB mode, this object provides the means to statically 
                 configure a port to forwarding/blocking modes. 'disabled(2)' 
                 indicates that the port is statically configured to blocking 
                 mode. 'forced(3)' indicates that the port is statically 
                 configured to forwarding mode. 'auto-span(1)' indicates that 
                 STP protocol is running."
         ::= { bridgeGroupPortEntry 5 }

bridgeGroupPortFastStart OBJECT-TYPE
	SYNTAX	EnableIndicator
	ACCESS	read-write
	STATUS	mandatory
	DESCRIPTION
                 "When FastStart is enabled, a port uses the minimum of hello 
                 time and forward delay time for transition from listening to 
                 learning to forwarding state. Once the port is in forwarding 
                 state, it will behave as a normal spanning tree port."
	 ::= { bridgeGroupPortEntry 6 }
END
-- SECTION 1: Top Level Definitions


CENTILLION-VIRTUALSEGMENT-MIB DEFINITIONS ::= BEGIN


-- Centillion Virtual Segment MIB Release 2.0.4
-- Revision 03/02/99

-- Copyright 1994-99 Nortel Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
        OBJECT-TYPE
                FROM RFC-1212
        StatusIndicator, sysConfig, Boolean
                FROM CENTILLION-ROOT-MIB
        BridgeGroupId
                FROM CENTILLION-BRIDGEGROUP-MIB
        DisplayString
                FROM RFC1213-MIB;


-- Textual Conventions

-- The following textual convention describes the type of virtual segments
-- in the system.
--
VirtualSegmentTypeId ::= 
        INTEGER {
                other(1),       -- none of the following
                token-ring(2),
                ethernet(3)
        }


-- Groups

virtualSegmentGroup     OBJECT IDENTIFIER ::= { sysConfig 23 }


-- SECTION 2: Virtual Segment Group
--
-- The virtual segment group contains information pertaining to all
-- virtual segments in the system.
--

virtualSegmentConfigNumber OBJECT-TYPE
        SYNTAX  INTEGER
        ACCESS  read-only
        STATUS  mandatory
        DESCRIPTION
                "The total number of configured virtual segments in the 
                system."
        ::= { virtualSegmentGroup 1 }

virtualSegmentActiveNumber OBJECT-TYPE
        SYNTAX  INTEGER
        ACCESS  read-only
        STATUS  mandatory
        DESCRIPTION
                "The total number of active virtual segments in the system."
        ::= { virtualSegmentGroup 2 }


virtualSegmentTable OBJECT-TYPE
        SYNTAX  SEQUENCE OF VirtualSegmentEntry
        ACCESS  not-accessible
        STATUS  mandatory
        DESCRIPTION
                "The Virtual Segment table. The virtual segment table contains
                information pertaining the each virtual segment in the system."
        ::= { virtualSegmentGroup 3 }

virtualSegmentEntry OBJECT-TYPE
        SYNTAX  VirtualSegmentEntry
        ACCESS  not-accessible
        STATUS  mandatory
        DESCRIPTION
                "A single entry in the virtual segment table. Virtual segments
                may be added by specifying a valid status for a non-existant
                entry in the table. Note that if no other values are
                specified in the set request, they are defaulted to a
                value as appropriate to the type of virtual Segment."
        INDEX   { virtualSegmentType, virtualSegmentId }
        ::= { virtualSegmentTable 1 }

VirtualSegmentEntry ::= SEQUENCE {
        virtualSegmentType
                VirtualSegmentTypeId,
        virtualSegmentId
                INTEGER,
        virtualSegmentStatus
                StatusIndicator,
        virtualSegmentIfIndex
                INTEGER,
        virtualSegmentConfiguredPortNumber
                INTEGER,
        virtualSegmentActivePortNumber
                INTEGER,
        virtualSegmentSpecific
                OBJECT IDENTIFIER,
        virtualSegmentAdminEncapsulation
                INTEGER,
        virtualSegmentBridgeGroupIdentifier
                BridgeGroupId,
        virtualSegmentGroupName
                DisplayString,
        virtualSegmentGroupServer
                Boolean
        }

virtualSegmentType OBJECT-TYPE
        SYNTAX  VirtualSegmentTypeId
        ACCESS  read-write
        STATUS  mandatory
        DESCRIPTION
                "The virtual segment type. When the type is ethernet, a MLT 
                 group will be created.  When the type is token ring, a token
                 ring vsegment is created." 
        ::= { virtualSegmentEntry 1 }

virtualSegmentId OBJECT-TYPE
        SYNTAX  INTEGER
        ACCESS  read-write
        STATUS  mandatory
        DESCRIPTION
                "The virtual segment identifier. The identifier is interpreted
                based upon the virtualSegmentType object. For example, the 
                virtualSegmentIdentifier for a token-ring VSegment 
                is the ring number.
                This identifier must be unique across local VSegments within 
                the specific virtualSegmentType."
        ::= { virtualSegmentEntry 2 }

virtualSegmentStatus OBJECT-TYPE
        SYNTAX  StatusIndicator
        ACCESS  read-write
        STATUS  mandatory
        DESCRIPTION
                "The current status of the virtual Segment entry. VSegments may
                be added by specifiying a valid status, and removed by
                specifying an invalid status."
        ::= { virtualSegmentEntry 3 }

virtualSegmentIfIndex OBJECT-TYPE
        SYNTAX  INTEGER
        ACCESS  read-only
        STATUS  mandatory
        DESCRIPTION
                "The value of the instance of the ifIndex object, defined
                in MIB-II, for the interface corresponding to this VSegment."
        ::= { virtualSegmentEntry 4 }

virtualSegmentConfiguredPortNumber OBJECT-TYPE
        SYNTAX  INTEGER
        ACCESS  read-only
        STATUS  mandatory
        DESCRIPTION
                "The number of ports configured in this VSegment."
        ::= { virtualSegmentEntry 5 }

virtualSegmentActivePortNumber OBJECT-TYPE
        SYNTAX  INTEGER
        ACCESS  read-only
        STATUS  mandatory
        DESCRIPTION
                "The number of active ports in this VSegment."
        ::= { virtualSegmentEntry 6 }

virtualSegmentSpecific OBJECT-TYPE
        SYNTAX  OBJECT IDENTIFIER
        ACCESS  read-only
        STATUS  mandatory
        DESCRIPTION
                "The object identifier to reference the corresponding instance
                in a VSegment specific MIB. If this information is not present,
                its value is set to the OBJECT IDENTIFIER { 0 0 }."
        ::= { virtualSegmentEntry 7 }

virtualSegmentAdminEncapsulation OBJECT-TYPE
        SYNTAX  INTEGER {
                other(1),               -- none of the following
                iso88025-tokenRing(2),
                ethernet-iso88023(3),   -- both ethernet & iso88023
                ethernet-csmacd(4),
                iso88023-csmacd(5)
                }
        ACCESS  read-write
        STATUS  mandatory
        DESCRIPTION
                "The encapulation used for generating management frames for
                multicast, broadcast and unknown destinations. The default
                values are specific to the virtualSemgentTypeId and are
                assigned as follows:
                        token-ring:     iso88025-tokenRing,
                        ethernet:       ethernet-iso88023
                Allowable values are also dependant on the 
                virtualSegmentTypeId."
        ::= { virtualSegmentEntry 8 }

virtualSegmentBridgeGroupIdentifier OBJECT-TYPE
        SYNTAX  BridgeGroupId
        ACCESS  read-only
        STATUS  mandatory
        DESCRIPTION
                "The spanning tree group identifier corresponding to this
                virtual segment."
        ::= { virtualSegmentEntry 9 }

virtualSegmentGroupName OBJECT-TYPE
        SYNTAX  DisplayString (SIZE(0..20))
        ACCESS  read-write
        STATUS  mandatory
        DESCRIPTION
                "The MLT group name corresponding to this virtual 
                segment.  This value is used for ethernet vsegment type 
                and is ignored for a token ring vsegment type."
        ::= { virtualSegmentEntry 10 }

virtualSegmentGroupServer OBJECT-TYPE
        SYNTAX  Boolean
        ACCESS  read-write
        STATUS  deprecated
        DESCRIPTION
                "Used to indicate a server is attached to this MLT
                 group. Default condition is false (no server attached
                 to this MLT group)."
        DEFVAL  { false }
        ::= { virtualSegmentEntry 11 }



-- SECTION 3: Virtual Segment Port Configuration Table
--
-- This table defines the port configuration for a virtual Segment.
--

virtualSegmentPortTable OBJECT-TYPE
        SYNTAX  SEQUENCE OF VirtualSegmentPortEntry
        ACCESS  not-accessible
        STATUS  mandatory
        DESCRIPTION
                "The Virtual Segment port configuration table. This table 
                contains information pertaining to the ports belonging to a
                virtual segment."
        ::= { virtualSegmentGroup 4 }

virtualSegmentPortEntry OBJECT-TYPE
        SYNTAX  VirtualSegmentPortEntry
        ACCESS  not-accessible
        STATUS  mandatory
        DESCRIPTION
                "An entry in the virtual Segment port table. Entries are 
                added by specifying the virtualSegmentPortType,
                 virtualSegmentPortIdentifier, 
                virtualSegmentPortCardNumber, and virtualSegmentPortPortNumber.
                Entries may be deleted simply by invalidating the 
                virtualSegmentPortStatus object."
        INDEX   { virtualSegmentPortType, 
                  virtualSegmentPortId, 
                  virtualSegmentPortCardNumber, 
                  virtualSegmentPortPortNumber }
        ::= { virtualSegmentPortTable 1 }

VirtualSegmentPortEntry ::= SEQUENCE {
        virtualSegmentPortType
                VirtualSegmentTypeId,
        virtualSegmentPortId
                INTEGER,
        virtualSegmentPortCardNumber
                INTEGER,
        virtualSegmentPortPortNumber
                INTEGER,
        virtualSegmentPortStatus
                StatusIndicator,
        virtualSegmentPortIfIndex
                INTEGER
        }

virtualSegmentPortType OBJECT-TYPE
        SYNTAX  VirtualSegmentTypeId
        ACCESS  read-write
        STATUS  mandatory
        DESCRIPTION
                "The virtual segment type of which this port is a member."
        ::= { virtualSegmentPortEntry 1 }

virtualSegmentPortId OBJECT-TYPE
        SYNTAX  INTEGER
        ACCESS  read-write
        STATUS  mandatory
        DESCRIPTION
                "The virtual segment identifier of which this port is 
                a member."
        ::= { virtualSegmentPortEntry 2 }

virtualSegmentPortCardNumber OBJECT-TYPE
        SYNTAX  INTEGER
        ACCESS  read-write
        STATUS  mandatory
        DESCRIPTION
                "The card number for this port in the virtual Segment."
        ::= { virtualSegmentPortEntry 3 }

virtualSegmentPortPortNumber OBJECT-TYPE
        SYNTAX  INTEGER
        ACCESS  read-write
        STATUS  mandatory
        DESCRIPTION
                "The port number for this port in the virtual Segment."
        ::= { virtualSegmentPortEntry 4 }

virtualSegmentPortStatus OBJECT-TYPE
        SYNTAX  StatusIndicator
        ACCESS  read-write
        STATUS  mandatory
        DESCRIPTION
                "The current status of the entry. Entries may be added by
                specifying a value of valid, and removed by setting the
                status to invalid."
        ::= { virtualSegmentPortEntry 5 }

virtualSegmentPortIfIndex OBJECT-TYPE
        SYNTAX  INTEGER
        ACCESS  read-only
        STATUS  mandatory
        DESCRIPTION
                "The value for this object identifies the instance of
                the ifIndex object defined in MIB-II, for the interface
                corresponding to this port. If no such entry exists, the
                value 0 may be returned."
        ::= { virtualSegmentPortEntry 6 }


END
-- SECTION 1: Top Level Definition


CENTILLION-BRIDGE-MIB DEFINITIONS ::= BEGIN


-- Centillion Bridge MIB Release 2.0.0
-- Revision 03/20/96

-- Copyright 1994-96 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	Counter, TimeTicks
		FROM RFC1155-SMI
	OBJECT-TYPE
		FROM RFC-1212
	extensions, EnableIndicator
		FROM CENTILLION-ROOT-MIB;


-- Textual Conventions

-- All representations of MAC addresses in this MIB Module
-- use, as a textual convention (i.e. this convention does
-- not affect their encoding), the data type:

MacAddress ::= OCTET STRING (SIZE (6))

-- a 6 octet address in the "canonical" order defined
-- by IEEE 802.1a, i.e., as if it were transmitted
-- least significant bit first, even though 802.5 (in
-- contrast to other n802.x protocols) requires MAC
-- addresses to be transmitted most significant bit first.
--
-- 16-bit addresses, if needed, are represented by setting
-- their upper 4 octets to all 0's, i.e., AAFF would be
-- represented as 00000000AAFF.


-- Similarly, all representations of Bridge-Id in this MIB
-- Module use, as a textual convention (i.e. this
-- convention does not affect their encoding), the data
-- type:

BridgeId ::= OCTET STRING (SIZE (8))

-- the Bridge-Identifier as used in the Spanning Tree
-- Protocol to uniquely identify a bridge.  Its first two
-- octets (in network byte order) contain a priority
-- value and its last 6 octets contain the MAC address
-- used to refer to a bridge in a unique fashion
-- (typically, the numerically smallest MAC address
-- of all ports on the bridge).
-- Several objects in this MIB module represent values of
-- timers used by the Spanning Tree Protocol.  In this
-- MIB, these timers have values in units of hundreths of
-- a second (i.e. 1/100 secs).
-- These timers, when stored in a Spanning Tree Protocol's
-- BPDU, are in units of 1/256 seconds.  Note, however,
-- that 802.1D-1990 specifies a settable granularity of
-- no more than 1 second for these timers.  To avoid
-- ambiguity, a data type is defined here as a textual
-- convention and all representation of these timers
-- in this MIB module are defined using this data type.  An
-- algorithm is also defined for converting between the
-- different units, to ensure a timer's value is not
-- distorted by multiple conversions.
-- The data type is:

Timeout ::= INTEGER -- a STP timer in units of 1/100 seconds

-- To convert a Timeout value into a value in units of
-- 1/256 seconds, the following algorithm should be used:
--
--      b  = floor( (n * 256) / 100)
--
-- where:
--      floor   =  quotient [ignore remainder]
--      n is the value in 1/100 second units
--      b is the value in 1/256 second units
--
-- To convert the value from 1/256 second units back to
-- 1/100 seconds, the following algorithm should be used:
--
--      n = ceiling( (b * 100) / 256)
--
-- where:
--      ceiling =  quotient [if remainder is 0], or
--                 quotient + 1 [if remainder is non-zero]
--      n is the value in 1/100 second units
--      b is the value in 1/256 second units
--
-- Note: it is important that the arithmetic operations are
-- done in the order specified (i.e., multiply first, divide
-- second).


-- Groups

cndot1dBridge   OBJECT IDENTIFIER ::= { extensions 17 }

cndot1dBase     OBJECT IDENTIFIER ::= { cndot1dBridge 1 }
cndot1dStp      OBJECT IDENTIFIER ::= { cndot1dBridge 2 }
cndot1dSr       OBJECT IDENTIFIER ::= { cndot1dBridge 3 }
cndot1dTp	OBJECT IDENTIFIER ::= { cndot1dBridge 4 }


-- SECTION 2:

--
-- The cndot1dBase group
--
-- Implementation of the cndot1dBase group is mandatory for all
-- bridges.
--

cndot1dBaseBridgeAddress OBJECT-TYPE
	SYNTAX  MacAddress
	ACCESS  read-only
	STATUS  mandatory
	DESCRIPTION
		"The MAC address used by this bridge when it must
		be referred to in a unique fashion.   It is
		recommended that this be the numerically smallest
		MAC address of all ports that belong to this
		bridge.  However it is only required to be unique.
		When concatenated with cndot1dStpPriority a unique
		BridgeIdentifier is formed which is used in the
		Spanning Tree Protocol."
	REFERENCE
		"IEEE 802.1D-1990: Sections 6.4.1.1.3 and 3.12.5"
	::= { cndot1dBase 1 }

cndot1dBaseNumPorts OBJECT-TYPE
	SYNTAX  INTEGER
	ACCESS  read-only
	STATUS  mandatory
	DESCRIPTION
		"The number of ports controlled by this bridging
		entity."
	REFERENCE
		"IEEE 802.1D-1990: Section 6.4.1.1.3"
	::= { cndot1dBase 2 }

cndot1dBaseType OBJECT-TYPE
	SYNTAX  INTEGER {
		unknown(1),
		transparent-only(2),
		sourceroute-only(3),
		srt(4)
		}
	ACCESS  read-only
	STATUS  mandatory
	DESCRIPTION
		"Indicates what type of bridging is being performed
		If a bridge is actually performing a
		certain type of bridging this will be indicated by
		entries in the port table for the given type."
	::= { cndot1dBase 3 }


-- The Generic Bridge Port Table

cndot1dBasePortTable OBJECT-TYPE
	SYNTAX  SEQUENCE OF Cndot1dBasePortEntry
	ACCESS  not-accessible
	STATUS  mandatory
	DESCRIPTION
		"A table that contains generic information about
		every port that is associated with this bridge.
		Transparent, source-route, and srt ports are
		included."
	::= { cndot1dBase 4 }

cndot1dBasePortEntry OBJECT-TYPE
	SYNTAX  Cndot1dBasePortEntry
	ACCESS  not-accessible
	STATUS  mandatory
	DESCRIPTION
		"A list of information for each port of the
		bridge."
	REFERENCE
		"IEEE 802.1D-1990: Section 6.4.2, 6.6.1"
	INDEX  { cndot1dBasePort }
	::= { cndot1dBasePortTable 1 }


Cndot1dBasePortEntry ::= SEQUENCE {
	cndot1dBasePort
		INTEGER,
	cndot1dBasePortIfIndex
		INTEGER,
	cndot1dBasePortCircuit
		OBJECT IDENTIFIER
	}

cndot1dBasePort OBJECT-TYPE
	SYNTAX  INTEGER
	ACCESS  read-only
	STATUS  mandatory
	DESCRIPTION
		"The port number of the port for which this entry
		contains bridge management information."
	::= { cndot1dBasePortEntry 1 }

cndot1dBasePortIfIndex OBJECT-TYPE
	SYNTAX  INTEGER
	ACCESS  read-only
	STATUS  mandatory
	DESCRIPTION
		"The value of the instance of the ifIndex object,
		defined in MIB-II, for the interface corresponding
		to this port."
	::= { cndot1dBasePortEntry 2 }

cndot1dBasePortCircuit OBJECT-TYPE
	SYNTAX  OBJECT IDENTIFIER
	ACCESS  read-only
	STATUS  mandatory
	DESCRIPTION
		"For a port which (potentially) has the same value
		of cndot1dBasePortVirtualRing as another port on the
		same bridge, this object contains the name of an
		object instance unique to this port.  For example,
		in the case where multiple ports correspond one-
		to-one with multiple X.25 virtual circuits, this
		value might identify an (e.g., the first) object
		instance associated with the X.25 virtual circuit
		corresponding to this port.

		For a port which has a unique value of
		dot1dBasePortIfIndex, this object can have the
		value { 0 0 }."
	::= { cndot1dBasePortEntry 3 }


-- The cndot1dStp group
--
-- Implementation of the cndot1dStp group is optional.  It is
-- implemented by those bridges that support the Spanning Tree
-- Protocol.
--

cndot1dStpProtocolSpecification OBJECT-TYPE
	SYNTAX  INTEGER {
		unknown(1),
		decLb100(2),
		ieee8021d(3)
		}
	ACCESS  read-only
	STATUS  mandatory
	DESCRIPTION
		"An indication of what version of the Spanning
		Tree Protocol is being run.  The value
		'decLb100(2)' indicates the DEC LANbridge 100
		Spanning Tree protocol.  IEEE 802.1d
		implementations will return 'ieee8021d(3)'.  If
		future versions of the IEEE Spanning Tree Protocol
		are released that are incompatible with the
		current version a new value will be defined."
	::= { cndot1dStp 1 }

cndot1dStpPriority OBJECT-TYPE
	SYNTAX  INTEGER (0..65535)
	ACCESS  read-write
	STATUS  mandatory
	DESCRIPTION
		"The value of the write-able portion of the Bridge
		ID, i.e., the first two octets of the (8 octet
		long) Bridge ID.  The other (last) 6 octets of the
		Bridge ID are given by the value of
		cndot1dBaseBridgeAddress."
	REFERENCE
		"IEEE 802.1D-1990: Section 4.5.3.7"
	::= { cndot1dStp 2 }

cndot1dStpTimeSinceTopologyChange OBJECT-TYPE
	SYNTAX  TimeTicks
	ACCESS  read-only
	STATUS  mandatory
	DESCRIPTION
		"The time (in hundredths of a second) since the
		last time a topology change was detected by the
		bridge entity."
	REFERENCE
		"IEEE 802.1D-1990: Section 6.8.1.1.3"
	::= { cndot1dStp 3 }

cndot1dStpTopChanges OBJECT-TYPE
	SYNTAX  Counter
	ACCESS  read-only
	STATUS  mandatory
	DESCRIPTION
		"The total number of topology changes detected by
		this bridge since the management entity was last
		reset or initialized."
	REFERENCE
		"IEEE 802.1D-1990: Section 6.8.1.1.3"
	::= { cndot1dStp 4 }

cndot1dStpDesignatedRoot OBJECT-TYPE
	SYNTAX  BridgeId
	ACCESS  read-only
	STATUS  mandatory
	DESCRIPTION
		"The bridge identifier of the root of the spanning
		tree as determined by the Spanning Tree Protocol
		as executed by this node.  This value is used as
		the Root Identifier parameter in all Configuration
		Bridge PDUs originated by this node."
	REFERENCE
		"IEEE 802.1D-1990: Section 4.5.3.1"
	::= { cndot1dStp 5 }

cndot1dStpRootCost OBJECT-TYPE
	SYNTAX  INTEGER
	ACCESS  read-only
	STATUS  mandatory
	DESCRIPTION
		"The cost of the path to the root as seen from
		this bridge."
	REFERENCE
		"IEEE 802.1D-1990: Section 4.5.3.2"
	::= { cndot1dStp 6 }

cndot1dStpRootPort OBJECT-TYPE
	SYNTAX  INTEGER
	ACCESS  read-only
	STATUS  mandatory
	DESCRIPTION
		"The port number of the port which offers the
		lowest cost path from this bridge to the root
		bridge."
	REFERENCE
		"IEEE 802.1D-1990: Section 4.5.3.3"
	::= { cndot1dStp 7 }

cndot1dStpMaxAge OBJECT-TYPE
	SYNTAX  Timeout
	ACCESS  read-only
	STATUS  mandatory
	DESCRIPTION
		"The maximum age of Spanning Tree Protocol
		information learned from the network on any port
		before it is discarded, in units of hundredths of
		a second.  This is the actual value that this
		bridge is currently using."
	REFERENCE
	"IEEE 802.1D-1990: Section 4.5.3.4"
	::= { cndot1dStp 8 }

cndot1dStpHelloTime OBJECT-TYPE
	SYNTAX  Timeout
	ACCESS  read-only
	STATUS  mandatory
	DESCRIPTION
		"The amount of time between the transmission of
		Configuration bridge PDUs by this node on any port
		when it is the root of the spanning tree or trying
		to become so, in units of hundredths of a second.
		This is the actual value that this bridge is
		currently using."
	REFERENCE
		"IEEE 802.1D-1990: Section 4.5.3.5"
	::= { cndot1dStp 9 }

cndot1dStpHoldTime OBJECT-TYPE
	SYNTAX  INTEGER
	ACCESS  read-only
	STATUS  mandatory
	DESCRIPTION
		"This time value determines the interval length
		during which no more than two Configuration bridge
		PDUs shall be transmitted by this node, in units
		of hundredths of a second."
	REFERENCE
	"IEEE 802.1D-1990: Section 4.5.3.14"
	::= { cndot1dStp 10 }

cndot1dStpForwardDelay OBJECT-TYPE
	SYNTAX  Timeout
	ACCESS  read-only
	STATUS  mandatory
	DESCRIPTION
		"This time value, measured in units of hundredths
		of a second, controls how fast a port changes its
		spanning state when moving towards the Forwarding
		state.  The value determines how long the port
		stays in each of the Listening and Learning
		states, which precede the Forwarding state.  This
		value is also used, when a topology change has
		been detected and is underway, to age all dynamic
		entries in the Forwarding Database.  [Note that
		this value is the one that this bridge is
		currently using, in contrast to
		cndot1dStpBridgeForwardDelay which is the value that
		this bridge and all others would start using
		if/when this bridge were to become the root.]"
	REFERENCE
		"IEEE 802.1D-1990: Section 4.5.3.6"
	::= { cndot1dStp 11 }

cndot1dStpBridgeMaxAge OBJECT-TYPE
	SYNTAX  Timeout (600..4000)
	ACCESS  read-write
	STATUS  mandatory
	DESCRIPTION
		"The value that all bridges use for MaxAge when
		this bridge is acting as the root.  Note that
		802.1D-1990 specifies that the range for this
		parameter is related to the value of
		cndot1dStpBridgeHelloTime. The granularity of this
		timer is specified by 802.1D-1990 to be 1 second.
		An agent may return a badValue error if a set is
		attempted to a value which is not a whole number
		of seconds."
	REFERENCE
		"IEEE 802.1D-1990: Section 4.5.3.8"
	::= { cndot1dStp 12 }

cndot1dStpBridgeHelloTime OBJECT-TYPE
	SYNTAX  Timeout (100..1000)
	ACCESS  read-write
	STATUS  mandatory
	DESCRIPTION
		"The value that all bridges use for HelloTime when
		this bridge is acting as the root.  The
		granularity of this timer is specified by 802.1D-
		1990 to be 1 second.  An agent may return a
		badValue error if a set is attempted to a value
		which is not a whole number of seconds."
	REFERENCE
		"IEEE 802.1D-1990: Section 4.5.3.9"
	::= { cndot1dStp 13 }

cndot1dStpBridgeForwardDelay OBJECT-TYPE
	SYNTAX  Timeout (400..3000)
	ACCESS  read-write
	STATUS  mandatory
	DESCRIPTION
		"The value that all bridges use for ForwardDelay
		when this bridge is acting as the root.  Note that
		802.1D-1990 specifies that the range for this
		parameter is related to the value of
		cndot1dStpBridgeMaxAge.  The granularity of this
		timer is specified by 802.1D-1990 to be 1 second.
		An agent may return a badValue error if a set is
		attempted to a value which is not a whole number
		of seconds."
	REFERENCE
		"IEEE 802.1D-1990: Section 4.5.3.10"
	::= { cndot1dStp 14 }


-- The Spanning Tree Port Table

cndot1dStpPortTable OBJECT-TYPE
	SYNTAX  SEQUENCE OF Cndot1dStpPortEntry
	ACCESS  not-accessible
	STATUS  mandatory
	DESCRIPTION
		"A table that contains port-specific information
		for the Spanning Tree Protocol."
	::= { cndot1dStp 15 }

cndot1dStpPortEntry OBJECT-TYPE
	SYNTAX  Cndot1dStpPortEntry
	ACCESS  not-accessible
	STATUS  mandatory
	DESCRIPTION
		"A list of information maintained by every port
		about the Spanning Tree Protocol state for that
		port."
	INDEX   { cndot1dStpPort }
	::= { cndot1dStpPortTable 1 }

Cndot1dStpPortEntry ::= SEQUENCE {
	cndot1dStpPort
		INTEGER,
	cndot1dStpPortPriority
		INTEGER,
	cndot1dStpPortState
		INTEGER,
	cndot1dStpPortEnable
		INTEGER,
	cndot1dStpPortPathCost
		INTEGER,
	cndot1dStpPortDesignatedRoot
		BridgeId,
	cndot1dStpPortDesignatedCost
		INTEGER,
	cndot1dStpPortDesignatedBridge
		BridgeId,
	cndot1dStpPortDesignatedPort
		OCTET STRING,
	cndot1dStpPortForwardTransitions
		Counter
	}

cndot1dStpPort OBJECT-TYPE
	SYNTAX  INTEGER (1..65535)
	ACCESS  read-only
	STATUS  mandatory
	DESCRIPTION
		"The port number of the port for which this entry
		contains Spanning Tree Protocol management
		information."
	REFERENCE
		"IEEE 802.1D-1990: Section 6.8.2.1.2"
	::= { cndot1dStpPortEntry 1 }

cndot1dStpPortPriority OBJECT-TYPE
	SYNTAX  INTEGER (0..255)
	ACCESS  read-write
	STATUS  mandatory
	DESCRIPTION
		"The value of the priority field which is
		contained in the first (in network byte order)
		octet of the (2 octet long) Port ID.  The other
		octet of the Port ID is given by the value of
		cndot1dStpPort."
	REFERENCE
		"IEEE 802.1D-1990: Section 4.5.5.1"
	::= { cndot1dStpPortEntry 2 }

cndot1dStpPortState OBJECT-TYPE
	SYNTAX  INTEGER {
		disabled(1),
		blocking(2),
		listening(3),
		learning(4),
		forwarding(5),
		broken(6)
		}
	ACCESS  read-only
	STATUS  mandatory
	DESCRIPTION
		"The port's current state as defined by
		application of the Spanning Tree Protocol.  This
		state controls what action a port takes on
		reception of a frame.  If the bridge has detected
		a port that is malfunctioning it will place that
		port into the broken(6) state.  For ports which
		are disabled (see cndot1dStpPortEnable), this object
		will have a value of disabled(1)."
	REFERENCE
		"IEEE 802.1D-1990: Section 4.5.5.2"
	::= { cndot1dStpPortEntry 3 }

cndot1dStpPortEnable OBJECT-TYPE
	SYNTAX  INTEGER {
		enabled(1),
		disabled(2)
		}
	ACCESS  read-write
	STATUS  mandatory
	DESCRIPTION
		"The enabled/disabled status of the port."
	REFERENCE
		"IEEE 802.1D-1990: Section 4.5.5.2"
	::= { cndot1dStpPortEntry 4 }

cndot1dStpPortPathCost OBJECT-TYPE
	SYNTAX  INTEGER (1..65535)
	ACCESS  read-write
	STATUS  mandatory
	DESCRIPTION
		"The contribution of this port to the path cost of
		paths towards the spanning tree root which include
		this port.  802.1D-1990 recommends that the
		default value of this parameter be in inverse
		proportion to the speed of the attached LAN."
	REFERENCE
		"IEEE 802.1D-1990: Section 4.5.5.3"
	::= { cndot1dStpPortEntry 5 }

cndot1dStpPortDesignatedRoot OBJECT-TYPE
	SYNTAX  BridgeId
	ACCESS  read-only
	STATUS  mandatory
	DESCRIPTION
		"The unique Bridge Identifier of the Bridge
		recorded as the Root in the Configuration BPDUs
		transmitted by the Designated Bridge for the
		segment to which the port is attached."
	REFERENCE
		"IEEE 802.1D-1990: Section 4.5.5.4"
	::= { cndot1dStpPortEntry 6 }

cndot1dStpPortDesignatedCost OBJECT-TYPE
	SYNTAX  INTEGER
	ACCESS  read-only
	STATUS  mandatory
	DESCRIPTION
		"The path cost of the Designated Port of the
		segment connected to this port.  This value is
		compared to the Root Path Cost field in received
		bridge PDUs."
	REFERENCE
		"IEEE 802.1D-1990: Section 4.5.5.5"
	::= { cndot1dStpPortEntry 7 }

cndot1dStpPortDesignatedBridge OBJECT-TYPE
	SYNTAX  BridgeId
	ACCESS  read-only
	STATUS  mandatory
	DESCRIPTION
		"The Bridge Identifier of the bridge which this
		port considers to be the Designated Bridge for
		this port's segment."
	REFERENCE
		"IEEE 802.1D-1990: Section 4.5.5.6"
	::= { cndot1dStpPortEntry 8 }

cndot1dStpPortDesignatedPort OBJECT-TYPE
	SYNTAX  OCTET STRING (SIZE (2))
	ACCESS  read-only
	STATUS  mandatory
	DESCRIPTION
		"The Port Identifier of the port on the Designated
		Bridge for this port's segment."
	REFERENCE
		"IEEE 802.1D-1990: Section 4.5.5.7"
	::= { cndot1dStpPortEntry 9 }

cndot1dStpPortForwardTransitions OBJECT-TYPE
	SYNTAX  Counter
	ACCESS  read-only
	STATUS  mandatory
	DESCRIPTION
		"The number of times this port has transitioned
		from the Learning state to the Forwarding state."
	::= { cndot1dStpPortEntry 10 }


-- the dot1Tp group

-- Implementation of the dot1Tp group is optional. It is implemented
-- by those bridges that support the transparent bridging mode.
-- A transparent or SRT bridge will implement this group.

-- Currently, Centillion Networks utilizes other proprietary
-- MIBS to support the information is this group with the
-- exception of those object defined here. The proprietary objects
-- in this group follow the standard object identifiers to allow
-- future implementation of the TP group.

cndot1dTpSrFrameForward OBJECT-TYPE
	SYNTAX	EnableIndicator
	ACCESS	read-write
	STATUS	mandatory
	DESCRIPTION
		"Indicates whether the system will forward source
		routed frames if running in transparent bridging
		mode. If this value is disabled(1), the system will
		drop all source-routed frames. The default value
		is disabled(1)."
	::= { cndot1dTp 5 }


END
-- SECTION 1: Top Level Definitions

                                     
CENTILLION-CONFIG-MIB DEFINITIONS ::= BEGIN


-- Centillion Configuration MIB Release 2.1.0
-- Revision 07/11/00

-- Copyright 1994-2000 Nortel Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.

-- This file defines the MIB for configuration and maintenance of the
-- system tables.
-- All configuration objects are not saved across system resets unless
-- the configruation is saved in flash memory, unless otherwise specified.


-- Imports

IMPORTS
	DisplayString, PhysAddress
		FROM RFC1213-MIB
	OBJECT-TYPE
		FROM RFC-1212
	Counter, TimeTicks, IpAddress
		FROM RFC1155-SMI
	StatusIndicator, BitField, MacAddress,
	EnableIndicator, sysConfig
		FROM CENTILLION-ROOT-MIB;

-- Textual Conventions

VlanId ::= INTEGER(1..4095)

-- Groups

sysTableConfig		OBJECT IDENTIFIER ::=	{ sysConfig 1 }
sysImgInfo              OBJECT IDENTIFIER ::=   { sysConfig 2 }
sysMcpRedundInfo        OBJECT IDENTIFIER ::=   { sysConfig 3 }
sysNetProtocol		OBJECT IDENTIFIER ::= 	{ sysConfig 14 }
sysTFTPGroup		OBJECT IDENTIFIER ::= 	{ sysConfig 18 }
sysSNMPGroup		OBJECT IDENTIFIER ::= 	{ sysConfig 19 }
netbiosGroup		OBJECT IDENTIFIER ::= 	{ sysConfig 21 }
lnmGroup		OBJECT IDENTIFIER ::= 	{ sysConfig 25 }

sysIpProtocol		OBJECT IDENTIFIER ::= 	{ sysNetProtocol 1 }


-- SECTION 2: MCP System Table Configuration Information
--
-- This information is specific to the system tables and may not be
-- visible to the user.
--

--- System Image Global Information

sysImgGbl OBJECT IDENTIFIER ::= { sysImgInfo 1 }

sysImgGblInvokeSrc OBJECT-TYPE
        SYNTAX  INTEGER {
                other(1),
                image1(2),
                image2(3)
                }
        ACCESS  read-write
        STATUS  mandatory
        DESCRIPTION
                "The source of system image to be invoked at next boot.
                 Default setting is image1.

                 If the desired image cannot be invoked,
                 another image (if found and valid) will be invoked 
                 automatically at next boot.

                 Note that if the system does not support
                 dual boot image, then image1 should be used."
        ::= { sysImgGbl 1 }


sysImgGblLoadDst OBJECT-TYPE
        SYNTAX  INTEGER {
                other(1),
                location1(2),
                location2(3)
                }
        ACCESS  read-write
        STATUS  mandatory
        DESCRIPTION
                "The non volatile memory destination where 
                 the system image will be (programmed by boot loader)
                 down loaded to at next boot.
                 Default setting is location1.

                 Note that if the system does not support
                 dual boot image, then location1 should be used."
        ::= { sysImgGbl 2 }


--- System Image Table Information

sysImgTable OBJECT-TYPE
        SYNTAX  SEQUENCE OF SysImgEntry
        ACCESS  not-accessible
        STATUS  mandatory
        DESCRIPTION
                "A table that provides additional information
                about the system images. The number of
                entries in the table is determined by the
                number of index of the system image."
        ::= { sysImgInfo 2 }


sysImgEntry OBJECT-TYPE
        SYNTAX  SysImgEntry
        ACCESS  not-accessible
        STATUS  mandatory
        DESCRIPTION
                "A row in the table of additional information
                about the system images. Entries can not
                be created or deleted via SNMP requests."
        INDEX   { sysImgIndx }
        ::= { sysImgTable 1 }


SysImgEntry ::= SEQUENCE {
        sysImgIndx INTEGER,
        sysImgVer DisplayString,
        sysImgStatus INTEGER
        }
 
 
sysImgIndx OBJECT-TYPE
        SYNTAX  INTEGER (1..65535)
        ACCESS  read-only
        STATUS  mandatory
        DESCRIPTION
                "The index of the system image."
        ::= { sysImgEntry 1 }


sysImgVer OBJECT-TYPE
        SYNTAX  DisplayString (SIZE(0..127))
        ACCESS  read-only
        STATUS  mandatory
        DESCRIPTION
                "The version of the system image stored in
                non volatile memory.

                Note that if the system does not support
                dual boot image, then zero length string
                should be returned for image2."
        ::= { sysImgEntry 2 }


sysImgStatus OBJECT-TYPE
        SYNTAX  INTEGER {
                other(1),
                good(2),
                bad(3)
                }
        ACCESS  read-only
        STATUS  mandatory
        DESCRIPTION
                "The status of system image stored in non volatile memory."
        ::= { sysImgEntry 3 }


--- System MCP Redundancy Global Information

sysMcpRedundGbl OBJECT IDENTIFIER ::= { sysMcpRedundInfo 1 }

sysMcpRedundNxtGblState OBJECT-TYPE
        SYNTAX  INTEGER {
                other(1),
                enable(2),
                disable(3)
                }
        ACCESS  read-write
        STATUS  mandatory
        DESCRIPTION
		"State of the Redundant MCP during next boot.
		Request to enable or disable redundant MCP.  This
		will update the configuration information for the
		redundant MCP pair.  It takes effect during next
		reset."
        ::= { sysMcpRedundGbl 1 }


--- System MCP Redundancy Table Information

sysMcpRedundTable OBJECT-TYPE
        SYNTAX  SEQUENCE OF SysMcpRedundEntry
        ACCESS  not-accessible
        STATUS  mandatory
        DESCRIPTION
                "A table that provides additional information
                about the system MCP redundancy. The number of
                entries in the table is determined by the
                number of index of the system MCP redundancy."
        ::= { sysMcpRedundInfo 2 }


sysMcpRedundEntry OBJECT-TYPE
        SYNTAX  SysMcpRedundEntry
        ACCESS  not-accessible
        STATUS  mandatory
        DESCRIPTION
                "A row in the table of additional information
                about the system MCP redundancy. Entries can not
                be created or deleted via SNMP requests."
        INDEX   { sysMcpRedundIndx }
        ::= { sysMcpRedundTable 1 }


SysMcpRedundEntry ::= SEQUENCE {
        sysMcpRedundIndx INTEGER,
        sysMcpRedundPriority INTEGER,
	sysMcpRedundType INTEGER,
	sysMcpRedundOperState INTEGER,
	sysMcpRedundCfgStatus INTEGER
        }
 
 
sysMcpRedundIndx OBJECT-TYPE
        SYNTAX  INTEGER (1..65535)
        ACCESS  read-only
        STATUS  mandatory
        DESCRIPTION
		"The index of the system MCP redundancy. Currently
		represents the slot number that this MCP is in."
        ::= { sysMcpRedundEntry 1 }


sysMcpRedundPriority OBJECT-TYPE
        SYNTAX  INTEGER (0..255)
        ACCESS  read-write
        STATUS  mandatory
        DESCRIPTION
                "The MCP redundancy priority which is used for primary
		MCP selection.  Default setting is zero."
        ::= { sysMcpRedundEntry 2 }

sysMcpRedundType OBJECT-TYPE
	SYNTAX  INTEGER {
		other(1),
		regular(2),
		primary(3),
		secondary(4),
		switching(5)
		}
	ACCESS  read-only
	STATUS  mandatory
	DESCRIPTION
		"Functional type of MCP in the chassis. Currently only
		ATM MCPs can be used for the redundant function.  Only
		MCPs in slots 1 and 2 can participate in redundancy.
		But other ATM MCPs can still be plugged into the chasis.
		This field represents the way that an MCP is
		participating in the redundancy."
	::= {sysMcpRedundEntry 3 }

sysMcpRedundOperState OBJECT-TYPE
	SYNTAX  INTEGER {
		other(1),
		active(2),
		inactive(3)
		}
	ACCESS  read-only
	STATUS  mandatory
	DESCRIPTION
		"Current state of this MCP"
	::= {sysMcpRedundEntry 4 }

sysMcpRedundCfgStatus OBJECT-TYPE
	SYNTAX  INTEGER {
		other(1),
		user-enable(2),
		user-disable(3),
		default-enable(4),
		default-disable(5)
		}
	ACCESS  read-only
	STATUS  mandatory
	DESCRIPTION
		"State of the Redundant MCP. Other(1) is used when the
		MCP is not participating in redundancy, default
		enable/disable used to represent the factory default
		case.  User enable/disable used when a user changes
		from the factory default state."
	::= { sysMcpRedundEntry 5 }

-- The following objects for Redundant MCP are for future
-- implementations when there is more time to implement the drivers
-- support.
--
--      sysMcpRedundPriStateChg OBJECT-TYPE
--      SYNTAX  COUNTER
--      ACCESS  read-only
--      STATUS  mandatory
--      DESCRIPTION
--              "Number of times this MCP has been a Primary MCP."
--      ::= { sysMcpRedundEntry 6 }
--
--      sysMcpRedundSecStateChg OBJECT-TYPE
--      SYNTAX  COUNTER
--      ACCESS  read-only
--      STATUS  mandatory
--      DESCRIPTION
--              "Number of times this MCP has been a Secondary MCP."
--      ::= { sysMcpRedundEntry 7 }
--
--      sysMcpRedundLastHeartBeat OBJECT-TYPE
--      SYNTAX  TimeTicks
--      ACCESS  read-only
--      STATUS  mandatory
--      DESCRIPTION
--              "Last time the MCP received a heart beat pulse from
--              the other MCP which is the participant in the redundant
--              MCP paring and does not include other ATM MCPs that may
--              be in the same chassis."
--      ::= { sysMcpRedundEntry 8 }
--
--      sysMcpRedundFailureDetected OBJECT-TYPE
--      SYNTAX  COUNTER
--      ACCESS  read-only
--      STATUS  mandatory
--      DESCRIPTION
--              "Number of times a redundant partner has failed."
--      ::= { sysMcpRedundEntry 9 }




-- SECTION 3: Routing Information
--
-- The RIF Table
--
-- The Routing Information Field (RIF) Table contains routing information
-- used by stations.
--

rifTable OBJECT-TYPE
	SYNTAX	SEQUENCE OF RifEntry
	ACCESS	not-accessible
	STATUS	mandatory
	DESCRIPTION
		"This table contains Routing Information Field (RIF)
		parameters. Entries may be used by one or more stations on
		the switch."
	::= { sysConfig 5 }

rifEntry OBJECT-TYPE
	SYNTAX	RifEntry
	ACCESS	not-accessible
	STATUS	mandatory
	DESCRIPTION
		"A single entry in the RIF table."
	INDEX	{ rifPath }
	::= { rifTable 1 }

RifEntry ::= SEQUENCE {
	rifPath
		OCTET STRING,
	rifIndex
		INTEGER,
	rifInUse
		BitField,
	rifCount
		INTEGER,
	rifLength
		INTEGER,
	rifNext
		INTEGER,
	rifPrevious
		INTEGER
	}

rifPath OBJECT-TYPE
	SYNTAX	OCTET STRING (SIZE (4..28))
	ACCESS	read-only
	STATUS	mandatory
	DESCRIPTION
		"RIF field, read from left to right, i.e. read from the
		switch."
	::= { rifEntry 1 }

rifIndex OBJECT-TYPE
	SYNTAX	INTEGER
	ACCESS	read-only
	STATUS	mandatory
	DESCRIPTION
		"Index into the RIF table. This index is used to enter a
		RIF in the station table."
	::= { rifEntry 2 }

rifInUse OBJECT-TYPE
	SYNTAX	BitField
	ACCESS	read-write
	STATUS	mandatory
	DESCRIPTION
		"Indicates that this RIF entry is valid if set. A unique
		RIF entry may be deleted only if it is not in use by a
		station."
	::= { rifEntry 3 }

rifCount OBJECT-TYPE
	SYNTAX	INTEGER
	ACCESS	read-only
	STATUS	mandatory
	DESCRIPTION
		"The number stations that this RIF is associated with."
	::= { rifEntry 4 }

rifLength OBJECT-TYPE
	SYNTAX	INTEGER
	ACCESS	read-only
	STATUS	mandatory
	DESCRIPTION
		"Byte length of the RIF entry."
	::= { rifEntry 5 }

rifNext OBJECT-TYPE
	SYNTAX	INTEGER
	ACCESS	read-only
	STATUS	mandatory
	DESCRIPTION
		"Next RIF field."
	::= { rifEntry 6 }

rifPrevious OBJECT-TYPE
	SYNTAX	INTEGER
	ACCESS	read-only
	STATUS	mandatory
	DESCRIPTION
		"Previous RIF field."
	::= { rifEntry 7 }


-- SECTION 4: Configuration Modes

systemMaxPacketInfoSize OBJECT-TYPE
	SYNTAX	INTEGER (516..17800)
	ACCESS	read-write
	STATUS	mandatory
	DESCRIPTION
		"The system maximum packet information field size. 
		Changing the maximum information size
		does not take effect until the next system reset."
	::= { sysConfig 6 }

systemConfigMode OBJECT-TYPE
	SYNTAX	INTEGER {
		other (1),			-- custom configuration
		transparentSwitchingNoSTP (2),
		source-route-bridging (3),
		transparent-bridging(4),
		noVirtualRingBridging(5)	-- no bridging between Rings
		}
	ACCESS	read-write
	STATUS	mandatory
	DESCRIPTION
		"This variable describes the current mode of bridging
		configuration in the switch. The bridging mode applies to
		all ports. The value other(1) is a read-only indication that
		the system is in a user customized the system configuration.
		Setting this object will save the configuration into flash
		and issue a system reset command."
	::= { sysConfig 7 }

systemConfigIpOption OBJECT-TYPE
        SYNTAX  INTEGER {
                other (1),
                eraseIP (2),
                preservedIP (3)
        }
        ACCESS read-write
        STATUS mandatory
        DESCRIPTION
               "Reading this object always returns other(1).  Setting of
                this object, which is optional, must be accomplished in
                the same SNMP request that set systemConfigMode."
        ::= { sysConfig 29 }

maxPerfMode OBJECT-TYPE
	SYNTAX	EnableIndicator
	ACCESS	read-write
	STATUS	mandatory
	DESCRIPTION
		"The current value of the system maximum performance mode.
		Setting this value to enabled causes the system to
		perform in maximum performance mode. Default is disabled.
		This variable does not take effect until the next system
		reset."
	::= { sysConfig 8 }


-- defaultConfigReset no longer supported


configSave OBJECT-TYPE
	SYNTAX	BitField
	ACCESS	read-write
	STATUS	mandatory
	DESCRIPTION
		"Save the current configuration into flash memory.
		When read, this value is always clear (1). The value may only
		be set to the set (2) state."
	::= { sysConfig 10 }

localAdminMacAddress OBJECT-TYPE
	SYNTAX	MacAddress
	ACCESS	read-write
	STATUS	mandatory
	DESCRIPTION
		"The system's locally administered MAC address. The current
		operation MAC address may be obtained by the ifPhysAddress
		entry in the ifTable. This parameter will take effect only
		after a reset is issued."
	::= { sysConfig 12 }


configLogin OBJECT-TYPE
	SYNTAX	OCTET STRING
	ACCESS	read-write
	STATUS	mandatory
	DESCRIPTION
		"The system login object. This object is used to login
		a network management station to the system for configuration.
		The format of the login request follows:
		    login indicator.login password, 
		where the login indicator is a single byte of the value
		1 = logoff, 2 = login, or 3 = set password and the password 
		is the system password. The password must be supplied for 
		upon login or altering the password. A manager must first
		login to the system before altering the password.
		When read, the first octet is returned, indicating whether
		a managment station is currently logged in to the system."
	::= { sysConfig 13 }

configProtocol OBJECT-TYPE
	SYNTAX	INTEGER {
		flash(1),	-- config obtained via flash
		tftpNoSave(2),	-- config obtained via TFTP
		tftpSave(3)
		}
	ACCESS	read-write
	STATUS	mandatory
	DESCRIPTION
		"The protocol used to retrieve system configuration. Flash
		indicates that the configuration is read from the flash.
		tftpNoSave indicates that the TFTP protocol should be used
		to retrieve the current configuration. The new configuration
		is not saved into flash, it is up to the user to save
		the configuration is desired. The new configuration will not
		take effect until the next system reset. tftpSave indicates
		that the newly uploaded configuration will be saved into
		flash, thus may be use to permanently update a configuration.
		The system is automatically reset."
	::= { sysConfig 15 }

configFilename	OBJECT-TYPE
	SYNTAX	DisplayString (SIZE(0..255))
	ACCESS	read-write
	STATUS	mandatory
	DESCRIPTION
		"The name of the configuration file that is sent to the
		server. The actual boot protocol used to retrieve the file
		is determined by configProtocol. This parameter may be
		configured via the network boot protocol."
	::= { sysConfig 16 }

configSource	OBJECT-TYPE
	SYNTAX	INTEGER {
		flashConfig(1),	-- config obtained via flash
		remoteConfig(2)	-- config obtained via remote
		}
	ACCESS	read-only
	STATUS	mandatory
	DESCRIPTION
		"An indication of how the system was actually configured.
		flashConfig indicates that the current configuration was
		obtained via flash. remoteConfig indicates that the
		configuration was obtained via the protocol determined
		by configProtocol."
	::= { sysConfig 17 }
	
sonmpTrConfig OBJECT-TYPE
	SYNTAX   INTEGER {
		 enable(1), 
		 disable(2)
		 }
        ACCESS   read-write
	STATUS   mandatory
	DESCRIPTION
		 "The configuration status of the Token Ring auto-topology.
		 If the value of this object is set to enable(1), the
		 Token Ring auto-topology frames will be sent out on every
		 Token Ring port on every 10 seconds interval.  The auto-
		 topology frames are received from the Token Ring port and
		 logged in the database.  If the value of this object is
		 set to disable(2), no Token ring topology frames are sent
		 and received."
        ::= { sysConfig 28 }

sonmpTrSpeed OBJECT-TYPE
        SYNTAX  INTEGER {
                other(1),
                topFast(2),
                topSlow(3)
                }
        ACCESS  read-write
        STATUS  mandatory
        DESCRIPTION
                "The Token Ring topology message (SONMP frame)
                transmit speed. The values that are read/write are:
                  topFast(2)...short interval between transmitting
                  topSlow(3)...long interval between transmitting

                The value that is readonly is:
                  other(1)...speed unknown, or other value

                In fast mode, the SONMP frame transmit interval
                is 10 seconds for all SONMP frames.

                In slow mode, the interval is 60 seconds for master
                NMM announcement SONMP frames, and 70 seconds for
                adjacent SONMP frames."
        ::= { sysConfig 30 }

srUnknownFrameFlood OBJECT-TYPE
        SYNTAX  EnableIndicator
        ACCESS  read-write
        STATUS  mandatory
        DESCRIPTION
                "Unknown Source Route Frame Flood.
                 Enable/Disable flooding of Source Route Frames to
                 the next hop while the route to the remote ring
                 is being learned and circuit is established."
        ::= { sysConfig 32 }

srbIeeeBpduEnable OBJECT-TYPE
       SYNTAX  EnableIndicator
       ACCESS  read-write
       STATUS  mandatory
       DESCRIPTION
               "Send Srb/Ieee BPDU as explorer.
                Enable/Disable the sending of Srb/IEEE BPDU's as explorers,
                allowing some routers to receive the BPDU with a rif."
       ::= { sysConfig 33 }

tbRifProxyEnable OBJECT-TYPE
       SYNTAX  EnableIndicator
       ACCESS  read-write
       STATUS  mandatory
       DESCRIPTION
               "Process route descriptor LE_ARP requests in token ring
               transparent bridging LANE. Enable/Disable the processing of 
               LE_ARP requests for route descriptors when received from a 
               source route ATM attached device."
       ::= { sysConfig 34 }

cpuClkRate OBJECT-TYPE
       SYNTAX  INTEGER {
           mhz66(1),
           mhz85(2)
       }
       ACCESS  read-only
       STATUS  mandatory
       DESCRIPTION
              "MCP Clock Rate.
              Indicates the speed at which the MCP processor functions."
       ::= { sysConfig 35 }

maxRids OBJECT-TYPE
		SYNTAX INTEGER
		ACCESS read-only
		STATUS mandatory
		DESCRIPTION
			   "Maximum number of Reassembly Ids.
			   Indicates the maximum number of RIDs the switch supports. Determined
			   by the XRam installed on the ATM cards in the switch."
        ::= { sysConfig 36 }

-- SECTION 5: Network Protocol Group
--
-- This group contains information used to configure the network
-- protocols supported by the switch. Each protocol will be defined
-- by a set of object identifiers specific to the protocol.
--

-- IP Protocol Group

-- The sysAddr, sysNetMask, sysBcastAddr,
-- defaultGatewayAddr, and ipConfigProtocol
-- are deprecated by ipHostTable. Jan/1997.
--
-- The 'deprecated' status indicates that the object is
-- obsolete, but that an implementor may wish to support that
-- those objects to foster interoperability with older
-- implementations.
--

sysAddr OBJECT-TYPE 
	SYNTAX	IpAddress
	ACCESS	read-write
	STATUS	deprecated  
	DESCRIPTION
		"The system's IP address. The current operational IP
		address may be obtained by the ipAdEntAddr entry in the
		ipAddrTable. This parameter will take effect only after
		a reset is issued."
	::= { sysIpProtocol 1 }

sysNetMask OBJECT-TYPE
	SYNTAX	IpAddress
	ACCESS	read-write
	STATUS	deprecated
	DESCRIPTION
		"The system's IP subnet mask. The current operational IP
		subnet mask may be obtained by the ipAdEntNetMask entry in
		the ipAddrTable. This parameter will take effect only after
		a reset is issued. The parameter is not saved unless
		written to flash."
	::= { sysIpProtocol 2 }

sysBcastAddr OBJECT-TYPE
	SYNTAX	IpAddress
	ACCESS	read-write
	STATUS	deprecated
	DESCRIPTION
		"The system's IP broadcast address. The current operational
		IP broadcast address may be obtained by the ipAdEntBcastAddr
		in the ipAddrTable. This parameter will take effect only after
		a reset is issued. This parameter is not saved unless written
		to flash."
	::= { sysIpProtocol 3 }

defaultGatewayAddr OBJECT-TYPE
	SYNTAX	IpAddress
	ACCESS	read-write
	STATUS	deprecated
	DESCRIPTION
		"The system's default getway IP address. the current
		operational default gateway's IP address can be obtained from
		the ipRoutingTable. This parameter will take effect only
		after a reset is issued. This parameter is not saved unless
		written to flash."
	::= { sysIpProtocol 4 }

configServerAddr OBJECT-TYPE
	SYNTAX	IpAddress
	ACCESS	read-write
	STATUS	mandatory
	DESCRIPTION
		"The IP address to which the requests for configuration
		files are sent. The protocol used to retrieve the
		configuration is determined by the configProtocol object.
		This parameter may be set dynamically as established by the
		ipConfigProtocol object."
	::= { sysIpProtocol 5 }

ipConfigProtocol OBJECT-TYPE
	SYNTAX	INTEGER {
		flash(1),	-- IP information obtained via flash
		bootp(2)	-- IP information obtained via BootP
		}
	ACCESS	read-write
	STATUS	deprecated 
	DESCRIPTION
		"The protocol used to obtain this IP
		addressing information."
	::= { sysIpProtocol 6 }


ipHostNumber	OBJECT-TYPE
  	SYNTAX  INTEGER
  	ACCESS  read-only
  	STATUS  mandatory
  	DESCRIPTION
  		"The number of IP entities (regardless of
		their current state) present on this system."
  	::= { sysIpProtocol 7 }


ipHostTable	OBJECT-TYPE
  	SYNTAX	SEQUENCE OF IpHostEntry
  	ACCESS	not-accessible
  	STATUS	mandatory
  	DESCRIPTION
		"This table contains all the ip entities this
		agent manages. The number of entries is
		given by the value of ipHostNumber."
		::= { sysIpProtocol 8 }


ipHostEntry	OBJECT-TYPE
	SYNTAX	IpHostEntry
	ACCESS	not-accessible
	STATUS  mandatory
	DESCRIPTION
		"An IP entity entry containing objects
		regarding this IP entity."

	INDEX	{ ipHostIndex }
	::= { ipHostTable 1 }

IpHostEntry ::=
	SEQUENCE {
	   ipHostIndex
	       INTEGER, 
           ipHostAddress 
	       IpAddress, 
	   ipHostNetMask
	       IpAddress,
	   ipHostBcastAddr
	       IpAddress,
	   ipHostDefaultGatewayAddr
	       IpAddress, 
	   ipHostConfigProtocol
	       INTEGER,
	   ipHostEnable 
	       INTEGER, 
	   ipHostType
	       INTEGER 
	}


  ipHostIndex	OBJECT-TYPE
  	SYNTAX	INTEGER
  	ACCESS  read-write
  	STATUS  mandatory
  	DESCRIPTION
  		"An index to the ipHostTable. Its value ranges
  		between 1 and the value of ipHostNumber."
		 
  	::= { ipHostEntry 1 }


ipHostAddress 	OBJECT-TYPE 
	SYNTAX	IpAddress
	ACCESS	read-write
	STATUS	mandatory
	DESCRIPTION
		"The IP address of this entity."
        ::= { ipHostEntry 2 }


ipHostNetMask 	OBJECT-TYPE 
	SYNTAX	IpAddress
	ACCESS	read-write
	STATUS	mandatory
	DESCRIPTION
		"The subnet mask associated with the Ip
		address of this entry."
        ::= { ipHostEntry 3 }

ipHostBcastAddr	OBJECT-TYPE 
	SYNTAX	IpAddress
	ACCESS	read-write
	STATUS	mandatory
	DESCRIPTION
		"The Broadcast address associated with the
		IP address of this entry."
        ::= { ipHostEntry 4 }

ipHostDefaultGatewayAddr   OBJECT-TYPE 
	SYNTAX	IpAddress
	ACCESS	read-write
	STATUS  mandatory	
	DESCRIPTION
		"The gateway address associated with the IP address of
		this entry."
        ::= { ipHostEntry 5 }

ipHostConfigProtocol	OBJECT-TYPE
	SYNTAX	INTEGER {
		flash(1),	--this Ip information obtained via flash.
		bootp(2) 	--this IP information obtained via BootP.
		}
	ACCESS  read-write
	STATUS  mandatory
	DESCRIPTION
		"The protocol used to obtain this IP
		host's addressing information."
	::= { ipHostEntry 6 }


ipHostEnable	OBJECT-TYPE
	SYNTAX  INTEGER {
		enable (1),
		disable(2)
		}
	ACCESS  read-write
	STATUS  mandatory
	DESCRIPTION
		"Enable or disable of this ip host entry."
	::= { ipHostEntry 7 }


 ipHostType	OBJECT-TYPE
	SYNTAX	INTEGER {
		primary(1),
		secondary(2)
		}
	ACCESS  read-only 
	STATUS  mandatory
	DESCRIPTION
		"A read only object indicating the type of
		this IP entity. "
	::= { ipHostEntry 8}



-- SECTION 6: TFTP Protocol Group
--
-- Implementation of the sysTFTP group is mandatory for all agent
-- products that support TFTP file transfers.
-- 
-- The sysTFTP Group is used by a station to initiate a TFTP transfer
-- from a TFTP server to this system (the TFTP client).  
--
-- In order to initiate a TFTP file transfer, the client must know
-- the following information:
--
-- 1. The operation to perform, either a get or a put (sysTFTPStart).
-- 2. What station is acting as the TFTP server (sysTFTPIpAddress).
-- 3. The file name (sysTFTPFileName) and the file type (sysTFTPFileType).
--        The file name can be a pathname.  The file type indicates to
--	  the agent what kind of information is being transferred.
-- 4. What module should receive the file (sysTFTPSlot).
--
--
-- For example, if one wished to inband download flash code to this agent,
-- one would set:
--
-- File type 	= Flash code
-- File name    = Pathname on the server where the file is located.
-- IP Address   = The IP of the TFTP file server.
-- TFTP Start   = get - retrieve the file from the server.
--
-- After setting the start object, the transfer takes place.  The  
-- sysTFTPResult object contains the result of the last TFTP transfer
-- attempted.
-- 

sysTFTPStart OBJECT-TYPE
	SYNTAX INTEGER {
		tftpNoTransfer(1),
		tftpGet(2),	-- download to agent
		tftpPut(3)	-- upload to server
		}
	ACCESS read-write
	STATUS mandatory
	DESCRIPTION
		"Setting sysTFTPStart to tftpGet(2) initiates a file
		transfer to the agent (download); tftpPut(3) initiates
		a file transfer to the server (upload)."
	::= { sysTFTPGroup 1 }

sysTFTPIpAddress OBJECT-TYPE
	SYNTAX IpAddress
	ACCESS read-write
	STATUS mandatory
	DESCRIPTION
		"The IP Address of the TFTP server."
	::= { sysTFTPGroup 2 }

sysTFTPFileName OBJECT-TYPE
	SYNTAX DisplayString (SIZE(0..255))
	ACCESS read-write
	STATUS mandatory
	DESCRIPTION
		"The file name of the file to retrieve (tftpGet), or the 
		name of	the file to create (tftpPut). "
	::= { sysTFTPGroup 3 }


sysTFTPFileType OBJECT-TYPE
	SYNTAX INTEGER {
		configuration(1),
		imageCode(2)
--		bootCode(3)
		}
	ACCESS read-write
	STATUS mandatory
	DESCRIPTION
		"The type of file image to upload/download.  The file
		type indicates to the agent what kind of file it is
		receiving.  configuration(1) indicates an update of the
		system configuration. imageCode(2) indicates a code upgrade of
		the operational proms.  bootCode(3) indicates a code
		upgrade of the boot proms."
	::= { sysTFTPGroup 4 }


sysTFTPResult OBJECT-TYPE
	SYNTAX INTEGER {
		clear(1),		--not initialized
		xferInProgress(2),
		okay(3),
		otherTFTPError(4),
		fileNotFound(5),	-- check for valid file name
		accessError(6),
		diskFull(7),		-- server disk is full
 		illegalTFTPOperation(8),
		invalidTFTPTransactionID(9),
		fileExists(10),		-- file already exists
		noSuchUser(11),		-- no such user
		noResources(12),	-- no resources to start
		noResponse(13),		-- check valid server IP address
		flashError(14),		-- flash programming error
		configMismatch(15),	-- configuration mismatch
		configChecksumError(16)	-- configuration checksum error
		}	
	ACCESS read-only
	STATUS mandatory
	DESCRIPTION
		"The result of the last TFTP operation."
	::= { sysTFTPGroup 5 }


-- SECTION 7: SNMP Group
--
-- The objects in this groups allow a management station control of the
-- SNMP elements of the system.
--

sysSNMPGetCommunity OBJECT-TYPE
	SYNTAX	DisplayString (SIZE(0..30))
	ACCESS	read-write
	STATUS	mandatory
	DESCRIPTION
		"The system get community string."
	::= { sysSNMPGroup 1 }

sysSNMPSetCommunity OBJECT-TYPE
	SYNTAX	DisplayString (SIZE(0..30))
	ACCESS	read-write
	STATUS	mandatory
	DESCRIPTION
		"The system set community string."
	::= { sysSNMPGroup 2 }

sysSNMPEnableTraps OBJECT-TYPE
	SYNTAX	EnableIndicator
	ACCESS	read-write
	STATUS	mandatory
	DESCRIPTION
		"Indicates whether the SNMP agent process is permitted
		to generate traps. This object provides global trap
		enable status, as specific traps may be enabled or disabled
		on an individual basis."
	::= { sysSNMPGroup 3 }

sysSNMPTrapIPReceiverTable OBJECT-TYPE
	SYNTAX	SEQUENCE OF SysSNMPTrapIPReceiverEntry
	ACCESS	not-accessible
	STATUS	mandatory
	DESCRIPTION
		"A table containing of network management stations that are
		to receive traps generated by the system."
	::= { sysSNMPGroup 4 }

sysSNMPTrapIPReceiverEntry OBJECT-TYPE
	SYNTAX	SysSNMPTrapIPReceiverEntry
	ACCESS	not-accessible
	STATUS	mandatory
	DESCRIPTION
		"A destination address and community string to a particular
		IP trap server. Entries are created by supplying a valid IP
		address of the trap server."
	INDEX	{ trapIPRcvrAddress }
	::= { sysSNMPTrapIPReceiverTable 1 }

SysSNMPTrapIPReceiverEntry ::= SEQUENCE {
	trapIPRcvrAddress
		IpAddress,
	trapIPRcvrStatus
		StatusIndicator,
	trapIPRcvrCommunity
		DisplayString
	}

trapIPRcvrAddress OBJECT-TYPE
	SYNTAX	IpAddress
	ACCESS	read-write
	STATUS	mandatory
	DESCRIPTION
		"The IP network address of the network management entity
		which will receive traps."
	::= { sysSNMPTrapIPReceiverEntry 1 }

trapIPRcvrStatus OBJECT-TYPE
	SYNTAX	StatusIndicator
	ACCESS	read-write
	STATUS	mandatory
	DESCRIPTION
		"Setting this object to the value invalid(2) has the effect
		of invalidating the corresponding entry in the 
		sysSNMPReceiverTrapTable. On a read, the value of valid(2) 
		is returned. Entries are added into the table by specifying
		a previously unknown trapRcvrNetAddress, along with the
		corresponding trapRcvrCommunity."
	::= { sysSNMPTrapIPReceiverEntry 2 }

trapIPRcvrCommunity OBJECT-TYPE
	SYNTAX	DisplayString (SIZE (0..30))
	ACCESS	read-write
	STATUS	mandatory
	DESCRIPTION
		"The community string to use for traps sent to this trap
		receiver."
	::= { sysSNMPTrapIPReceiverEntry 3 }

sysMgmtRingNumber OBJECT-TYPE
	SYNTAX	INTEGER (0..4095)
	ACCESS	read-write
	STATUS	mandatory
	DESCRIPTION
		"A unique ring number assigned to the system's managment
		entity. This ring will not appear as a source-route hop
		as it is seen only in frames destined to or sourced from
		the system management entity."
	::= { sysConfig 20 }

--
-- The NetBIOS Group
--
-- This group contains NetBIOS information on a system wide basis.

netbiosNameTableAgingTimer OBJECT-TYPE
	SYNTAX	INTEGER
	ACCESS	read-write
	STATUS	mandatory
	DESCRIPTION
		"The non-zero timeout period in seconds for aging out
		dynamically learned Netbios names. The default value
		is 300 seconds."
	::= { netbiosGroup 1 }

netbiosNameQueryInterval OBJECT-TYPE
	SYNTAX	INTEGER (0..255)
	ACCESS	read-write
	STATUS	mandatory
	DESCRIPTION
		"The time period in hundreds of milliseconds in which
		NetBIOS name queries are allowed to be bridged. A value of
		0 disables briding NetBIOS name queries. The default value
		is 5 (a half second)."
	::= { netbiosGroup 2 }

netbiosNameTableFlush OBJECT-TYPE
	SYNTAX	BitField
	ACCESS	read-write
	STATUS	mandatory
	DESCRIPTION
		"If set, indicates that the NetBIOS name table should be
		flushed. Flushing the table removes all of the dynamically
		learned entries from the NetBIOS name table. When read,
		this object always returns a value of clear."
	::= { netbiosGroup 3 }

netbiosNameTableEntry OBJECT-TYPE
	SYNTAX	SEQUENCE OF NetbiosNameEntry
	ACCESS	not-accessible
	STATUS	deprecated
	DESCRIPTION
		"A NetBIOS name table. This table is a list of the NetBIOS
		names learned or configured on the switch."
	::= { netbiosGroup 4 }

netbiosNameEntry OBJECT-TYPE
	SYNTAX	NetbiosNameEntry
	ACCESS	not-accessible
	STATUS	deprecated
	DESCRIPTION
		"A NetBIOS name table entry. Entries may be deleted by
		setting the status object to invalid (2). Entries are added
		by specifying the name, station and ring or card/port as
		appropriate."
	INDEX { netbiosNameName }
	::= { netbiosNameTableEntry 1 }

NetbiosNameEntry ::= SEQUENCE {
	netbiosNameName
		DisplayString,
	netbiosNameStatus
		StatusIndicator,
	netbiosNameStationAddress
		PhysAddress,
	netbiosNameVirtualRingNumber
		INTEGER,
	netbiosNameCardNumber
		INTEGER,
	netbiosNamePortNumber
		INTEGER,
	netbiosNamePortType
		INTEGER,
	netbiosNameAge
		TimeTicks,
	netbiosNameProxies
		Counter,
	netbiosNameSuppressedQueries
		Counter
	}

netbiosNameName OBJECT-TYPE
	SYNTAX	DisplayString (SIZE(15))
	ACCESS	read-only
	STATUS	deprecated
	DESCRIPTION
		"The NetBIOS name."
	::= { netbiosNameEntry 1 }

netbiosNameStatus OBJECT-TYPE
	SYNTAX	StatusIndicator
	ACCESS	read-only
	STATUS	deprecated
	DESCRIPTION
		"The status of the NetBIOS name entry. Setting this object to
		invalid (2) causes the entry to be deleted from the name
		table. The value should always be read as valid(1)."
	::= { netbiosNameEntry 2 }

netbiosNameStationAddress OBJECT-TYPE
	SYNTAX	PhysAddress (SIZE(6))
	ACCESS	read-only
	STATUS	deprecated
	DESCRIPTION
		"The address of the station from which this name was
		learned or configured. This object must be specified when
		adding an entry into the table."
	::= { netbiosNameEntry 3 }

netbiosNameVirtualRingNumber OBJECT-TYPE
	SYNTAX	INTEGER
	ACCESS	read-only
	STATUS	deprecated
	DESCRIPTION
		"The virtual ring number from which the entry was learned or 
		configured. If the switch is operating is a mode where
		virtual rings are invalid, then this number will be 0. This
		object must be specified when adding an entry in the table
		if appropriate."
	::= { netbiosNameEntry 4 }

netbiosNameCardNumber OBJECT-TYPE
	SYNTAX	INTEGER
	ACCESS	read-only
	STATUS	deprecated
	DESCRIPTION
		"The card number from which the entry was learned or 
		configured. If the switch is operating is a mode where
		virtual rings are valid, then this number will be 0. This
		object must be specified when adding an entry in the table
		if appropriate."
	::= { netbiosNameEntry 5 }

netbiosNamePortNumber OBJECT-TYPE
	SYNTAX	INTEGER
	ACCESS	read-only
	STATUS	deprecated
	DESCRIPTION
		"The port number from which the entry was learned or 
		configured. If the switch is operating is a mode where
		virtual rings are valid, then this number will be 0. This
		object must be specified when adding an entry in the table
		if appropriate."
	::= { netbiosNameEntry 6 }

netbiosNamePortType OBJECT-TYPE
	SYNTAX	INTEGER {
		other(1),
		token-ring(2),
		fddi(3),
		ethernet(4),
		atm(5)
		}
	ACCESS	read-only
	STATUS	deprecated
	DESCRIPTION
		"The type of port from which the entry was learned or 
		configured."
	::= { netbiosNameEntry 7 }

netbiosNameAge OBJECT-TYPE
	SYNTAX	TimeTicks
	ACCESS	read-only
	STATUS	deprecated
	DESCRIPTION
		"The amount of time (in hundredths of a second) before
		this entry is aged, or the elapsed time since the
		entry was learned or configured."
	::= { netbiosNameEntry 8 }

netbiosNameProxies OBJECT-TYPE
	SYNTAX	Counter
	ACCESS	read-only
	STATUS	deprecated
	DESCRIPTION
		"The number of times that the switch has proxied for
		this station."
	::= { netbiosNameEntry 9 }

netbiosNameSuppressedQueries OBJECT-TYPE
	SYNTAX	Counter
	ACCESS	read-only
	STATUS	deprecated
	DESCRIPTION
		"The number of NetBIOS name queries from this station
		which were suppressed by the switch due to the configured
		name query interval (netbiosNameQueryInterval)"
	::= { netbiosNameEntry 10 }

cnnetbiosNameTableEntry OBJECT-TYPE
        SYNTAX  SEQUENCE OF CnnetbiosNameEntry
        ACCESS  not-accessible
        STATUS  mandatory
        DESCRIPTION
                "A NetBIOS name table with VLAN information. This table is
                a list of the NetBIOS
                names learned or configured on the switch."
        ::= { netbiosGroup 5 }
 
cnnetbiosNameEntry OBJECT-TYPE
        SYNTAX  CnnetbiosNameEntry
        ACCESS  not-accessible
        STATUS  mandatory
        DESCRIPTION
                "A NetBIOS name table entry. Entries may be deleted by
                setting the status object to invalid (2). Entries are added
                by specifying the name, station, ring or card/port, vlan
                id as appropriate."
        INDEX { cnnetbiosNameVlanId, cnnetbiosNameName }
        ::= { cnnetbiosNameTableEntry 1 }
 
CnnetbiosNameEntry ::= SEQUENCE {
        cnnetbiosNameName
                DisplayString,
        cnnetbiosNameStatus
                StatusIndicator,
        cnnetbiosNameStationAddress
                PhysAddress,
        cnnetbiosNameVirtualRingNumber
                INTEGER,
        cnnetbiosNameCardNumber
                INTEGER,
        cnnetbiosNamePortNumber
                INTEGER,
        cnnetbiosNameVlanId
                VlanId,
        cnnetbiosNamePortType
                INTEGER,
        cnnetbiosNameAge
                TimeTicks,
        cnnetbiosNameProxies
                Counter,
        cnnetbiosNameSuppressedQueries
                Counter
        }
 
cnnetbiosNameName OBJECT-TYPE
        SYNTAX  DisplayString (SIZE(15))
        ACCESS  read-only
        STATUS  mandatory
        DESCRIPTION
                "The NetBIOS name."
        ::= { cnnetbiosNameEntry 1 }
 
cnnetbiosNameStatus OBJECT-TYPE
        SYNTAX  StatusIndicator
        ACCESS  read-only
        STATUS  mandatory
        DESCRIPTION
                "The status of the NetBIOS name entry. Setting this object to
                invalid (2) causes the entry to be deleted from the name
                table. The value should always be read as valid(1)."
        ::= { cnnetbiosNameEntry 2 }
 
cnnetbiosNameStationAddress OBJECT-TYPE
        SYNTAX  PhysAddress (SIZE(6))
        ACCESS  read-only
        STATUS  mandatory
        DESCRIPTION
                "The address of the station from which this name was
                learned or configured. This object must be specified when
                adding an entry into the table."
        ::= { cnnetbiosNameEntry 3 }
 
cnnetbiosNameVirtualRingNumber OBJECT-TYPE
        SYNTAX  INTEGER
        ACCESS  read-only
        STATUS  mandatory
        DESCRIPTION
                "The virtual ring number from which the entry was learned or
                configured. If the switch is operating is a mode where
                virtual rings are invalid, then this number will be 0.  This
                object must be specified when adding an entry in the table
                if appropriate."
        ::= { cnnetbiosNameEntry 4 }
 
cnnetbiosNameCardNumber OBJECT-TYPE
        SYNTAX  INTEGER
        ACCESS  read-only
        STATUS  mandatory
        DESCRIPTION
                "The card number from which the entry was learned or
                configured. If the switch is operating is a mode where
                virtual rings are valid, then this number will be 0.  This
                object must be specified when adding an entry in the table
                if appropriate."
        ::= { cnnetbiosNameEntry 5 }

cnnetbiosNamePortNumber OBJECT-TYPE
        SYNTAX  INTEGER
        ACCESS  read-only
        STATUS  mandatory
        DESCRIPTION
                "The port number from which the entry was learned or
                configured. If the switch is operating is a mode where
                virtual rings are valid, then this number will be 0.  This
                object must be specified when adding an entry in the table
                if appropriate."
        ::= { cnnetbiosNameEntry 6 }
 
cnnetbiosNameVlanId OBJECT-TYPE
        SYNTAX  VlanId
        ACCESS  read-only
        STATUS  mandatory
        DESCRIPTION
                "The 802.1q vid for the VLan from which the entry was
                learned or configured. This object must be specified
                when adding an entry in the table if appropriate."
        ::= { cnnetbiosNameEntry 7 }
 
cnnetbiosNamePortType OBJECT-TYPE
        SYNTAX  INTEGER {
                other(1),
                token-ring(2),
                fddi(3),
                ethernet(4),
                atm(5)
                }
        ACCESS  read-only
        STATUS  mandatory
        DESCRIPTION
                "The type of port from which the entry was learned or
                configured."
        ::= { cnnetbiosNameEntry 8 }
 
cnnetbiosNameAge OBJECT-TYPE
        SYNTAX  TimeTicks
        ACCESS  read-only
        STATUS  mandatory
        DESCRIPTION
                "The amount of time (in hundredths of a second) before
                this entry is aged, or the elapsed time since the
                entry was learned or configured."
        ::= { cnnetbiosNameEntry 9 }
 
cnnetbiosNameProxies OBJECT-TYPE
        SYNTAX  Counter
        ACCESS  read-only
        STATUS  mandatory
        DESCRIPTION
                "The number of times that the switch has proxied for
                this station."
        ::= { cnnetbiosNameEntry 10 }
 
cnnetbiosNameSuppressedQueries OBJECT-TYPE
        SYNTAX  Counter
        ACCESS  read-only
        STATUS  mandatory
        DESCRIPTION
                "The number of NetBIOS name queries from this station
                which were suppressed by the switch due to the configured
                name query interval (netbiosNameQueryInterval)"
        ::= { cnnetbiosNameEntry 11 }


 --
 -- The LAN Network Manager (LNM) Group
 --
 -- This group contains LAN Network Manager information on a system wide basis.
 
 lnmOperStatus OBJECT-TYPE
     SYNTAX INTEGER {
         up(1),
         down(2),
         other(3)
         }
     ACCESS read-only
     STATUS mandatory
     DESCRIPTION
         " This object reflects the actual  
         state of LNM which  may differ  
         from that of the lnmAdminStatus
         object. This can occur when    
         the LNM task has failed but the
         the corresponding lnmAdminStatus 
 	is 'up'."
     ::= { lnmGroup 1 }
 
 lnmAdminStatus OBJECT-TYPE
     SYNTAX INTEGER {
         up(1),
         down(2)
         }
     ACCESS read-write
     STATUS mandatory
     DESCRIPTION
         "The desired  state of the LNM on 
         the switch as prescribed by the 
         operator.   The actions of the agent
         will,  if  at all possible,  eventually  
         result in the desired  state being 
         reflected in the lnmOperStatus."
     DEFVAL { down }
     ::= { lnmGroup 2 }
 
 lnmBridgeGroupDisplayMode OBJECT-TYPE
     SYNTAX INTEGER {
         aggregate(1),
         separate(2)
         }
     ACCESS read-write
     STATUS mandatory
     DESCRIPTION
         "Indicates how LNM should display 
         spanning tree groups. If set to aggregate,
 	 LNM displays all spanning tree groups as
 	 one internal management ring.
 	 If set to separate, LNM displays
 	 each spanning tree group as a separate
         internal management ring."
     DEFVAL { aggregate }
     ::= { lnmGroup 3 }

 lnmLinkPassword OBJECT-TYPE
    SYNTAX EnableIndicator
    ACCESS read-write
    STATUS mandatory
    DESCRIPTION
        "Indicates the use of the default LNM management
        password or the first 6 to 8 characters of the 
        system password."
    ::= { lnmGroup 4 }
END
-- SECTION 1: Top Level Definitions


CENTILLION-DOT3-EXTENSIONS-MIB DEFINITIONS ::= BEGIN

-- Centillion IEEE 802.3 Ethernet Extensions MIB Release 2.0.0
-- Revision 05/16/96

-- Copyright 1996 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
        Gauge
                FROM RFC1155-SMI
	OBJECT-TYPE
		FROM RFC-1212
	extensions
		FROM CENTILLION-ROOT-MIB;


-- Groups

cnDot3Extensions OBJECT IDENTIFIER ::= { extensions 4 }


-- SECTION 2: Ethernet Extensions Table

cnDot3ExtnTable OBJECT-TYPE
	SYNTAX  SEQUENCE OF CnDot3ExtnEntry
	ACCESS  not-accessible
	STATUS  mandatory
	DESCRIPTION
		"This table contains Ethernet interface
                parameters and state variables, one entry
                per 802.3 interface."
	::= { cnDot3Extensions 1 }

cnDot3ExtnEntry OBJECT-TYPE
	SYNTAX  CnDot3ExtnEntry
	ACCESS  not-accessible
	STATUS  mandatory
	DESCRIPTION
		"A list of Ethernet status and parameter
        	 values for an 802.3 interface."
	INDEX   { cnDot3ExtnIfIndex }
	::= { cnDot3ExtnTable 1 }

CnDot3ExtnEntry ::= SEQUENCE {
	cnDot3ExtnIfIndex
		INTEGER,
	cnDot3ExtnIfAdminSpeed
		INTEGER,
	cnDot3ExtnIfOperSpeed
		Gauge,
	cnDot3ExtnIfAdminConnectionType
		INTEGER,
	cnDot3ExtnIfOperConnectionType
		INTEGER
	}

cnDot3ExtnIfIndex OBJECT-TYPE
	SYNTAX  INTEGER
	ACCESS  read-only
	STATUS  mandatory
	DESCRIPTION
		"The value of this object identifies the
		802.3 interface for which this entry
		contains management information. 
		This value should same as the Ifindex 
		in the interface table"
	::= { cnDot3ExtnEntry 1 }

cnDot3ExtnIfAdminSpeed OBJECT-TYPE
	SYNTAX	INTEGER {
		forced10(1),   -- forced 10Mbps
		forced100(2),  -- forced 100Mbps
		auto(3),       -- auto 10/100
		forced1000(4)  -- forced 1000Mbps 
		}
	ACCESS	read-write
	STATUS	mandatory
	DESCRIPTION
		"The configured speed of the interface.
		The default value for 10 Mbps interfaces is
		forced10(1).  The default value for 100 Mbps
		interfaces is auto(3). "
	::= { cnDot3ExtnEntry 2 }

cnDot3ExtnIfOperSpeed OBJECT-TYPE
	SYNTAX	Gauge
	ACCESS	read-only
	STATUS	mandatory
	DESCRIPTION
		"The operational speed of the interface in bits per
                second."
	::= { cnDot3ExtnEntry 3 }

cnDot3ExtnIfAdminConnectionType OBJECT-TYPE
	SYNTAX	INTEGER {
		halfDuplex(1),   -- forced half duplex
		fullDuplex(2),   -- forced full duplex 
		auto(3)          -- auto half/full duplex
		}
	ACCESS	read-write
	STATUS	mandatory
	DESCRIPTION
		"The administration connection type of the interface."
	::= { cnDot3ExtnEntry 4 }

cnDot3ExtnIfOperConnectionType OBJECT-TYPE
	SYNTAX	INTEGER {
		halfDuplex(1),   -- forced half duplex
		fullDuplex(2)    -- forced full duplex 
		}
	ACCESS	read-only
	STATUS	mandatory
	DESCRIPTION
		"The operational connection type of the interface."
	::= { cnDot3ExtnEntry 5 }

END
-- SECTION 1: Top Level Definitions


CENTILLION-DOT5-EXTENSIONS-MIB DEFINITIONS ::= BEGIN


-- Centillion IEEE 802.5 Token Ring Extensions MIB Release 2.0.1
-- Revision 03/20/96

-- Copyright 1994-96 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	OBJECT-TYPE
		FROM RFC-1212
	extensions, EnableIndicator
		FROM CENTILLION-ROOT-MIB;


-- Textual Conventions

-- The following identifies the configuration of the ring port.

TrPortConnType ::=
	INTEGER {
		trPortDTR(1),		-- port has a direct connection to
					-- a ring station

		tr4PortStation(2),	-- port is a standard ring station

		trPortRiRoPhantom(3),	-- port is connected to Ring-In or
					-- Ring-Out of a MAU and provides
					-- phantom drive

		trPortRiRoNoPhantom(4), -- port is Ring-In/Ring-Out and
					-- does not provide phantom drive

                trPortHub(16),		-- detects phantom, NICs attached
					-- to port

                trPortStation(17),	-- sources phantom, attached to a
					-- concentrator port

                trPortBay_Ro(18),	-- connects to a Bay Hub RI port,
					-- sources phantom

                trPortBay_Ri(19),	-- connects to a Bay Hub RO port,
					-- detects phantom

                trPortOther_Ro(20),	-- connects to a non-Bay Hub RI
					-- port, detects phantom

                trPortOther_Ri(21),	-- connects to a non-Bay Hub RO
					-- port, source phantom

                trPortFdtr_hub(22),	-- full duplex stations attached
					-- to port, detects phantom

                trPortFdtr_station(23),	-- full duplex, sources phantom,
					-- used for inter-switch link

                trPortAutoStationHub(24)     -- Automatically determines
                                             -- Station or hub connection type
	}


-- Groups

cnDot5Extensions OBJECT IDENTIFIER ::= { extensions 3 }



-- SECTION 2: MIB Objects


-- Centillion Token Ring Extensions Table

cnDot5ExtnTable OBJECT-TYPE
	SYNTAX  SEQUENCE OF CnDot5ExtnEntry
	ACCESS  not-accessible
	STATUS  mandatory
	DESCRIPTION
		"This table contains Token Ring interface
                parameters and state variables, one entry
                per 802.5 interface."
	::= { cnDot5Extensions 1 }

cnDot5ExtnEntry OBJECT-TYPE
	SYNTAX  CnDot5ExtnEntry
	ACCESS  not-accessible
	STATUS  mandatory
	DESCRIPTION
		"A list of Token Ring status and parameter
                values for an 802.5 interface."
	INDEX   { cnDot5ExtnIfIndex }
	::= { cnDot5ExtnTable 1 }

CnDot5ExtnEntry ::= SEQUENCE {
	cnDot5ExtnIfIndex
		INTEGER,
	cnDot5ExtnPortConnType
		TrPortConnType,
	cnDot5ExtnPortSpeedSense
		EnableIndicator,
	cnDot5ExtnAdminRingSpeed
		INTEGER

	}

cnDot5ExtnIfIndex OBJECT-TYPE
	SYNTAX  INTEGER
	ACCESS  read-only
	STATUS  mandatory
	DESCRIPTION
		"The value of this object identifies the
		802.5 interface for which this entry
		contains management information.  The
		value of this object for a particular
		interface has the same value as the
		ifIndex object, defined in [4,6],
		for the same interface."
	::= { cnDot5ExtnEntry 1 }

cnDot5ExtnPortConnType OBJECT-TYPE
	SYNTAX	TrPortConnType
	ACCESS	read-write
	STATUS	mandatory
	DESCRIPTION
		"The type of connection used on this port. Setting a value
                to this object requires the port to be reset and re-opened
                before taking effect. Allowable	connections for TR4 are:
		Station - (default for TR4) the port is configured as a 
		  	  standard ring station,
		Ring-In/Ring-Out - the port is connected to the Ring-In
                                   or Ring-Out port of a MAU with an
                                   appropriate cable.
                DTR - the port has a direct connection to a ring station.

                A different set of connection type for TR8 are :
		Hub, Station, Bay/SNPX RO, Bay/SNPX RI, Other RO,
		Other RI, FDTR Hub, FDTR Station"
	::= { cnDot5ExtnEntry 2 }

cnDot5ExtnPortSpeedSense OBJECT-TYPE
	SYNTAX	EnableIndicator
	ACCESS	read-write
	STATUS	mandatory
	DESCRIPTION
		"Indicates whether speed sensing is enabled (default),
		or disabled on the port. This is used in conjuection with
		the RingSpeed to either match or force to the configured
		speed."
	::= { cnDot5ExtnEntry 3 }

cnDot5ExtnAdminRingSpeed OBJECT-TYPE
	SYNTAX	INTEGER {
		autoDetect(1),
		forceFourMegabit(2),
		forceSixteenMegabit(3),
		matchFourMegabit(4),
		matchSixteenMegabit(5),
		force32Megabit(6),
		autoDetect16or32(7),
		autoDetect4or16or32(8)
		}
	ACCESS	read-write
	STATUS	mandatory
	DESCRIPTION
		"The configured ring speed of the port. The speed will take
		effect on the next opening of the ring. The speeds of
		'force' indicates that the port should enter the ring
		regardless of the current ring speed. The 'match' speeds
		indcate the the port should insert at the configured speed,
		only if the current ring speed matches the port speed.
		The operational ring speed may be obtained by the usual
		dot5RingSpeed object. The 'auto detect' indicates that the
		ring detect and insert at the current ring speed."
	::= { cnDot5ExtnEntry 4 }



-- Centillion 5000 Token Ring Extention Table

cnS5TrExtnTable OBJECT-TYPE
        SYNTAX  SEQUENCE OF CnS5TrExtnEntry
        ACCESS  not-accessible
        STATUS  mandatory
        DESCRIPTION
                "This table contains additional Token Ring interface
                parameters and state variables, one entry per
                802.5 interface for 5000BH token ring cards."
        ::= { cnDot5Extensions 2 }
 
cnS5TrExtnEntry OBJECT-TYPE
        SYNTAX  CnS5TrExtnEntry
        ACCESS  not-accessible
        STATUS  mandatory
        DESCRIPTION
                "A list of Token Ring additional status and parameter
                values for an 802.5 interface for 5000BH token ring
                cards."
        INDEX   { cnS5TrExtnIfIndex }
        ::= { cnS5TrExtnTable 1 }
 
CnS5TrExtnEntry ::= SEQUENCE {
	cnS5TrExtnIfIndex
		INTEGER,
        cnS5TrExtnFrontPortConnect
		INTEGER,	
	cnS5TrExtnOperBkplaneAtt
		INTEGER
        }

cnS5TrExtnIfIndex OBJECT-TYPE
        SYNTAX  INTEGER
        ACCESS  read-only
        STATUS  mandatory
        DESCRIPTION
                "The value of this object identifies the
                802.5 interface for which this entry
                contains management information.  The
                value of this object for a particular
                interface has the same value as the
                ifIndex object, defined in [4,6],
                for the same interface."
        ::= { cnS5TrExtnEntry 1 }

cnS5TrExtnFrontPortConnect OBJECT-TYPE
        SYNTAX  INTEGER {
		other(1),
		disable(2),
		enable(3)
		}
        ACCESS  read-write
        STATUS  mandatory
        DESCRIPTION
                "If enabled, front port insertion is allowed.  This setting
		 has no meaning other than in tr8PortHub mode."  
        ::= { cnS5TrExtnEntry 2 }

cnS5TrExtnOperBkplaneAtt OBJECT-TYPE
	SYNTAX	INTEGER {
		other(1),
		notCapable(2),
		capableAndAttached(3),
		capableAndDetached(4)
	}
	ACCESS	read-only
	STATUS	mandatory
	DESCRIPTION
		"This object returns the operating backplane 
		 attachment state of a token ring port.  For the
		 ports that do not have backplane attachment
		 capability, notCapable(2) is returned."
        ::= { cnS5TrExtnEntry 3 }


END
-- SECTION 1: Top Level Definitions


CENTILLION-FDB-MIB DEFINITIONS ::= BEGIN


-- Centillion Forwarding Database MIB Release 2.0.0
-- Revision 03/20/96

-- Copyright 1995-96 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	PhysAddress
		FROM RFC1213-MIB
	OBJECT-TYPE
		FROM RFC-1212
	CardId, PortId, StatusIndicator,
	BitField, sysConfig
		FROM CENTILLION-ROOT-MIB;


-- Textual Conventions

FdbTypeId ::= INTEGER {
		unknown(1),		-- none of the following
		token-ring(2),		-- token-ring format
		ethernet(3),		-- Ethernet format
		route-descriptor(4)	-- route descriptor
	}

VlanId ::= INTEGER(1..4095)

-- Groups

fdbGroup	OBJECT IDENTIFIER ::= { sysConfig 22 }


-- SECTION 2:	Forwarding Database Group
--
-- This group contains information relevant to the forwarding database
-- in the system.

--
-- The following textual-convention defines the station types that
-- are represented in the station table.
--

fdbRemoteAgingTimer	OBJECT-TYPE
	SYNTAX	INTEGER (10..1000000)
	ACCESS	read-write
	STATUS	mandatory
	DESCRIPTION
		"The timeout period in seconds for aging out dynamically
		learned remote (off-ring) stations. The default value is
		300 seconds."
	::= { fdbGroup 1 }

fdbTableFlush OBJECT-TYPE
	SYNTAX	OCTET STRING (SIZE(0..4))
	ACCESS	read-write
	STATUS	mandatory
	DESCRIPTION
		"When read, this object returns a zero length string.
		If set, the octets describe which stations to flush. All 
		4 octets must be specified. The encoding of the octet string
		follows:
		octet 1: the fdb type identifier to flush, unknown (1)
			 indicates flush any fdb type.
		octet 2: 0x0 to flush remote stations
			 0x1 to flush local stations
			 0x2 to flush all stations
		octet 3: the card number to flush, a value of 0xff will
			 flush all cards.
		octet 4: the port number to flush, a value of 0xff will
			 flush all ports."
	::= { fdbGroup 2 }

-- The Fdb Table
--
-- This table contains all MAC addresses in the system. Static stations
-- may be configured.

fdbTable OBJECT-TYPE
	SYNTAX	SEQUENCE OF FdbEntry
	ACCESS	not-accessible
	STATUS	deprecated
	DESCRIPTION
		"This table contains fdb information for each station
		known to the system, one entry per station. Static stations
		may be created by setting fdbStatus to be valid. The
		index of fdbStatus will contains infomation on the
		station type, stationAddress, stationCard and stationPort. 
		Entries may be subsequently modified by
		setting the appropriate object for the entry. Entries are
		deleted by clearing stationInUse."
	::= { fdbGroup 3 }

fdbEntry OBJECT-TYPE
	SYNTAX	FdbEntry
	ACCESS	not-accessible
	STATUS	deprecated
	DESCRIPTION
		"An list of station information for each station known to
		the system. Static stations may be configured by properly
		specifying at least the fdbType, fdbAddress,
		fdbCard and fdbPort."
	INDEX	{ fdbType, fdbAddress, fdbCard, fdbPort }
	::= { fdbTable 1 }


FdbEntry ::= SEQUENCE {
	fdbType
		FdbTypeId,
	fdbAddress
		PhysAddress,
	fdbCard
		CardId,
	fdbPort
		PortId,
	fdbIfIndex
		INTEGER,
	fdbStatus
		StatusIndicator,
	fdbLocal
		BitField,
	fdbStatic
		BitField,
	fdbDuplicate
		BitField,
	fdbRIFPath
		OCTET STRING
	}

fdbType OBJECT-TYPE
	SYNTAX	FdbTypeId
	ACCESS	read-only
	STATUS	deprecated
	DESCRIPTION
		"The type of the station. Station address are represented
		in the canonical form as specified by their type."
	::= { fdbEntry 1 }

fdbAddress OBJECT-TYPE
	SYNTAX	PhysAddress
	ACCESS	read-only
	STATUS	deprecated
	DESCRIPTION
		"The fdbs physical address. The physical address is
		represented in the canonical form according to the
		corresponding stationType. If the entry is a
		route-descriptor type, then the physical address is in
		the form of ring-ring-bridge."
	::= { fdbEntry 2 }

fdbCard OBJECT-TYPE
	SYNTAX	CardId
	ACCESS	read-only
	STATUS	deprecated
	DESCRIPTION
		"The card number through which this station is reached."
	::= { fdbEntry 3 }

fdbPort OBJECT-TYPE
	SYNTAX	PortId
	ACCESS	read-only
	STATUS	deprecated
	DESCRIPTION
		"The interface through which this station is reached."
	::= { fdbEntry 4 }

fdbIfIndex OBJECT-TYPE
	SYNTAX	INTEGER
	ACCESS	read-only
	STATUS	deprecated
	DESCRIPTION
		"The interface through which this station is reached. The
		value for this object identifies the instance of the ifIndex
		object defined in MIB-II. If no such entry exists, the value
		0 may be returned."
	::= { fdbEntry 5 }

fdbStatus OBJECT-TYPE
	SYNTAX	StatusIndicator
	ACCESS	read-write
	STATUS	deprecated
	DESCRIPTION
		"This indicates the validity of the station. Stations
		are added by supplying the required objects as index of
		fdbStatus, and setting the status to valid. Static stations 
		may be deleted by setting this object to invalid."
	::= { fdbEntry 6 }

fdbLocal OBJECT-TYPE
	SYNTAX	BitField
	ACCESS	read-write
	STATUS	deprecated
	DESCRIPTION
		"If set, this object indicates the station is attached to a
                 ring that is directly attached to the token ring port.
                 This object does not apply to Ethernet stations."
	::= { fdbEntry 7 }

fdbStatic OBJECT-TYPE
	SYNTAX	BitField
	ACCESS	read-only
	STATUS	deprecated
	DESCRIPTION
		"Fdb is static if this bit is set."
	::= { fdbEntry 8 }

fdbDuplicate OBJECT-TYPE
	SYNTAX	BitField
	ACCESS	read-only
	STATUS	deprecated
	DESCRIPTION
		"Indicates that another fdb with the same address was
		learned from a different card and port."
	::= { fdbEntry 9 }

fdbRIFPath OBJECT-TYPE
	SYNTAX	OCTET STRING (SIZE(0..28))
	ACCESS	read-write
	STATUS	deprecated
	DESCRIPTION
		"The RIF path to the station. The RIF Path is specified
		as being sourced from the system, as read from left-to-right.
		A RIF path is valid only for objects whose stationType
		is token-ring. The value may be a zero length string."
	::= { fdbEntry 10 }


-- Static Station Table (Read Only)
--
-- This table contains the list of user defined static stations.  All objects
-- in this table are read-only.  The columnar objects for this table are
-- the indices to the fdbTable, hence addition information pertaining to
-- such MAC address can be retrieved easily.


fdbSSTable OBJECT-TYPE
        SYNTAX  SEQUENCE OF FdbSSEntry
        ACCESS  not-accessible
        STATUS  mandatory
        DESCRIPTION
                "This table contains the list of user defined static
                 stations.  All the objects in this table are read-only
                 and are intended to aid reading static station
                 configuration."
        ::= { fdbGroup 4 }
 
fdbSSEntry OBJECT-TYPE
        SYNTAX  FdbSSEntry
        ACCESS  not-accessible
        STATUS  mandatory
        DESCRIPTION
		"This is an entry in the fdbSSTable which is indexed by
                 fdbSSIndex.  Adding to the static station list is done
                 via fdbTable.  All objects here are read-only."
        INDEX   { fdbSSIndex }
        ::= { fdbSSTable 1 }
 
 
FdbSSEntry ::= SEQUENCE {
        fdbSSIndex
                INTEGER,
        fdbSSType
                FdbTypeId,
        fdbSSAddress
                PhysAddress,
        fdbSSCard
                CardId,
        fdbSSPort
                PortId,
        fdbSSVlanId
                VlanId
        }
 
fdbSSIndex OBJECT-TYPE
        SYNTAX  INTEGER
        ACCESS  read-only
        STATUS  mandatory
        DESCRIPTION
		"This is the index to the static station table." 
        ::= { fdbSSEntry 1 }
 
fdbSSType OBJECT-TYPE
	SYNTAX	FdbTypeId
	ACCESS	read-only
	STATUS	mandatory
	DESCRIPTION
		"This represents the media type for this static station."
	::= { fdbSSEntry 2 }

fdbSSAddress OBJECT-TYPE
	SYNTAX	PhysAddress
	ACCESS	read-only
	STATUS	mandatory
	DESCRIPTION
		"This is the MAC address for this static station."
	::= { fdbSSEntry 3 }

fdbSSCard OBJECT-TYPE
	SYNTAX	CardId
	ACCESS	read-only
	STATUS	mandatory
	DESCRIPTION
		"This is the card where this station station is."
	::= { fdbSSEntry 4 }

fdbSSPort OBJECT-TYPE
	SYNTAX	PortId
	ACCESS	read-only
	STATUS	mandatory
	DESCRIPTION
		"This is the port where this station station is."
	::= { fdbSSEntry 5 }

fdbSSVlanId OBJECT-TYPE
	SYNTAX	VlanId
	ACCESS	read-only
	STATUS	mandatory
	DESCRIPTION
		"This is a vlan id of a vlan to which this static station 
		belongs to."
	::= { fdbSSEntry 6 }



-- The Fdb Table for Vlan
--
-- This table contains all MAC addresses in the system. Static stations
-- may be configured.

cnfdbTable OBJECT-TYPE
	SYNTAX	SEQUENCE OF CnfdbEntry
	ACCESS	not-accessible
	STATUS	mandatory
	DESCRIPTION
		"This table contains fdb information for each station
		known to the system, one entry per station per vlan. Static 
		stations may be created by setting fdbStatus to be valid. The
		index of fdbStatus will contains infomation on the
		station type, stationAddress, stationCard, stationPort
		and vlanId. Entries may be subsequently modified by
		setting the appropriate object for the entry. Entries are
		deleted by clearing stationInUse. Basically, this table
		is identical with the fdbTable except with fdbVlanId
		being introduced"
	::= { fdbGroup 5 }

cnfdbEntry OBJECT-TYPE
	SYNTAX	CnfdbEntry
	ACCESS	not-accessible
	STATUS	mandatory
	DESCRIPTION
		"An list of station information for each station per vlan known
		to the system. Static stations may be configured by properly
		specifying at least the cnfdbType, cnfdbAddress,
		cnfdbCard, cnfdbPort and cnfdbVlanId."
	INDEX	{ cnfdbType, cnfdbAddress, cnfdbCard, cnfdbPort, cnfdbVlanId}
	::= { cnfdbTable 1 }


CnfdbEntry ::= SEQUENCE {
	cnfdbType
		FdbTypeId,
	cnfdbAddress
		PhysAddress,
	cnfdbCard
		CardId,
	cnfdbPort
		PortId,
	cnfdbVlanId
		VlanId,
	cnfdbIfIndex
		INTEGER,
	cnfdbStatus
		StatusIndicator,
	cnfdbLocal
		BitField,
	cnfdbStatic
		BitField,
	cnfdbDuplicate
		BitField,
	cnfdbRIFPath
		OCTET STRING
	}

cnfdbType OBJECT-TYPE
	SYNTAX	FdbTypeId
	ACCESS	read-only
	STATUS	mandatory
	DESCRIPTION
		"The type of the station. Station address are represented
		in the canonical form as specified by their type."
	::= { cnfdbEntry 1 }

cnfdbAddress OBJECT-TYPE
	SYNTAX	PhysAddress
	ACCESS	read-only
	STATUS	mandatory
	DESCRIPTION
		"The fdbs physical address. The physical address is
		represented in the canonical form according to the
		corresponding stationType. If the entry is a
		route-descriptor type, then the physical address is in
		the form of ring-ring-bridge."
	::= { cnfdbEntry 2 }

cnfdbCard OBJECT-TYPE
	SYNTAX	CardId
	ACCESS	read-only
	STATUS	mandatory
	DESCRIPTION
		"The card number through which this station is reached."
	::= { cnfdbEntry 3 }

cnfdbPort OBJECT-TYPE
	SYNTAX	PortId
	ACCESS	read-only
	STATUS	mandatory
	DESCRIPTION
		"The interface through which this station is reached."
	::= { cnfdbEntry 4 }

cnfdbVlanId OBJECT-TYPE
	SYNTAX	VlanId
	ACCESS	read-only
	STATUS	mandatory
	DESCRIPTION
		"The vlan ID through which this station is reached."
	::= { cnfdbEntry 5 }

cnfdbIfIndex OBJECT-TYPE
	SYNTAX	INTEGER
	ACCESS	read-only
	STATUS	mandatory
	DESCRIPTION
		"The interface through which this station is reached. The
		value for this object identifies the instance of the ifIndex
		object defined in MIB-II. If no such entry exists, the value
		0 may be returned."
	::= { cnfdbEntry 6 }

cnfdbStatus OBJECT-TYPE
	SYNTAX	StatusIndicator
	ACCESS	read-write
	STATUS	mandatory
	DESCRIPTION
		"This indicates the validity of the station. Stations
		are added by supplying the required objects as index of
		fdbStatus, and setting the status to valid. Static stations 
		may be deleted by setting this object to invalid."
	::= { cnfdbEntry 7 }

cnfdbLocal OBJECT-TYPE
	SYNTAX	BitField
	ACCESS	read-write
	STATUS	mandatory
	DESCRIPTION
		"If set, this object indicates the station is attached to a
                 ring that is directly attached to the token ring port.
                 This object does not apply to Ethernet stations."
	::= { cnfdbEntry 8 }

cnfdbStatic OBJECT-TYPE
	SYNTAX	BitField
	ACCESS	read-only
	STATUS	mandatory
	DESCRIPTION
		"Fdb is static if this bit is set."
	::= { cnfdbEntry 9 }

cnfdbDuplicate OBJECT-TYPE
	SYNTAX	BitField
	ACCESS	read-only
	STATUS	mandatory
	DESCRIPTION
		"Indicates that another fdb with the same address was
		learned from a different card and port."
	::= { cnfdbEntry 10 }

cnfdbRIFPath OBJECT-TYPE
	SYNTAX	OCTET STRING (SIZE(0..28))
	ACCESS	read-write
	STATUS	mandatory
	DESCRIPTION
		"The RIF path to the station. The RIF Path is specified
		as being sourced from the system, as read from left-to-right.
		A RIF path is valid only for objects whose stationType
		is token-ring. The value may be a zero length string."
	::= { cnfdbEntry 11 }

END
-- SECTION 1: Top Level Definitions


CENTILLION-IF-EXTENSIONS-MIB DEFINITIONS ::= BEGIN


-- Centillion Interface Extension MIB Release 2.0.6
-- Revision 04/18/00

-- Copyright 1994-2000 Nortel Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	OBJECT-TYPE
		FROM RFC-1212
	extensions, BitField, Boolean, EnableIndicator, MacAddress
		FROM CENTILLION-ROOT-MIB
	Counter
		FROM RFC1155-SMI;


-- Groups

cnIfExtensions	OBJECT IDENTIFIER ::= { extensions 2 }


-- SECTION 2: Interface Extension Table

cnIfExtnTable OBJECT-TYPE
	SYNTAX	SEQUENCE OF CnIfExtnEntry
	ACCESS	not-accessible
	STATUS	mandatory
	DESCRIPTION
		"A list of interface entries. The numebr of entries is
		given by the value of ifNumber."
	::= { cnIfExtensions 1 }

cnIfExtnEntry OBJECT-TYPE
	SYNTAX	CnIfExtnEntry
	ACCESS	not-accessible
	STATUS	mandatory
	DESCRIPTION
		"An interface entry containing objects at the subnetwork
		layer and below for a particular interface."
	INDEX	{ cnIfExtnIndex }
	::= { cnIfExtnTable 1 }

CnIfExtnEntry ::= SEQUENCE {
	cnIfExtnIndex
		INTEGER,
	cnIfExtnCardNumber
		INTEGER,
	cnIfExtnPortNumber
		INTEGER,
	cnIfFilterEnable
		INTEGER,
	cnIfFilterDownload
		BitField,
	cnIfNetbiosNameFilteringState
		EnableIndicator,
	cnIfNetbiosBcastDiscard
		Boolean,
	cnIfNetbiosNameProxyState
		EnableIndicator,
	cnIfForwardingIdentifier
		OBJECT IDENTIFIER,
        cnIfInNoResources
		Counter,
        cnIfOutNoResources
		Counter,
	cnIfVlanMismatch
		Counter,
	cnIfVlanCapabilities
		OCTET STRING,
        cnIfExtnLocalAdminAddress
		MacAddress,
	cnIfExtnPhyAddressDefault
	    INTEGER,
    cnIfVlanTrunk
        EnableIndicator,
	cnIfUsrInDiscards
		Counter,
	cnIfUsrOutDiscards
		Counter,
    cnIfUserPriority
        INTEGER,
    cnIfTrafficClasses
        INTEGER,
    cnIfExpeditedPriorities
        OCTET STRING
	}

cnIfExtnIndex OBJECT-TYPE
	SYNTAX	INTEGER
	ACCESS	read-only
	STATUS	mandatory
	DESCRIPTION
		"A unique value for each interface corresponding to the
		ifIndex value for the same interface."
	::= { cnIfExtnEntry 1 }

cnIfExtnCardNumber OBJECT-TYPE
	SYNTAX	INTEGER
	ACCESS	read-only
	STATUS	mandatory
	DESCRIPTION
		"The card number associated with this particular interface."
	::= { cnIfExtnEntry 2 }

cnIfExtnPortNumber OBJECT-TYPE
	SYNTAX	INTEGER
	ACCESS	read-only
	STATUS	mandatory
	DESCRIPTION
		"The port number associated with this particular interface."
	::= { cnIfExtnEntry 3 }

cnIfFilterEnable OBJECT-TYPE
	SYNTAX  INTEGER {
			enableInputFiltersOnly(1),
			disableAllFilters(2),
			enableOutputFiltersOnly(3),
			enableInputAndOutputFilters(4)
			}
	ACCESS	read-write
	STATUS	mandatory
	DESCRIPTION
		"The state of filtering on this port. 
		The filter port table will become valid when 
		filters are is downloaded to the port via setting the
		cnIfFilterDownload object. In the high-perfomrance mode,
		filters will be disable on all ports execpt the management
		port."
	::= { cnIfExtnEntry 4 }

cnIfFilterDownload OBJECT-TYPE
	SYNTAX	BitField
	ACCESS	read-write
	STATUS	mandatory
	DESCRIPTION
		"Downloads the filters to the port. Value will always
		be read as zero."
	::= { cnIfExtnEntry 5 }

cnIfNetbiosNameFilteringState OBJECT-TYPE
	SYNTAX	EnableIndicator
	ACCESS	read-write
	STATUS	mandatory
	DESCRIPTION
		"The state of NetBIOS name filtering on this port. 
		Note that a port with filtering disabled may have a valid
		NetBIOS name table. The table will become valid when 
		filtering is enabled on the port."
	::= { cnIfExtnEntry 6 }

cnIfNetbiosBcastDiscard OBJECT-TYPE
	SYNTAX	Boolean
	ACCESS	read-write
	STATUS	mandatory
	DESCRIPTION
		"This indicates whether NetBIOS broadcasts are to be discarded
		on this interface."
	::= { cnIfExtnEntry 7 }

cnIfNetbiosNameProxyState OBJECT-TYPE
	SYNTAX	EnableIndicator
	ACCESS	read-write
	STATUS	mandatory
	DESCRIPTION
		"The state of NetBIOS name proxying on this port."
	::= { cnIfExtnEntry 8 }

cnIfForwardingIdentifier OBJECT-TYPE
	SYNTAX	OBJECT IDENTIFIER
	ACCESS	read-only
	STATUS	mandatory
	DESCRIPTION
		"This object references the correspsonding instance in the
		MIB object which describes the ports forwarding function.
		For example, if the port is participating in bridging, then
		this object contains the OID of the bridgeGroupPortTable.
		If this information is not present, its value is set to the
		OBJECT IDENTIFIER { 0 0 }."
	::= { cnIfExtnEntry 9 }

cnIfInNoResources  OBJECT-TYPE
	SYNTAX  Counter
	ACCESS  read-only
	STATUS  mandatory
	DESCRIPTION
		"The number of inbound packet which were dropped by the switch
                 because of lack of certain type of system resource."
	::= { cnIfExtnEntry 10 }

cnIfOutNoResources  OBJECT-TYPE
	SYNTAX  Counter
	ACCESS  read-only
	STATUS  mandatory
	DESCRIPTION
		"The number of outbound packet which were dropped by the switch
                 because of lack of certain type of system resource."
	::= { cnIfExtnEntry 11 }

cnIfVlanMismatch        OBJECT-TYPE
     	SYNTAX   Counter
     	ACCESS   read-only
     	STATUS   mandatory
     	DESCRIPTION
              	"The number of packets which were dropped due to
                the switch not being able to qualify a packet based
                on the VLAN policies defined. This object is only
                valid on  interfaces that represent LAN physical
                port."
     	::= { cnIfExtnEntry 12 }

cnIfVlanCapabilities    OBJECT-TYPE
	SYNTAX	 OCTET STRING(SIZE(1))
     	ACCESS   read-only
     	STATUS   mandatory
     	DESCRIPTION
     	   	"This object contains bit mask flags to indicate
                support for port-based VLAN, 802.1Q Tagging,
                and protocol-based VLAN on a port. Bit definition:
				bit 0:	port-based VLAN
				bit 1:	802.1Q Tagging
				bit 2:	protocol-based VLAN
				bit 3-7:future use."
     	::= { cnIfExtnEntry 13 }

cnIfExtnLocalAdminAddress OBJECT-TYPE
     	SYNTAX  MacAddress
     	ACCESS  read-write
     	STATUS  mandatory
     	DESCRIPTION
          	"The interface's locally administed address if applicable.
          	The interface's media-specific MIB must define the bit
          	and byte ordering and format of the value contained by
          	this object. For interfaces which do not have such an
          	address (e.g., a serial line), this object should
          	contain an octet string of zero length."
     	::= { cnIfExtnEntry 14}

cnIfExtnPhyAddressDefault OBJECT-TYPE
     	SYNTAX  INTEGER {
             	useDefaultPhyAddress(1),
             	useLocallyAdministeredAddress(2)
             	}
     	ACCESS  read-write
     	STATUS  mandatory
     	DESCRIPTION
          	"This object refers to which mac address is being used:
          	the default or locally administered address. The value 
		of useLocallyAdministeredAddress(2) is read-only.
		Setting this object with useDefaultPhyAddress(1) will 
		have the effect of deleting the locally administered 
		address.  It cannot be restored."
     	::= { cnIfExtnEntry 15}
 
cnIfVlanTrunk OBJECT-TYPE
        SYNTAX  EnableIndicator
        ACCESS  read-write
        STATUS  mandatory
        DESCRIPTION
            "This object controls the VLAN trunk mode for the interface.
            In trunk mode, the interface accepts both tagged and untagged
            frames in its default VLAN.  Trunk mode is only available for
            interfaces that support 802.1Q tagging, as indicated by
            cnIfVlanCapabilities.  An interface in trunk mode cannot do
            protocol-based VLAN classification.  The trunk mode cannot be
            changed while the interface belongs to an MLT group."
        ::= { cnIfExtnEntry 16 }

cnIfUsrInDiscards OBJECT-TYPE
	SYNTAX  Counter
	ACCESS  read-only
	STATUS  mandatory
	DESCRIPTION
		"The total number of inbound packets which were dropped by
		user-defined filters."
	::= { cnIfExtnEntry 17 }

cnIfUsrOutDiscards OBJECT-TYPE
	SYNTAX  Counter
	ACCESS  read-only
	STATUS  mandatory
	DESCRIPTION
		"The total number of outbound packets which were dropped by
		user-defined filters."
	::= { cnIfExtnEntry 18 }
 
cnIfUserPriority OBJECT-TYPE
    SYNTAX  INTEGER (0..7)
    ACCESS  read-write
    STATUS  mandatory
    DESCRIPTION
        "The IEEE 802.1Q default user priority associated with this
        particular interface.  All ingress frames that lack a priority
        tag are assigned this user priority.  Ethernet LAN ports and
        virtual ports can be assigned any valid user priority value.
        Token Ring LAN ports and virtual ports can only have user
        priority 0."
    ::= { cnIfExtnEntry 19 }
 
cnIfTrafficClasses OBJECT-TYPE
    SYNTAX  INTEGER
    ACCESS  read-only
    STATUS  mandatory
    DESCRIPTION
        "The number of internal traffic classes supported by this
        particular interface.  An interface with more than 1 traffic
        class supports prioritized frames."
    ::= { cnIfExtnEntry 20 }
 
cnIfExpeditedPriorities OBJECT-TYPE
    SYNTAX  OCTET STRING (SIZE(0..8))
    ACCESS  read-write
    STATUS  mandatory
    DESCRIPTION
        "The user priorities that receive expedited forwarding on
        this particular interface.  An empty octet string indicates
        that all frames forward at normal priority, regardless of the
        user priority.  Each octet in a non-empty string defines a
        user priority which receives expedited forwarding treatment.
        Ethernet LAN interfaces can be configured with expedited user
        priorities.  All other types of interfaces must always be
        configured with empty expedited priority strings."
    ::= { cnIfExtnEntry 21 }

END
-- SECTION 1: Top Level Definitions


BNET-ATM-ATOM-AUG-MIB DEFINITIONS ::= BEGIN


-- Copyright 1996 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.

-- Imports

IMPORTS

        OBJECT-TYPE
                FROM RFC-1212
	s5AtmTop
  		FROM S5-ROOT-MIB
        AtmAddr
		FROM ATM-TC-MIB           
    	ifIndex
            	FROM RFC1213-MIB
    	atmVclVpi, atmVclVci
            	FROM ATM-MIB
	atmSoftPVccLeafReference
		FROM ATM-SOFT-PVC-MIB;



-- added since not in s5 root mib...
--s5AtmTop          OBJECT IDENTIFIER ::= { series5000 14 }

bnetAtmAug     OBJECT IDENTIFIER ::= { s5AtmTop 3 }
 
bnetAtmDeviceAtmAddr  OBJECT-TYPE
    SYNTAX  AtmAddr
    ACCESS  read-only
    STATUS  mandatory
    DESCRIPTION
    "The ATM address which applies for this particular device.
    Where multiple addresses apply, include only primary one."
    ::= { bnetAtmAug 1 }

bnetAtmLearnAddrs OBJECT-TYPE
    SYNTAX  INTEGER {
        other(1),
        learnAddrs(2),
        forgetAddrs(3)
    }
    ACCESS  read-write
    STATUS  mandatory
    DESCRIPTION
	"When set to learnAddrs, atmAddrVcl and atmVclAddrBind
	tables will keep track of ATM Addresses."
    DEFVAL { learnAddrs }
    ::= { bnetAtmAug 2 }

atmfAddressClientTable OBJECT-TYPE
    SYNTAX SEQUENCE OF AtmfAddressClientEntry
    ACCESS not-accessible
    STATUS mandatory
    DESCRIPTION
        "Provides additional detail about each ATM client."
    ::= { bnetAtmAug 3 }
 
atmfAddressClientEntry OBJECT-TYPE
    SYNTAX AtmfAddressClientEntry
    ACCESS not-accessible
    STATUS mandatory
    DESCRIPTION
        "An entry with information about an ATM client."
    INDEX { atmfAddressPort, atmfAddressAtmAddress }
-- Augments atmfAddressTable FROM ATM-FORUM-ADDR-REG
    ::= { atmfAddressClientTable 1 }
 
AtmfAddressClientEntry ::= SEQUENCE {
    atmfAddressPort INTEGER,
    atmfAddressAtmAddress AtmAddr,
    atmfAddressClientType INTEGER,
    atmfAddressClientCallCount INTEGER
    }

atmfAddressPort OBJECT-TYPE
    SYNTAX INTEGER
    ACCESS read-only
    STATUS mandatory
    DESCRIPTION
	" Uni Port "
    ::= { atmfAddressClientEntry 1 }


atmfAddressAtmAddress OBJECT-TYPE
    SYNTAX AtmAddr 
    ACCESS read-only
    STATUS mandatory
    DESCRIPTION
	"ATM Address"
    ::= { atmfAddressClientEntry 2 }


atmfAddressClientType OBJECT-TYPE
    SYNTAX INTEGER {
        other(1),
        cnTurbo(2),
        cnCircuitSaver(3),
        laneTurbo(4),
        laneCircuitSaver(5),
        external(6),
	les(7),
	bus(8),
	les_bus(9),
	lecs(10),
	spvc(11)
        }
    ACCESS read-only
    STATUS mandatory
    DESCRIPTION
        "Indicates the type of client."
    DEFVAL { external }
    ::= { atmfAddressClientEntry 3 }
 
atmfAddressClientCallCount OBJECT-TYPE
    SYNTAX INTEGER
--    Rsyntax INTEGER
    ACCESS read-only
    STATUS mandatory
    DESCRIPTION
        "Indicates number of calls currently up, which
	involve this particular client address."
    ::= { atmfAddressClientEntry 4 }
 
-- This is the extension table for atmSoftPVccTable.

bnetAtmSoftPVccExtnTable OBJECT-TYPE
    SYNTAX SEQUENCE OF BnetAtmSoftPVccExtnEntry
    ACCESS not-accessible
    STATUS mandatory
    DESCRIPTION
        "The table used to maintain Soft Permanent Virtual
        Channel Connection (Soft PVCCs) circuit ids.
        The Soft PVCC table is applicable only to switches."
    ::= { bnetAtmAug 4 }

bnetAtmSoftPVccExtnEntry OBJECT-TYPE
    SYNTAX BnetAtmSoftPVccExtnEntry
    ACCESS not-accessible
    STATUS mandatory
    DESCRIPTION
	"Each entry in this table represents the circuit id of a  
	Soft Permanent Virtual Channel Connection (Soft PVCC)."
    INDEX { ifIndex, atmVclVpi, atmVclVci, atmSoftPVccLeafReference }
    ::= { bnetAtmSoftPVccExtnTable 1 }

BnetAtmSoftPVccExtnEntry ::= SEQUENCE {
    bnetAtmSoftPVccCircuitId	INTEGER
    }

bnetAtmSoftPVccCircuitId  OBJECT-TYPE
    SYNTAX INTEGER
    ACCESS read-only
    STATUS mandatory
    DESCRIPTION
	"This is the circuit id for a Soft PVCC."
    ::= { bnetAtmSoftPVccExtnEntry 1 }

END
-- SECTION 1: Top Level Definitions


CENTILLION-LESBUS-MIB DEFINITIONS ::= BEGIN


-- Centillion LANE Extention MIB Release 2.0.7
-- Revision 04/18/00

-- Copyright 1994-2000 Nortel Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	OBJECT-TYPE
		FROM RFC-1212
	lecIndex, AtmLaneAddress
		FROM LAN-EMULATION-CLIENT-MIB
	LesLocalIndex
		FROM LAN-EMULATION-LES-MIB
	TimeIntervalSec
		FROM S5-TCS-MIB
	atmLane, EnableIndicator
		FROM CENTILLION-ROOT-MIB
        lecsConfIndex
                FROM LAN-EMULATION-ELAN-MIB
    TruthValue
            FROM SNMPv2-TC-v1;

--  Groups

cnLesBusExtnGroup	OBJECT IDENTIFIER ::=	{ atmLane 1 }
cnLecExtnGroup  	OBJECT IDENTIFIER ::=	{ atmLane 2 }
cnLecsExtnGroup		OBJECT IDENTIFIER ::=	{ atmLane 3 }
atmCallRoutingConfig	OBJECT IDENTIFIER ::=	{ atmLane 4 }
cnLaneGlobalConf	OBJECT IDENTIFIER ::=	{ atmLane 5 }


-- SECTION 2: LES/BUS Extention Group

cnLesBusTable  OBJECT-TYPE
	SYNTAX	SEQUENCE OF CnLesBusEntry
	ACCESS	not-accessible
	STATUS	mandatory
	DESCRIPTION
		"smart les/bus enable and unique server id."
	::= { cnLesBusExtnGroup 1 }

cnLesBusEntry OBJECT-TYPE
	SYNTAX	CnLesBusEntry
	ACCESS	not-accessible
	STATUS	mandatory
	DESCRIPTION
		" ."
	INDEX	{ cnLesBusConfIndex }
	::= { cnLesBusTable 1 }

CnLesBusEntry ::= SEQUENCE {
	cnLesBusConfIndex
		LesLocalIndex,
	cnLesBusSmartLes
		INTEGER,
	cnLesBusServerId
		INTEGER,
	cnLesBusBusAddrSpec
		AtmLaneAddress,
	cnLesBusBusAddrActual
		AtmLaneAddress
	}

cnLesBusConfIndex OBJECT-TYPE
	SYNTAX LesLocalIndex
	ACCESS read-only
	STATUS mandatory
	DESCRIPTION
		" A value which uniquely identifies a conceptual row in the lesConfTable."
	::= {cnLesBusEntry 1}

cnLesBusSmartLes OBJECT-TYPE
	SYNTAX  INTEGER {
		enabled (1),
		disabled (2)
		}
	ACCESS read-write
	STATUS mandatory
	DESCRIPTION
		" This object is used to turn on/off smart les/bus."
	::= { cnLesBusEntry 2}

cnLesBusServerId OBJECT-TYPE
	SYNTAX INTEGER
	ACCESS read-write
	STATUS mandatory
	DESCRIPTION
		" This object specifies the unique server id among all les/bus pairs
		  that serve the same elan."
	::= {cnLesBusEntry 3}

cnLesBusBusAddrSpec OBJECT-TYPE
	SYNTAX AtmLaneAddress
	ACCESS read-write
	STATUS mandatory
	DESCRIPTION
		" The bus address."
	::= {cnLesBusEntry 4}

cnLesBusBusAddrActual OBJECT-TYPE
	SYNTAX AtmLaneAddress
	ACCESS read-only
	STATUS mandatory
	DESCRIPTION
		" The bus address."
	::= {cnLesBusEntry 5}
	
cnLesBusPeerTable OBJECT-TYPE
	SYNTAX	SEQUENCE OF CnLesBusPeerEntry
	ACCESS	not-accessible
	STATUS	mandatory
	DESCRIPTION
		"The LES/BUS peer table.  This table contains the all
		LES/BUS pairs of the ELANs managed by the agent.  The
		LES/BUS instantiated by the agent is also included
		in this table.  Other LES/BUS pairs that are not 
		running in the same system being managed by the agent
		are configured by the user.  Note that there is no
		verification protocol supported for the entries configured
		by the user."
	::= { cnLesBusExtnGroup 2 }

cnLesBusPeerEntry OBJECT-TYPE
	SYNTAX	CnLesBusPeerEntry
	ACCESS	not-accessible
	STATUS	mandatory
	DESCRIPTION
		"A pair of LES/BUS for the ELAN managed by the agent."
	INDEX	{ cnLesBusIndex, cnLesBusPeerIndex }
	::= { cnLesBusPeerTable 1 }

CnLesBusPeerEntry ::= SEQUENCE {
	cnLesBusIndex 
		LesLocalIndex,
	cnLesBusPeerIndex 
		INTEGER,
   	cnLesBusPeerLesAddr  
		AtmLaneAddress,
	cnLesBusPeerBusAddr 
		AtmLaneAddress,
	cnLesBusPeerStatus  
		INTEGER 
	}

cnLesBusIndex OBJECT-TYPE
	SYNTAX	LesLocalIndex
	ACCESS	read-only
	STATUS	mandatory
	DESCRIPTION
		"Index into the ELAN this pair of LES/BUS is servicing."
	::= { cnLesBusPeerEntry 1 }

cnLesBusPeerIndex OBJECT-TYPE
	SYNTAX	INTEGER
	ACCESS	read-only
	STATUS	mandatory
	DESCRIPTION
		"An arbitrary integer which uniquly identifies a pair
		of LES/BUS within an ELAN."
	::= { cnLesBusPeerEntry 2 }

cnLesBusPeerLesAddr OBJECT-TYPE
	SYNTAX	AtmLaneAddress
	ACCESS	read-write
	STATUS	mandatory
	DESCRIPTION
		"The ATM address of the LES."
	::= { cnLesBusPeerEntry 3 }

cnLesBusPeerBusAddr OBJECT-TYPE
	SYNTAX	AtmLaneAddress
	ACCESS	read-write
	STATUS	mandatory
	DESCRIPTION
		"The ATM address of the BUS."
	::= { cnLesBusPeerEntry 4 }

cnLesBusPeerStatus OBJECT-TYPE
	SYNTAX	INTEGER {
		create(1),        -- create an entry, write only
		delete(2),        -- delete an entry, write only
		active(3),	  -- read only value
		inactive(4)	  -- read only value
		}
	ACCESS	read-write
	STATUS	mandatory
	DESCRIPTION
		"This object is used to create or destroy an entry
		from this table.  This object also reflect the current
		state of the peer LES/BUS.  If both peer LES and BUS are
		connected to this LES/BUS, then active(3) is returned 
		when read, otherwise inactive(4) will be returned."
	::= { cnLesBusPeerEntry 5 }


-- Port range support for LESBUS

cnLesBusPortTable OBJECT-TYPE
	SYNTAX	SEQUENCE OF CnLesBusPortEntry
	ACCESS	not-accessible
	STATUS	mandatory
	DESCRIPTION
		"The ATM port a LESBUS uses to establish virtual circuits(VCC). 
		A User can choose to either select the any-port capability,
		which let the LESBUS choose whichever the ATM port is available.
		Or the user can specify a list of ATM ports the LESBUS will
		request the VCCs.  When a list of ATM ports are specified,
		There are four objects used for specifying the ATM port
		numbers.  The object cnLesBusPortAtmPort1 is used first,
		the object cnLesBusPortAtmPort2 second if the first failed
		and so on."
	::= { cnLesBusExtnGroup 3 }

cnLesBusPortEntry OBJECT-TYPE
	SYNTAX	CnLesBusPortEntry
	ACCESS	not-accessible
	STATUS	mandatory
	DESCRIPTION
		"Each entry represent a LESBUS maintained by this agent.
		The entries are indexed by the same index (LesBusIndex)
		from the LesBusConfigTable defined in the ATM Forum LESBUS MIB."
	INDEX	{ cnLesBusPortElanIndex, cnLesBusPortIndex }
	::= { cnLesBusPortTable 1 }

CnLesBusPortEntry ::= SEQUENCE {
	cnLesBusPortElanIndex
		INTEGER,
	cnLesBusPortIndex
		INTEGER,
	cnLesBusCardId
		INTEGER,
	cnLesBusPortId
		INTEGER,
	cnLesBusPortStatus
		INTEGER
	}

cnLesBusPortElanIndex OBJECT-TYPE
	SYNTAX	INTEGER
	ACCESS	read-only
	STATUS	mandatory
	DESCRIPTION
		"An index to the LESBUS pair that will use this table."
	::= { cnLesBusPortEntry 1 }

cnLesBusPortIndex OBJECT-TYPE
	SYNTAX	INTEGER
	ACCESS	read-only
	STATUS	mandatory
	DESCRIPTION
		"An index to an entry in the port table"
	::= { cnLesBusPortEntry 2 }

cnLesBusCardId OBJECT-TYPE
	SYNTAX	INTEGER
	ACCESS	read-write
	STATUS	mandatory
	DESCRIPTION
		"Card ID of the ATM card."
	::= { cnLesBusPortEntry 3 }

cnLesBusPortId OBJECT-TYPE
	SYNTAX	INTEGER
	ACCESS	read-write
	STATUS	mandatory
	DESCRIPTION
		"Port ID of the ATM port."
	::= { cnLesBusPortEntry 4 }

cnLesBusPortStatus OBJECT-TYPE
	SYNTAX	INTEGER {
		create(1),        -- create an entry, write only
		delete(2),        -- delete an entry, write only
		active(3),	  -- read only value
		inactive(4)		  -- read only value
		}
	ACCESS	read-write
	STATUS	mandatory
	DESCRIPTION
		"The object is used to create or destroy an entry
		from this table.  This object also reflect the current
		state of the port entry.  If the client uses this port
		to join the ELAN, then active(3) is returned when read."
	::= { cnLesBusPortEntry 5 }


--  SECTION 3: LEC Extention Group

cnLecServerTable OBJECT-TYPE
	SYNTAX	SEQUENCE OF CnLecServerEntry
	ACCESS	not-accessible
	STATUS	mandatory
	DESCRIPTION
		"The LE Client's user configured server list.
		 The LEC can use any pf the servers defined in this
		 table.  The search order matches the order of the
		 entries in the table."
	::= { cnLecExtnGroup 1 }

cnLecServerEntry OBJECT-TYPE
	SYNTAX	CnLecServerEntry
	ACCESS	not-accessible
	STATUS	mandatory
	DESCRIPTION
		"A LE server that the LEC can use."
	INDEX	{ lecIndex, cnLecServerIndex }
	::= { cnLecServerTable 1 }

CnLecServerEntry ::= SEQUENCE {
	cnLecServerIndex
		INTEGER,
	cnLecServerType
		INTEGER,
	cnLecServerAddress
		AtmLaneAddress,
	cnLecServerStatus
		INTEGER
	}

cnLecServerIndex OBJECT-TYPE
	SYNTAX	INTEGER
	ACCESS	read-only
	STATUS	mandatory
	DESCRIPTION
		"An index to the lec server table."
	::= { cnLecServerEntry 1 }

cnLecServerType OBJECT-TYPE
	SYNTAX	INTEGER {
		lecsAtmForum(1),
		lecsFromIlmi(2),
		directLecs(3),
		directLes(4),
		lecsFromPvc(5)
		}
	ACCESS	read-write
	STATUS	mandatory
	DESCRIPTION
		"The field specifies how the the LEC can get to the server
		 and the server type (LES or LECS).  The LEC can connect
		 to either the LECS via ILMI/PVC/ATM address or the LES
		 via ATm address."
	::= { cnLecServerEntry 2 }

cnLecServerAddress OBJECT-TYPE
	SYNTAX	AtmLaneAddress
	ACCESS	read-write
	STATUS	mandatory
	DESCRIPTION
		"The field specifies the ATM address (20 octets) of the
		 server when an ATM address is needed.  If an ATM address
		 is not needed, zero will be returned when read."
	::= { cnLecServerEntry 3 }

cnLecServerStatus OBJECT-TYPE
	SYNTAX	INTEGER {
		create(1),        -- create an entry, write only
		delete(2),        -- delete an entry, write only
		active(3)	  -- read only value
		}
	ACCESS	read-write
	STATUS	mandatory
	DESCRIPTION
		"The object is used to create or destroy an entry
		from this table.  The entry is always in active
		state once created."
	::= { cnLecServerEntry 4 }

-- Port range support for LEC

cnLecPortTable OBJECT-TYPE
	SYNTAX	SEQUENCE OF CnLecPortEntry
	ACCESS	not-accessible
	STATUS	mandatory
	DESCRIPTION
		"The ATM port a LEC uses to establish virtual circuits(VCC). 
		A User can choose to either select the any-port capability,
		which let the LEC choose whichever the ATM port is available.
		Or the user can specify a list of ATM ports the LEC will
		request the VCCs.  When a list of ATM ports are specified,
		There are four objects used for specifying the ATM port
		numbers.  The object cnLecPortAtmPort1 is used first,
		the object cnlecPortAtmPort2 second if the first failed
		and so on."
	::= { cnLecExtnGroup 2 }

cnLecPortEntry OBJECT-TYPE
	SYNTAX	CnLecPortEntry
	ACCESS	not-accessible
	STATUS	mandatory
	DESCRIPTION
		"Each entry represent a LEC maintained by this agent.
		The entries are indexed by the same index (lecIndex)
		from the lecConfigTable defined in the ATM Forum LEC MIB."
	INDEX	{ cnLecPortlecIndex, cnLecPortIndex }
	::= { cnLecPortTable 1 }

CnLecPortEntry ::= SEQUENCE {
	cnLecPortlecIndex
		INTEGER,
	cnLecPortIndex
		INTEGER,
	cnLecCardId
		INTEGER,
	cnLecPortId
		INTEGER,
	cnLecPortStatus
		INTEGER
	}

cnLecPortlecIndex OBJECT-TYPE
	SYNTAX	INTEGER
	ACCESS	read-only
	STATUS	mandatory
	DESCRIPTION
		"An index to the LEC that will use this table."
	::= { cnLecPortEntry 1 }

cnLecPortIndex OBJECT-TYPE
	SYNTAX	INTEGER
	ACCESS	read-only
	STATUS	mandatory
	DESCRIPTION
		"An index to an entry in the port table"
	::= { cnLecPortEntry 2 }

cnLecCardId OBJECT-TYPE
	SYNTAX	INTEGER
	ACCESS	read-write
	STATUS	mandatory
	DESCRIPTION
		"Card ID of the ATM card."
	::= { cnLecPortEntry 3 }

cnLecPortId OBJECT-TYPE
	SYNTAX	INTEGER
	ACCESS	read-write
	STATUS	mandatory
	DESCRIPTION
		"Port ID of the ATM port."
	::= { cnLecPortEntry 4 }

cnLecPortStatus OBJECT-TYPE
	SYNTAX	INTEGER {
		create(1),        -- create an entry, write only
		delete(2),        -- delete an entry, write only
		active(3),	  -- read only value
		inactive(4)		  -- read only value
		}
	ACCESS	read-write
	STATUS	mandatory
	DESCRIPTION
		"The object is used to create or destroy an entry
		from this table.  This object also reflect the current
		state of the port entry.  If the client uses this port
		to join the ELAN, then active(3) is returned when read."
	::= { cnLecPortEntry 5 }


--  SECTION 4: LECS Extention Group

-- Port range support for LESBUS

cnLecsPortTable OBJECT-TYPE
	SYNTAX	SEQUENCE OF CnLecsPortEntry
	ACCESS	not-accessible
	STATUS	mandatory
	DESCRIPTION
		"The ATM port a Lecs uses to establish virtual circuits(VCC). 
		A User can choose to either select the any-port capability,
		which let the Lecs choose whichever the ATM port is available.
		Or the user can specify a list of ATM ports the Lecs will
		request the VCCs.  When a list of ATM ports are specified,
		There are four objects used for specifying the ATM port
		numbers.  The object cnLecsPortAtmPort1 is used first,
		the object cnLecsPortAtmPort2 second if the first failed
		and so on."
	::= { cnLecsExtnGroup 1 }

cnLecsPortEntry OBJECT-TYPE
	SYNTAX	CnLecsPortEntry
	ACCESS	not-accessible
	STATUS	mandatory
	DESCRIPTION
		"Each entry represent a Lecs maintained by this agent.
		The entries are indexed by the same index (LecsIndex)
		from the LecsConfigTable defined in the ATM Forum Lecs MIB."
	INDEX	{ cnLecsIndex, cnLecsPortIndex }
	::= { cnLecsPortTable 1 }

CnLecsPortEntry ::= SEQUENCE {
	cnLecsIndex
		INTEGER,
	cnLecsPortIndex
		INTEGER,
	cnLecsCardId
		INTEGER,
	cnLecsPortId
		INTEGER,
	cnLecsPortStatus
		INTEGER
	}

cnLecsIndex OBJECT-TYPE
	SYNTAX	INTEGER
	ACCESS	read-only
	STATUS	mandatory
	DESCRIPTION
		"An index to the Lecs pair that will use this table."
	::= { cnLecsPortEntry 1 }

cnLecsPortIndex OBJECT-TYPE
	SYNTAX	INTEGER
	ACCESS	read-only
	STATUS	mandatory
	DESCRIPTION
		"An index to an entry in the port table"
	::= { cnLecsPortEntry 2 }

cnLecsCardId OBJECT-TYPE
	SYNTAX	INTEGER
	ACCESS	read-write
	STATUS	mandatory
	DESCRIPTION
		"Card ID of the ATM card."
	::= { cnLecsPortEntry 3 }

cnLecsPortId OBJECT-TYPE
	SYNTAX	INTEGER
	ACCESS	read-write
	STATUS	mandatory
	DESCRIPTION
		"Port ID of the ATM port."
	::= { cnLecsPortEntry 4 }

cnLecsPortStatus OBJECT-TYPE
	SYNTAX	INTEGER {
		create(1),        -- create an entry, write only
		delete(2),        -- delete an entry, write only
		active(3),	  -- read only value
		inactive(4)		  -- read only value
		}
	ACCESS	read-write
	STATUS	mandatory
	DESCRIPTION
		"The object is used to create or destroy an entry
		from this table.  This object also reflect the current
		state of the port entry.  If the client uses this port
		to join the ELAN, then active(3) is returned when read."
	::= { cnLecsPortEntry 5 }

cnLecsExtnTable  OBJECT-TYPE
        SYNTAX  SEQUENCE OF CnLecsExtnEntry
        ACCESS  not-accessible
        STATUS  mandatory
        DESCRIPTION
                "LECS LANE extension table"
        ::= { cnLecsExtnGroup 2 }
 
cnLecsExtnEntry OBJECT-TYPE
        SYNTAX  CnLecsExtnEntry
        ACCESS  not-accessible
        STATUS  mandatory
        DESCRIPTION
                "An extension to the lecsConfEntry which contains
                 objects associated to a LECS."
        INDEX   { lecsConfIndex }
        ::= { cnLecsExtnTable 1 }
 
CnLecsExtnEntry ::= SEQUENCE {
        cnLecsExtnAtmAddressSelect
                INTEGER
        }

cnLecsExtnAtmAddressSelect OBJECT-TYPE
        SYNTAX INTEGER {
            atmForum(1),
            userDefined(2)
            }
        ACCESS read-write
        STATUS mandatory
        DESCRIPTION
                "LECS ATM Address selection.
                 atmForum(1) - ATM Forum well known ATM Address.
                 userDefined(2) - User defined ATM Address."
        ::= {cnLecsExtnEntry 1}


--  SECTION 5: ATM Call Routing Table (IISP)

-- This group contains information pertaining to ATM elan
-- configuration in the system

atmCallRoutingConfigTable OBJECT-TYPE
	SYNTAX  SEQUENCE OF AtmCallRoutingConfigEntry
	ACCESS  not-accessible
	STATUS  mandatory
	DESCRIPTION
		"ATM call routing config table"
	::= { atmCallRoutingConfig 1 }

atmCallRoutingConfigEntry OBJECT-TYPE
	SYNTAX  AtmCallRoutingConfigEntry
	ACCESS  not-accessible
	STATUS  mandatory
	DESCRIPTION
        	"Objects atmCallRoutingId, and atmCallRoutingRowStatus are 
		 required during row creation.  And object elanLesRowStatus 
		 is required during row deletion."
    	INDEX { atmCallRoutingId }
	::= { atmCallRoutingConfigTable 1 }

AtmCallRoutingConfigEntry ::= SEQUENCE {
	atmCallRoutingId
		INTEGER,
	atmCallRoutingAtmAddress
		AtmLaneAddress,
	atmCallRoutingType
		INTEGER,
	atmCallRoutingCard
		INTEGER,
	atmCallRoutingPort
		INTEGER,
	atmCallRoutingCost
		INTEGER,
	atmCallRoutingEnable
		INTEGER,
	atmCallRoutingRowStatus
		INTEGER,
	atmCallRoutingScope
		INTEGER,
	atmCallRoutingVpi
		INTEGER,
	atmCallRoutingFilterEnable
		EnableIndicator
	}

atmCallRoutingId OBJECT-TYPE
    SYNTAX INTEGER
    ACCESS read-only
    STATUS mandatory
    DESCRIPTION
        " Route id "
    ::= { atmCallRoutingConfigEntry 1 }
 
atmCallRoutingAtmAddress OBJECT-TYPE
    SYNTAX AtmLaneAddress
    ACCESS read-write
    STATUS mandatory
    DESCRIPTION
        "Routable ATM address for route type host and network.
	 Filter prefix for a default route entry."
    ::= { atmCallRoutingConfigEntry 2 }
 
atmCallRoutingType OBJECT-TYPE
	SYNTAX 	INTEGER {
		host(1),
		network(2),
		linkGroup(3),
		default(4)
		}
    	ACCESS read-write
	STATUS  mandatory
	DESCRIPTION 
		"A complete ATM address is specified in a routing entry 
		when the route type is host.  For the network route 
		type, only partial ATM address, usually the network 
		prefix portion, is specified.  Linkgroup is a special
		route type which can be defined in a way that loops are
		eliminated.  The default type allows a route entry 
		to be created that forwards to all destinations. "
	::= { atmCallRoutingConfigEntry 3 }

atmCallRoutingCard OBJECT-TYPE
	SYNTAX	INTEGER (1..16)
	ACCESS	read-write
	STATUS	mandatory
	DESCRIPTION
		"This field indicates the ATM card id."
	::= { atmCallRoutingConfigEntry 4 }

atmCallRoutingPort OBJECT-TYPE
	SYNTAX	INTEGER (1..16)
	ACCESS	read-write
	STATUS	mandatory
	DESCRIPTION
		"This field indicates ATM port id."
	::= { atmCallRoutingConfigEntry 5 }

atmCallRoutingCost OBJECT-TYPE
	SYNTAX 	INTEGER (0..255)
	ACCESS 	read-write
	STATUS  mandatory
	DESCRIPTION 
		"The cost of the route. range from 0 to 255 with 0 
		the least cost. This is the link group id if 
		atmCallRoutingType is linkGroup."
	::= { atmCallRoutingConfigEntry 6 }

atmCallRoutingEnable OBJECT-TYPE
	SYNTAX  INTEGER {
		enable(1),
		disable(2)
		}
	ACCESS	read-write
	STATUS 	mandatory
	DESCRIPTION
		"Enable bit of the call routing.
		1 = enable routing
		2 = disable routing "
	::= { atmCallRoutingConfigEntry 7 }


atmCallRoutingRowStatus OBJECT-TYPE
	SYNTAX 	INTEGER {
		add(1),
		delete(2)
		}
	ACCESS 	read-write
	STATUS  mandatory
	DESCRIPTION 
		"The current status of the entry. Entries may be added by 
		specifying a value of valid, and removed by setting the status
		to invalid."
	::= { atmCallRoutingConfigEntry 8 }

atmCallRoutingScope OBJECT-TYPE
	SYNTAX 	INTEGER (0..104) 
	ACCESS 	read-write
	STATUS  mandatory
	DESCRIPTION 
		"PNNI scope value"
	::= { atmCallRoutingConfigEntry 9 }

atmCallRoutingVpi OBJECT-TYPE
        SYNTAX INTEGER (0..15)
        ACCESS read-write
        STATUS mandatory
        DESCRIPTION
               " The VPI of the route."
        ::= { atmCallRoutingConfigEntry 10 }

atmCallRoutingFilterEnable OBJECT-TYPE
        SYNTAX  EnableIndicator
	ACCESS	read-write
	STATUS 	mandatory
	DESCRIPTION
		"Enable bit of the filter for a default route.
		When the filter is enabled, data will be forwarded
		to all destinations except for a defined prefix."
        DEFVAL { disabled } 
	::= { atmCallRoutingConfigEntry 11 }


--  SECTION 6: ATM Golobal Config

cnLaneSig OBJECT-TYPE
	SYNTAX	INTEGER {
		enabled(1),
		disabled(2)
		}
	ACCESS	read-write
	STATUS	mandatory
	DESCRIPTION
		"Global parameter to enable or disable signalling
		 in the box."
	::= { cnLaneGlobalConf 1}

cnLaneEdge OBJECT-TYPE
	SYNTAX  INTEGER {
		edgeOnly(1),
		edgeAndSwitch(2),
		switchOnly(3)
		}
	ACCESS	read-write
	STATUS 	mandatory
	DESCRIPTION
		"Global configuration of the box
		 edge: configured as LEC only services
		 edgeAndswitch: configured as full LANE services
		 switchOnly: configured as switch only services."
	::= { cnLaneGlobalConf 2 }

cnLaneNetPrefix OBJECT-TYPE
	SYNTAX  OCTET STRING(SIZE(13))
	ACCESS	read-write
	STATUS 	mandatory
	DESCRIPTION
		"Useful if the box is configured as edgeAndswitch."
	::= { cnLaneGlobalConf 3 }
	
cnLaneStatusEnquiryEnable OBJECT-TYPE
        SYNTAX  EnableIndicator
        ACCESS  read-write
        STATUS  mandatory
        DESCRIPTION
                "This object is used to enable or disable the Status
                 enquiry. Note that this parametwer is used only
                if the ATM signalling is enabled."
        DEFVAL { disabled } 
        ::= { cnLaneGlobalConf 4 }
 
cnLaneStatusEnquiryInterval OBJECT-TYPE
        SYNTAX  TimeIntervalSec (120..9999)
        ACCESS  read-write
        STATUS  mandatory
        DESCRIPTION
                "The Status Enquiry requests for each call are sent
                 periodically at this interval (in secs). Note that
                 this parametwer is used only if the ATM signalling
                 and atmSysStatusEnquiryEnable are enabled."
        DEFVAL { 600 }
        ::= { cnLaneGlobalConf 5 }

--  SECTION 7: LEC Config Extention Group

cnLecConfigExtnTable OBJECT-TYPE
        SYNTAX  SEQUENCE OF CnLecConfigExtnEntry
        ACCESS  not-accessible
        STATUS  mandatory
        DESCRIPTION
                "This the extension table of lecConfigTable. "
        ::= { cnLecExtnGroup 3 }

cnLecConfigExtnEntry OBJECT-TYPE
        SYNTAX  CnLecConfigExtnEntry
        ACCESS  not-accessible
        STATUS  mandatory
        DESCRIPTION
                "Each table entry contains configuration information
                for one LAN Emulation Client."
        INDEX   { lecIndex }
        ::= { cnLecConfigExtnTable 1 }
 
CnLecConfigExtnEntry ::= SEQUENCE {
        cnLecTargetlessArp
                EnableIndicator,
        cnLecQoSAdminStatus
                EnableIndicator,
        cnLecQoSOperStatus
                TruthValue
        }
 
 
cnLecTargetlessArp OBJECT-TYPE
        SYNTAX  EnableIndicator
        ACCESS  read-write
        STATUS  mandatory
        DESCRIPTION
                "This object is used to enable or disable the
                targetless LE_ARP."
        DEFVAL { enabled }
        ::= { cnLecConfigExtnEntry 1 }
 
cnLecQoSAdminStatus OBJECT-TYPE
        SYNTAX  EnableIndicator
        ACCESS  read-write
        STATUS  mandatory
        DESCRIPTION
                "This object is used to enable or disable QoS
                features for the LEC.  QoS can be enabled for
                V2 capable LECs in Ethernet ELANs."
        DEFVAL { disabled }
        ::= { cnLecConfigExtnEntry 2 }
 
cnLecQoSOperStatus OBJECT-TYPE
        SYNTAX  TruthValue
        ACCESS  read-only
        STATUS  mandatory
        DESCRIPTION
                "This object is true when the LEC is able to
                conduct QoS feature operation.  It is false
                when QoS features are not permitted, such as
                when cnLecQoSAdminStatus is not enabled or the
                LEC does not join a V2 capable ELAN."
        ::= { cnLecConfigExtnEntry 3 }

END

-- SECTION 1: Top Level Definitions
 
CENTILLION-LECS-MPOA-MIB DEFINITIONS ::= BEGIN
 
--  
-- Revision 1/23/98 
 
-- Copyright 1998 Bay Networks, Inc.
-- All rights reserved.
-- This Bay Networks SNMP Management Information Base Specification
-- (Specification) embodies Bay Networks' confidential and
-- proprietary intellectual property. Bay Networks retains all
-- title and ownership in the Specification, including any
-- revisions.
 
-- This Specification is supplied "AS IS," and Bay Networks makes
-- no warranty, either express or implied, as to the use,
-- operation, condition, or performance of the Specification.
 
-- Imports

IMPORTS
        OBJECT-TYPE
                FROM RFC-1212
	TruthValue, RowStatus
		FROM SNMPv2-TC-v1
        Integer32
                FROM SNMPv2-SMI-v1
        atmLane
		FROM CENTILLION-ROOT-MIB
        AtmConfigAddr, InternetworkAddrType, MpcIndex, MpsIndex
		FROM MPOA-MIB
        lecsConfIndex
                FROM LAN-EMULATION-ELAN-MIB;



cnLecsMpoaGroup	        OBJECT IDENTIFIER ::= { atmLane 6 }

-- SECTION 2:  Lecs Mpoa Mpc Table

-- This table contains information pertaining to Lecs for Mpoa Mpc
 
cnLecsMpoaMpcTable OBJECT-TYPE
    SYNTAX  SEQUENCE OF CnLecsMpoaMpcEntry
    ACCESS  not-accessible
    STATUS  mandatory
    DESCRIPTION
           "The Bay Networks proprietary LECS MPC Table.
           This table contains configuration information
           for all LECS Mpoa Mpcs this agent manages."
    ::= { cnLecsMpoaGroup  1 }


cnLecsMpoaMpcEntry OBJECT-TYPE
    SYNTAX  CnLecsMpoaMpcEntry
    ACCESS  not-accessible
    STATUS  mandatory
    DESCRIPTION
           "Each entry contains LECS MPC information
           for all LECS this agent manages."
    INDEX   { lecsConfIndex,
	      cnLecsMpoaMpcIndex }
    ::= { cnLecsMpoaMpcTable 1 }


CnLecsMpoaMpcEntry ::=
    SEQUENCE {
        cnLecsMpoaMpcIndex                MpcIndex,
        cnLecsMpoaMpcRowStatus            RowStatus,
        cnLecsMpoaMpcCtrlAtmAddr          AtmConfigAddr,
	cnLecsMpoaMpcSCSetupFrameCount    Integer32,
	cnLecsMpoaMpcSCSetupFrameTime     Integer32,
	cnLecsMpoaMpcInitialRetryTime     Integer32,
	cnLecsMpoaMpcRetryTimeMaximum     Integer32,
	cnLecsMpoaMpcHoldDownTime         Integer32,
        cnLecsMpoaMpcDefaultTLV           TruthValue
    }

cnLecsMpoaMpcIndex OBJECT-TYPE
    SYNTAX   MpcIndex
    ACCESS   read-write
    STATUS   mandatory
    DESCRIPTION
         "A value which uniquely identifies this conceptual
         row in the cnLecsMpoaMpcTable."  
    ::= { cnLecsMpoaMpcEntry 1 }

cnLecsMpoaMpcRowStatus OBJECT-TYPE
    SYNTAX   RowStatus
    ACCESS   read-write
    STATUS   mandatory
    DESCRIPTION
         "This object allows creation and deletion of Lecs 
         MPOA Clients.

         Within each conceptual cnLecsMpoaMpcTable row, writable
         objects may be modified, regardless of the value of
         cnLecsMpoaMpcRowStatus."
    ::= { cnLecsMpoaMpcEntry 2 }

cnLecsMpoaMpcCtrlAtmAddr OBJECT-TYPE
    SYNTAX   AtmConfigAddr
    ACCESS   read-write
    STATUS   mandatory
    DESCRIPTION
         "The MPC's Control ATM Address.  There exists one Control ATM
	 Address per MPC, therefore, the value of this entry is unique
	 within the table.  The control ATM Address is the address which
	 is used by the MPC in its requests to the MPS.  The value of
	 this object should not change, once created."
     ::= { cnLecsMpoaMpcEntry 3}

cnLecsMpoaMpcSCSetupFrameCount OBJECT-TYPE
    SYNTAX Integer32 (1..65535)
    ACCESS read-write
    STATUS mandatory
    DESCRIPTION
         "This represents the Short-cut setup frame count
         parameter.
 
         This value is frames measured over mpcSCFrameTime
         seconds.
         Flow detection is protocol independent. i.e. all network layers
         lecsMpcProtocolEntries for this MPC share the flow rate
         specification.
         A value of 1 causes all flows to initiate resolution/shortcut.
         process."
    DEFVAL { 10 }
    ::= { cnLecsMpoaMpcEntry 4 }
 
cnLecsMpoaMpcSCSetupFrameTime OBJECT-TYPE
    SYNTAX Integer32 (1..60)
    ACCESS read-write
    STATUS mandatory
    DESCRIPTION
         "Short-cut setup frame time, in seconds."
    DEFVAL { 1 }
    ::= { cnLecsMpoaMpcEntry 5 }
 
 
cnLecsMpoaMpcInitialRetryTime OBJECT-TYPE
    SYNTAX Integer32 (1..300)
    ACCESS read-write
    STATUS mandatory
    DESCRIPTION
         "This is the initial value for the retry time out period used
	 for timing out MPOA Resolution Requests in seconds.  Retry time
	 consists of this initial time-out and a retry muliplier.  If a
	 response is not received, then another request is sent with a
	 timeout of retry time * retry time maximum seconds, or until
	 cnLecsMpoaMpcRetryTimeMaximum."
    DEFVAL { 5 }
    ::= { cnLecsMpoaMpcEntry 6 }
 
cnLecsMpoaMpcRetryTimeMaximum OBJECT-TYPE
    SYNTAX Integer32 (10..300)
    ACCESS read-write
    STATUS mandatory
    DESCRIPTION
         "Cumulative max value for Retry Time.
         Retries are attempted at intervals determined by the
         algorithm descrived in the definition of
         cnLecsMpoaMpcInitalRetryTime."
    REFERENCE
         "Multiprotocol Over ATM. AF-MPOA-0087.000.
         Section 4.3 MPOA Retry Mechanism"
    DEFVAL { 40 }
    ::= { cnLecsMpoaMpcEntry 7 }

cnLecsMpoaMpcHoldDownTime OBJECT-TYPE
    SYNTAX Integer32 (30..1200)
    ACCESS read-write
    STATUS mandatory
    DESCRIPTION
         "Hold Down Time
         Minimum time to wait before reinitiating
         a failed resolution attempt.  Default is
         cnLecsMpoaMpcRetryTimeMaximum * 4."
    REFERENCE
         "Multiprotocol Over ATM. AF-MPOA-0087.000.
         Section 4.1.2.1 MPC Parameters"
    DEFVAL { 160 }
    ::= { cnLecsMpoaMpcEntry 8 }

cnLecsMpoaMpcDefaultTLV OBJECT-TYPE
    SYNTAX TruthValue
    ACCESS read-write
    STATUS mandatory
    DESCRIPTION
        "Indicates whether this CnLecsMpoaMpcEntry
         contains the default TLV settings. Only one
         entry in the table can have the default
         setttings."
    DEFVAL { false }
        ::= {cnLecsMpoaMpcEntry 9 }
 


-- SECTION 3:  Lecs Mpoa Mps Table

-- This table contains information pertaining to Lecs for Mpoa Mps
 
cnLecsMpoaMpsTable OBJECT-TYPE
    SYNTAX  SEQUENCE OF CnLecsMpoaMpsEntry
    ACCESS  not-accessible
    STATUS  mandatory
    DESCRIPTION
           "The Bay Networks proprietary LECS MPS Table.
           This table contains configuration information
           for all LECS Mpoa Mpss this agent manages."
    ::= { cnLecsMpoaGroup 2 }


cnLecsMpoaMpsEntry OBJECT-TYPE
    SYNTAX  CnLecsMpoaMpsEntry
    ACCESS  not-accessible
    STATUS  mandatory
    DESCRIPTION
           "Each entry contains LECS MPS information
           for all LECS this agent manages."
    INDEX   { lecsConfIndex,
	      cnLecsMpoaMpsIndex }
    ::= { cnLecsMpoaMpsTable 1 }


CnLecsMpoaMpsEntry ::=
    SEQUENCE {
        cnLecsMpoaMpsIndex                MpsIndex,
        cnLecsMpoaMpsRowStatus            RowStatus,
	cnLecsMpoaMpsCtrlAtmAddr          AtmConfigAddr,
        cnLecsMpoaMpsKeepAliveTime        Integer32,
	cnLecsMpoaMpsKeepAliveLifeTime    Integer32,
	cnLecsMpoaMpsInitialRetryTime     Integer32,
	cnLecsMpoaMpsRetryTimeMaximum     Integer32,
	cnLecsMpoaMpsGiveupTime           Integer32,
	cnLecsMpoaMpsDefaultHoldingTime   Integer32,
        cnLecsMpoaMpsDefaultTLV           TruthValue
    }

cnLecsMpoaMpsIndex OBJECT-TYPE
    SYNTAX   MpsIndex
    ACCESS   read-write
    STATUS   mandatory
    DESCRIPTION
         "A value which uniquely identifies this conceptual
         row in the cnLecsMpoaMpsTable."  
    ::= { cnLecsMpoaMpsEntry 1 }

cnLecsMpoaMpsRowStatus OBJECT-TYPE
    SYNTAX   RowStatus
    ACCESS   read-write
    STATUS   mandatory
    DESCRIPTION
         "This object allows creation and deletion of Lecs 
         MPOA Clients.

         Within each conceptual cnLecsMpoaMpsTable row, writable
         objects may be modified, regardless of the value of
         cnLecsMpoaMpsRowStatus."
    ::= { cnLecsMpoaMpsEntry 2 }

cnLecsMpoaMpsCtrlAtmAddr OBJECT-TYPE
    SYNTAX   AtmConfigAddr
    ACCESS   read-write
    STATUS   mandatory
    DESCRIPTION
         "The MPS's Control ATM Address.  There exists one
         Control ATM Address per MPS, therefore, the value
         of this entry is unique within the table."
     ::= { cnLecsMpoaMpsEntry 3 }

cnLecsMpoaMpsKeepAliveTime OBJECT-TYPE
    SYNTAX  Integer32 (1..300)
    ACCESS  read-write
    STATUS  mandatory
    DESCRIPTION
         "Keep-alive time is max interval between
         the MPS sending MPOA Keep-Alives in seconds."
    DEFVAL { 10 }
    ::= { cnLecsMpoaMpsEntry 4 }
 
cnLecsMpoaMpsKeepAliveLifeTime OBJECT-TYPE
    SYNTAX  Integer32 (3..1000)
    ACCESS  read-write
    STATUS  mandatory
    DESCRIPTION
         "Keep-Alive Lifetime
         The length of time an MPC may consider a Keep-Alive
         valid in seconds.  This value must be at least
         three times the cnLecsMpoaMpsKeepAliveTime."
    DEFVAL { 35 }
    ::= { cnLecsMpoaMpsEntry 5 }

cnLecsMpoaMpsInitialRetryTime OBJECT-TYPE
    SYNTAX  Integer32 (1..300)
    ACCESS  read-write
    STATUS  mandatory
    DESCRIPTION
         "Initial value in seconds for the
         MPOA retry mechanism."
    DEFVAL { 5 }
    ::= { cnLecsMpoaMpsEntry 6 }
 
cnLecsMpoaMpsRetryTimeMaximum OBJECT-TYPE
    SYNTAX  Integer32 (10..300)
    ACCESS  read-write
    STATUS  mandatory
    DESCRIPTION
         "Cumulative max value in seconds
         for Retry Time."
    REFERENCE
         "Multiprotocol Over ATM.  AF-MPOA-0087.000.
         Section 4.3 MPOA Retry Mechanism"
    DEFVAL { 40 }
    ::= { cnLecsMpoaMpsEntry 7 }

cnLecsMpoaMpsGiveupTime OBJECT-TYPE
    SYNTAX  Integer32 (5..300)
    ACCESS  read-write
    STATUS  mandatory
    DESCRIPTION
         "Give Up Time.
         Minimum time in seconds to wait before giving up on a
         pending resolution request."
    DEFVAL { 40 }
    ::= { cnLecsMpoaMpsEntry 8 }
 
cnLecsMpoaMpsDefaultHoldingTime OBJECT-TYPE
    SYNTAX  Integer32 (1..120)
    ACCESS  read-write
    STATUS  mandatory
    DESCRIPTION
         "Default Holding Time in minutes.
         The default Holding Time used in NHRP
         Resolution Replies.  An egress MPS may use
         local information to determine a more
         appropriate Holding Time."
    DEFVAL { 20 }
    ::= { cnLecsMpoaMpsEntry 9 }


cnLecsMpoaMpsDefaultTLV OBJECT-TYPE
    SYNTAX TruthValue
    ACCESS read-write
    STATUS mandatory
    DESCRIPTION
        "Indicates whether this CnLecsMpoaMpsEntry
         contains the default TLV settings.  Only one
         entry in the table can have the default
         settings."
    DEFVAL { false }
        ::= {cnLecsMpoaMpsEntry 10 }
 

-- SECTION 4:  Lecs Mpoa Mpc Protocol Table 

-- This table contains information pertaining to protocal 
-- for Lecs Mpoa Mpc
 
cnLecsMpoaMpcProtocolTable OBJECT-TYPE
    SYNTAX  SEQUENCE OF CnLecsMpoaMpcProtocolEntry
    ACCESS  not-accessible
    STATUS  mandatory
    DESCRIPTION
           "The Bay Networks proprietary Protocol LECS MPS Table.
           This table contains the protocal configuration information
           for all LECS this agent manages."
    ::= { cnLecsMpoaGroup 3 }


cnLecsMpoaMpcProtocolEntry OBJECT-TYPE
    SYNTAX  CnLecsMpoaMpcProtocolEntry
    ACCESS  not-accessible
    STATUS  mandatory
    DESCRIPTION
           "Each entry contains Protocol LECS MPC information
           for all LECS this agent manages."
    INDEX   { lecsConfIndex,
	      cnLecsMpoaMpcProtocolIndex,
              cnLecsMpoaMpcFlowDetectProtocol }
    ::= { cnLecsMpoaMpcProtocolTable 1 }


CnLecsMpoaMpcProtocolEntry ::=
    SEQUENCE {
        cnLecsMpoaMpcProtocolIndex       MpcIndex,
        cnLecsMpoaMpcFlowDetectProtocol  InternetworkAddrType,        
        cnLecsMpoaMpcProtocolRowStatus   RowStatus,
	cnLecsMpoaMpcProtocolEnable      TruthValue
    }

cnLecsMpoaMpcProtocolIndex OBJECT-TYPE
    SYNTAX   MpcIndex
    ACCESS   read-only
    STATUS   mandatory
    DESCRIPTION
         "A value which uniquely identifies this conceptual
         row in the cnLecsMpoaMpcProtocolTable."  
    ::= { cnLecsMpoaMpcProtocolEntry 1 }

cnLecsMpoaMpcFlowDetectProtocol OBJECT-TYPE
    SYNTAX InternetworkAddrType
    ACCESS read-only
    STATUS mandatory
    DESCRIPTION
         "The protocol on which flow detection is performed.
         This value is an index into the Protocol Table."
     ::= { cnLecsMpoaMpcProtocolEntry 2 }

cnLecsMpoaMpcProtocolRowStatus OBJECT-TYPE
    SYNTAX   RowStatus
    ACCESS   read-write
    STATUS   mandatory
    DESCRIPTION
         "This object allows creation and deletion of Lecs 
         MPOA Protocol."
     ::= { cnLecsMpoaMpcProtocolEntry 3 }


cnLecsMpoaMpcProtocolEnable OBJECT-TYPE
    SYNTAX   TruthValue 
    ACCESS   read-write
    STATUS   mandatory
    DESCRIPTION
	 "This object enables or disables mpoa for a particular protocol
	 for this entry in the table."
    ::= { cnLecsMpoaMpcProtocolEntry 4 }


-- SECTION 5:  Lecs Mpoa Mps Protocol Table 

-- This table contains information pertaining to protocal 
-- for Lecs Mpoa Mps
 
cnLecsMpoaMpsProtocolTable OBJECT-TYPE
    SYNTAX  SEQUENCE OF CnLecsMpoaMpsProtocolEntry
    ACCESS  not-accessible
    STATUS  mandatory
    DESCRIPTION
           "The Bay Networks proprietary Protocol LECS MPS Table.
           This table contains the protocal configuration information
           for all LECS this agent manages."
    ::= { cnLecsMpoaGroup 4 }


cnLecsMpoaMpsProtocolEntry OBJECT-TYPE
    SYNTAX  CnLecsMpoaMpsProtocolEntry
    ACCESS  not-accessible
    STATUS  mandatory
    DESCRIPTION
           "Each entry contains Protocol LECS MPs information
           for all LECS this agent manages."
    INDEX   { lecsConfIndex,
	      cnLecsMpoaMpsProtocolIndex,
              cnLecsMpoaMpsInternetworkLayerProtocol }
    ::= { cnLecsMpoaMpsProtocolTable 1 }


CnLecsMpoaMpsProtocolEntry ::=
    SEQUENCE {
        cnLecsMpoaMpsProtocolIndex               MpsIndex,
        cnLecsMpoaMpsInternetworkLayerProtocol  InternetworkAddrType,        
        cnLecsMpoaMpsProtocolRowStatus   RowStatus,
	cnLecsMpoaMpsProtocolEnable      TruthValue
    }


cnLecsMpoaMpsProtocolIndex OBJECT-TYPE
    SYNTAX   MpsIndex
    ACCESS   read-only
    STATUS   mandatory
    DESCRIPTION
         "A value which uniquely identifies this conceptual
         row in the cnLecsMpoaMpsProtocolTable."  
    ::= { cnLecsMpoaMpsProtocolEntry 1 }

cnLecsMpoaMpsInternetworkLayerProtocol OBJECT-TYPE
    SYNTAX InternetworkAddrType
    ACCESS read-only
    STATUS mandatory
    DESCRIPTION
         "The protocol on which flow detection is performed.
         This value is an index into the Protocol Table."
     ::= { cnLecsMpoaMpsProtocolEntry 2 }

cnLecsMpoaMpsProtocolRowStatus OBJECT-TYPE
    SYNTAX  RowStatus
    ACCESS   read-write
    STATUS   mandatory
    DESCRIPTION
         "This object allows creation and deletion of Lecs 
         MPOA Protocol."
     ::= { cnLecsMpoaMpsProtocolEntry 3 }


cnLecsMpoaMpsProtocolEnable OBJECT-TYPE
    SYNTAX   TruthValue 
    ACCESS   read-write
    STATUS   mandatory
    DESCRIPTION
	 "This object enables or disables mpoa for a particular protocol 
	 for this entry in the table."
    ::= { cnLecsMpoaMpsProtocolEntry 4 }

END

-- SECTION 6: Top Level Definitions
 
CENTILLION-LANE-V2-EXT-MIB DEFINITIONS ::= BEGIN
 
-- Centillion LANEv2 Extention MIB Release 1.0.0
-- Revision 6/24/98 
 
-- Copyright 1998 Bay Networks, Inc.
-- All rights reserved.
-- This Bay Networks SNMP Management Information Base Specification
-- (Specification) embodies Bay Networks' confidential and
-- proprietary intellectual property. Bay Networks retains all
-- title and ownership in the Specification, including any
-- revisions.
 
-- This Specification is supplied "AS IS," and Bay Networks makes
-- no warranty, either express or implied, as to the use,
-- operation, condition, or performance of the Specification.
 
-- Imports

IMPORTS
        OBJECT-TYPE
                FROM RFC-1212
	TruthValue
		FROM SNMPv2-TC-v1
        atmLane
		FROM CENTILLION-ROOT-MIB
	AtmLaneAddress
		FROM LAN-EMULATION-CLIENT-MIB
	lesConfIndex
		FROM LAN-EMULATION-LES-MIB
	lecsConfIndex, elanConfIndex
		FROM LAN-EMULATION-ELAN-MIB;


cnLesV2ExtnGroup	OBJECT IDENTIFIER ::= { atmLane 7 }
cnLecsV2ExtnGroup	OBJECT IDENTIFIER ::= { atmLane 8 }
cnElanV2ExtnGroup	OBJECT IDENTIFIER ::= { atmLane 9 }

CnLesLecDataFrameSize ::= INTEGER {
        max1516(2),
        max4544(3),
        max9234(4),
        max18190(5),

        -- LANE 2.0
	max1580(6)
        }


-- SECTION 7: LES LANEv2 Extension Group

cnLesV2ExtnTable  OBJECT-TYPE
	SYNTAX	SEQUENCE OF CnLesV2ExtnEntry
	ACCESS	not-accessible
	STATUS	mandatory
	DESCRIPTION
		"LES LANEv2 extension table"
	::= { cnLesV2ExtnGroup 1 }

cnLesV2ExtnEntry OBJECT-TYPE
	SYNTAX	CnLesV2ExtnEntry
	ACCESS	not-accessible
	STATUS	mandatory
	DESCRIPTION
		"An extension to the lesConfEntry which contains
		 objects associated to a LES."
	INDEX	{ lesConfIndex }
	::= { cnLesV2ExtnTable 1 }

CnLesV2ExtnEntry ::= SEQUENCE {
	cnLesV2ExtnV2Capable 
		TruthValue,
	cnLesV2ExtnElanID
		INTEGER,
	cnLesV2ExtnMaxFrameSize
		CnLesLecDataFrameSize
	}


cnLesV2ExtnV2Capable OBJECT-TYPE
	SYNTAX TruthValue
	ACCESS read-write
	STATUS mandatory
	DESCRIPTION
        	"LES V2 Capable.
		 Indicates whether this LES is setup to behave as 
		 a LANE V2 LES.  A setting which will be used for 
		 the LEC the next time it joins."
        DEFVAL { false }
	::= {cnLesV2ExtnEntry 1}

cnLesV2ExtnElanID OBJECT-TYPE
	SYNTAX INTEGER
	ACCESS read-write
	STATUS mandatory
	DESCRIPTION
        	"The ELAN-ID associated with this LES."
        DEFVAL { 0 }
	::= {cnLesV2ExtnEntry 2}

cnLesV2ExtnMaxFrameSize OBJECT-TYPE
	SYNTAX CnLesLecDataFrameSize
	ACCESS read-write
	STATUS mandatory
	DESCRIPTION
        	"The maximum AAL-5 SDU size of a data
         	 frame that the LE service can guarantee
         	 not to drop because it is too large."
	::= {cnLesV2ExtnEntry 3}


-- SECTION 8: LECS LANEv2 Extension Group

cnLecsV2ExtnTable  OBJECT-TYPE
	SYNTAX	SEQUENCE OF CnLecsV2ExtnEntry
	ACCESS	not-accessible
	STATUS	mandatory
	DESCRIPTION
		"LECS LANEv2 extension table"
	::= { cnLecsV2ExtnGroup 1 }

cnLecsV2ExtnEntry OBJECT-TYPE
	SYNTAX	CnLecsV2ExtnEntry
	ACCESS	not-accessible
	STATUS	mandatory
	DESCRIPTION
		"An extension to the lecsConfEntry which contains
		 objects associated to a LECS."
	INDEX	{ lecsConfIndex }
	::= { cnLecsV2ExtnTable 1 }

CnLecsV2ExtnEntry ::= SEQUENCE {
	cnLecsV2ExtnWellKnownAtmAddress
		AtmLaneAddress
	}

cnLecsV2ExtnWellKnownAtmAddress OBJECT-TYPE
	SYNTAX AtmLaneAddress
	ACCESS read-only
	STATUS mandatory
	DESCRIPTION
        	"LECS LANEv2 well-known ATM Address.
		 For LANEv2: C500790000000000000000000000A03E00000100"
	::= {cnLecsV2ExtnEntry 1}


-- SECTION 9: ELAN V2 Extension Group

cnElanV2ExtnTable  OBJECT-TYPE
	SYNTAX	SEQUENCE OF CnElanV2ExtnEntry
	ACCESS	not-accessible
	STATUS	mandatory
	DESCRIPTION
		"ELAN LANEv2 extension table"
	::= { cnElanV2ExtnGroup 1 }

cnElanV2ExtnEntry OBJECT-TYPE
	SYNTAX	CnElanV2ExtnEntry
	ACCESS	not-accessible
	STATUS	mandatory
	DESCRIPTION
		"An extension to the elanConfEntry which contains
		 objects associated to an ELAN."
	INDEX	{ elanConfIndex }
	::= { cnElanV2ExtnTable 1 }

CnElanV2ExtnEntry ::= SEQUENCE {
	cnElanV2ExtnV2Capable 
		TruthValue,
	cnElanV2ExtnElanID 
		INTEGER 
	}

cnElanV2ExtnV2Capable OBJECT-TYPE
	SYNTAX TruthValue
	ACCESS read-write
	STATUS mandatory
	DESCRIPTION
        	"ELAN V2 Capable.
		 Indicates whether this ELAN is setup to behave as 
		 a LANE V2 ELAN.  A setting which will be used for 
		 the LEC the next time it joins."
        DEFVAL { false }
	::= {cnElanV2ExtnEntry 1}

cnElanV2ExtnElanID OBJECT-TYPE
	SYNTAX INTEGER
	ACCESS read-write
	STATUS mandatory
	DESCRIPTION
        	"The ELAN-ID associated with this ELAN."
        DEFVAL { 0 }
	::= {cnElanV2ExtnEntry 2}


END
-- SECTION 1: Top Level Definitions

PNNI-EXT-MIB DEFINITIONS ::= BEGIN


-- PNNI Extensions MIB Release 2.0.1
-- Revision 12/21/97

-- Copyright 1997 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.



-- Imports

IMPORTS
	OBJECT-TYPE
		FROM RFC-1212
	extensions
		FROM CENTILLION-ROOT-MIB
	lecsConfIndex
		FROM LAN-EMULATION-ELAN-MIB;


-- PNNI Extensions Groups
cnPnniExt       OBJECT IDENTIFIER ::= { extensions 5 }

cnPnniMainExt   OBJECT IDENTIFIER ::= { cnPnniExt 1 }
cnPnnilecsExt   OBJECT IDENTIFIER ::= { cnPnniExt 2 }
cnPnniTdbOverload   OBJECT IDENTIFIER ::= { cnPnniExt 3 }


-- SECTION 2: MIB Objects

-- General PNNI Information

cnPnniAdminStatus OBJECT-TYPE
	SYNTAX  INTEGER {
			enabled(1),
			disabled(2) }
	ACCESS read-write
	STATUS mandatory
	DESCRIPTION
		"The desired state of PNNI in the switching system.
		Setting this object to disabled(2) disables PNNI
		capability in the switch.  Setting it to enabled(1)
		enables PNNI capability." 
	::= { cnPnniMainExt 1 }

cnPnniCurNodes OBJECT-TYPE
	SYNTAX INTEGER
	ACCESS read-only
	STATUS mandatory
	DESCRIPTION
		"The number of PNNI logical nodes currently configured 
		in the switching system."
      	::= { cnPnniMainExt 2 }


-- LECS Configuration Extention Table

lecsConfExtTable    OBJECT-TYPE
       SYNTAX SEQUENCE OF LecsConfExtEntry
       ACCESS not-accessible
       STATUS mandatory
       DESCRIPTION
	       "This table contains the configuration
	       information that are additional to the 
	       existing lecsConfTable"
       ::= { cnPnnilecsExt 1}

lecsConfExtEntry OBJECT-TYPE
       SYNTAX LecsConfExtEntry
       ACCESS not-accessible
       STATUS mandatory
       DESCRIPTION
	       "Each entry represents a LECS this
	       agent maintains in this extension table.
	       A row in this table is not valid unless
	       the same row is valid in the lecsConfTable
	       defined in af1129r5.mib"
       INDEX { lecsConfIndex }
       ::= { lecsConfExtTable 1 }

LecsConfExtEntry ::= SEQUENCE {
       lecsConfExtScope
	       INTEGER
       }

lecsConfExtScope   OBJECT-TYPE
       SYNTAX INTEGER (0..104)
       ACCESS read-write
       STATUS mandatory
       DESCRIPTION
	       "PNNI scope value"
       ::= { lecsConfExtEntry 1}

-- PNNI Database Overload Configurable Parameters

cnPnniMemConsumptionLowwater OBJECT-TYPE
        SYNTAX  INTEGER
        ACCESS  read-write
        STATUS  mandatory
        DESCRIPTION
              "The value of low memory watermark. If memory allocated
              to PNNI task is less than this value, then the
              Database resynchronization be attempted."
        ::= { cnPnniTdbOverload 1 }

cnPnniMemConsumptionHighwater OBJECT-TYPE
        SYNTAX  INTEGER
        ACCESS  read-write
        STATUS  mandatory
        DESCRIPTION
              "The value of high memory watermark. If memory allocated
              to PNNI task is greater than this value, then the
              node will enter to topology database overload state."
        ::= { cnPnniTdbOverload 2 }

cnPnniOverLoadRetryTime OBJECT-TYPE
        SYNTAX  INTEGER
        ACCESS  read-write
        STATUS  mandatory
        DESCRIPTION
              "The value of the database resynch attempt timer in
              seconds."
        ::= { cnPnniTdbOverload 3 }


END


-- SECTION 1: Top Level Definitions


CENTILLION-SYSTEM-MONITOR-MIB DEFINITIONS ::= BEGIN


-- Centillion System Monitoring MIB Release 2.0.1
-- Revision 07/11/2000

-- Copyright 1994-2000 Nortel Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	Counter
		FROM RFC1155-SMI
	OBJECT-TYPE
		FROM RFC-1212
	sysMonitor
		FROM CENTILLION-ROOT-MIB;


-- SECTION 2: System Monitoring Information

cardMonitorTable OBJECT-TYPE
	SYNTAX	SEQUENCE OF CardMonEntry
	ACCESS	not-accessible
	STATUS	mandatory
	DESCRIPTION
		"Card Monitor Table."
	::= { sysMonitor 1 }

cardMonEntry OBJECT-TYPE
	SYNTAX	CardMonEntry
	ACCESS	not-accessible
	STATUS	mandatory
	DESCRIPTION
		"An entry in the card monitor table. Each entry represents
		statistics collected on each possible slot in the system."
	INDEX	{ cardMonIndex }
	::= { cardMonitorTable 1 }

CardMonEntry ::= SEQUENCE {
	cardMonIndex
		INTEGER,
	cardMonCellsReceived
		Counter,
	cardMonCellsTransmitted
		Counter,
	cardMonCellsDropped
		Counter,
	cardMonSARReceived
		Counter,
	cardMonSARTransmitted
		Counter,
	cardMonSARDropped
		Counter,
	cardMonMSIMsgs
		Counter,
	cardMonCardInsertions
		Counter,
	cardMonCardRemovals
		Counter
	}

cardMonIndex OBJECT-TYPE
	SYNTAX	INTEGER
	ACCESS	read-only
	STATUS	mandatory
	DESCRIPTION
		"The card number index. Valid entries are system dependent
		based on the chassis type."
	::= { cardMonEntry 1 }

cardMonCellsReceived OBJECT-TYPE
	SYNTAX	Counter
	ACCESS	read-only
	STATUS	mandatory
	DESCRIPTION
		"The number of cells revceived by the card. Note this
		statistic is not maintained in high-performance mode."
	::= { cardMonEntry 2 }

cardMonCellsTransmitted OBJECT-TYPE
	SYNTAX	Counter
	ACCESS	read-only
	STATUS	mandatory
	DESCRIPTION
		"The number of cells transmitted by the card. Note this
		statistic is not maintained in high-performance mode."
	::= { cardMonEntry 3 }

cardMonCellsDropped OBJECT-TYPE
	SYNTAX	Counter
	ACCESS	read-only
	STATUS	mandatory
	DESCRIPTION
		"The number of cells dropped by the card."
	::= { cardMonEntry 4 }

cardMonSARReceived OBJECT-TYPE
	SYNTAX	Counter
	ACCESS	read-only
	STATUS	mandatory
	DESCRIPTION
		"The number of SAR packets revceived by the card. Note this
		statistic is not maintained in high-performance mode."
	::= { cardMonEntry 5 }

cardMonSARTransmitted OBJECT-TYPE
	SYNTAX	Counter
	ACCESS	read-only
	STATUS	mandatory
	DESCRIPTION
		"The number of SAR packetd transmitted by the card. Note this
		statistic is not maintained in high-performance mode."
	::= { cardMonEntry 6 }

cardMonSARDropped OBJECT-TYPE
	SYNTAX	Counter
	ACCESS	read-only
	STATUS	mandatory
	DESCRIPTION
		"The number of SAR packets dropped by the card."
	::= { cardMonEntry 7 }

cardMonMSIMsgs OBJECT-TYPE
	SYNTAX	Counter
	ACCESS	read-only
	STATUS	mandatory
	DESCRIPTION
		"The total number of MSI messages to and from the card. Note
		this statistic is not maintained in high-performance mode. "
	::= { cardMonEntry 8 }
	
cardMonCardInsertions OBJECT-TYPE
	SYNTAX	Counter
	ACCESS	read-only
	STATUS	mandatory
	DESCRIPTION
		"The number of card insertions into the slot represented by
		the slot number." 
	::= { cardMonEntry 9 }

cardMonCardRemovals OBJECT-TYPE
	SYNTAX	Counter
	ACCESS	read-only
	STATUS	mandatory
	DESCRIPTION
		"The number of card removals on the slot."
	::= { cardMonEntry 10 }

cpuPctUse OBJECT-TYPE
    SYNTAX INTEGER
    ACCESS read-only
    STATUS mandatory
    DESCRIPTION
           "Current utilization of the MCP cpu.
           Displays the utilization of the MCP cpu as a percentage at the time
           the object is polled. CPU utilization is highly variable, and as
           such, cpuPctUse can only be considered a snap shot and may not
           be valid immediately after polling the object."
    ::= { sysMonitor 4 }

END
-- SECTION 1: Top Level Definitions


CENTILLION-SOURCE-ROUTING-MIB DEFINITIONS ::= BEGIN


-- Centillion Source Routing MIB Release 2.0.0
-- Revision 03/20/96

-- Copyright 1994-96 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	EnableIndicator
		FROM CENTILLION-ROOT-MIB
	cndot1dSr
		FROM CENTILLION-BRIDGE-MIB
	OBJECT-TYPE
		FROM RFC-1212;


-- SECTION 2: Source Routing Port Table 

cndot1dSrPortTable OBJECT-TYPE
	SYNTAX  SEQUENCE OF Cndot1dSrPortEntry
	ACCESS  not-accessible
	STATUS  mandatory
	DESCRIPTION
		"A table that contains information about every
		port that is associated with this source route
		bridge."
	::= { cndot1dSr 1 }

cndot1dSrPortEntry OBJECT-TYPE
	SYNTAX  Cndot1dSrPortEntry
	ACCESS  not-accessible
	STATUS  mandatory
	DESCRIPTION
		"A list of information for each port of a source
		route bridge."
	INDEX   { cndot1dSrPort }
	::= { cndot1dSrPortTable 1 }

Cndot1dSrPortEntry ::= SEQUENCE {
	cndot1dSrPort
		INTEGER,
	cndot1dSrPortAREHopCount
		INTEGER,
	cndot1dSrPortSTEHopCount
		INTEGER
	}

cndot1dSrPort OBJECT-TYPE
	SYNTAX  INTEGER (1..65535)
	ACCESS  read-only
	STATUS  mandatory
	DESCRIPTION
		"The port number of the port for which this entry
		contains Source Route management information."
	::= { cndot1dSrPortEntry 1 }

cndot1dSrPortAREHopCount OBJECT-TYPE
	SYNTAX  INTEGER
	ACCESS  read-write
	STATUS  mandatory
	DESCRIPTION
		"The maximum number of routing descriptors allowed
		in an All Paths Explorer frames."
	::= { cndot1dSrPortEntry 2 }

cndot1dSrPortSTEHopCount OBJECT-TYPE
	SYNTAX  INTEGER
	ACCESS  read-write
	STATUS  mandatory
	DESCRIPTION
		"The maximum number of routing descriptors allowed
		in an Spanning Tree Explorer frames."
	::= { cndot1dSrPortEntry 3 }

cndot1dSrExplorerProxy OBJECT-TYPE
	SYNTAX  EnableIndicator
	ACCESS  read-write
	STATUS  mandatory
	DESCRIPTION
		"Indicates whether the bridge proxies explorer
		packets."
	::= { cndot1dSr 3 }

cndot1dSrBridgeNum OBJECT-TYPE
        SYNTAX  INTEGER
        ACCESS  read-write
        STATUS  mandatory
	DESCRIPTION
               "A bridge number uniquely identifies a bridge when
                more than one bridge is used to span the same two
                segments.  Current source routing protocols limit
                this value to the range: 0 through 15. A value of
                65535 signifies that no bridge number is assigned
                to this bridge. This bridge number is global to a
                SR bridge group. That is all local segments defined
                to a SR bridge group will use the same bridge number."
	::= { cndot1dSr 4 }

END
-- SECTION 1: Top Level Definitions


CENTILLION-PORT-RING-MASTER-MONITOR-MIB DEFINITIONS ::= BEGIN


-- Centillion Token Ring Port Ring Master Monitor MIB Release 2.0.0
-- Revision 03/20/96

-- Copyright 1995-96 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	OBJECT-TYPE
		FROM RFC-1212
	TimeTicks, IpAddress
		FROM RFC1155-SMI
	MacAddress, sysMonitor
		FROM CENTILLION-ROOT-MIB;


-- SECTION 2: TR Port Ring Master Monitoring Information

portRmLastChg	OBJECT-TYPE
	SYNTAX	TimeTicks
	ACCESS	read-only
	STATUS	mandatory
	DESCRIPTION
		"The value of sysUpTime the last time an entry in the
		 Port Ring master Table was added, deleted, or modified.
		 If the Port Ring master Table has not changed since cold/warm
		 start of the agent, then the value is zero."
	::= { sysMonitor 2 }

portRmTable OBJECT-TYPE
	SYNTAX	SEQUENCE OF PortRmEntry
	ACCESS	not-accessible
	STATUS	mandatory
	DESCRIPTION
		"Port Ring Master Monitor Table."
	::= { sysMonitor 3 }

portRmEntry OBJECT-TYPE
	SYNTAX	PortRmEntry
	ACCESS	not-accessible
	STATUS	mandatory
	DESCRIPTION
		"A row in the Port NMM Table.  Entries in the table can
		 not be created or deleted via SNMP."
	INDEX	{ portRmSlotNum, portRmPortNum }
	::= { portRmTable 1 }

PortRmEntry ::= SEQUENCE {
	portRmSlotNum
		INTEGER,
	portRmPortNum
		INTEGER,
	portRmIpAddr
		IpAddress,
	portRmMacAddr
		MacAddress
	}

portRmSlotNum OBJECT-TYPE
	SYNTAX	INTEGER (0..255)
	ACCESS	read-only
	STATUS	mandatory
	DESCRIPTION
		"The slot on which the topology message was received.
		NOTE: Non-modular devices that do not have multiplt slots
		should set this value to 1."
	::= { portRmEntry 1 }

portRmPortNum OBJECT-TYPE
	SYNTAX  INTEGER (0..255)
	ACCESS	read-only
	STATUS	mandatory
	DESCRIPTION
		"The port on which the RM_HELLO topology message was 
		 received."
	::= { portRmEntry 2 }

portRmIpAddr OBJECT-TYPE
	SYNTAX	IpAddress
	ACCESS	read-only
	STATUS	mandatory
	DESCRIPTION
		"The IP address of the sender of the RM_HELLO topology
		 message."
	::= { portRmEntry 3 }

portRmMacAddr OBJECT-TYPE
	SYNTAX	MacAddress
	ACCESS	read-only
	STATUS	mandatory
	DESCRIPTION
		"The MAC address of the sender of the RM_HELLO topology
		 message."
	::= { portRmEntry 4 }


END
-- SECTION 1: Top Level Definitions


CENTILLION-FILTERS-MIB DEFINITIONS ::= BEGIN

-- Centillion Filters MIB Release 2.0.5
-- Revision 04/18/00

-- Copyright 1994-2000 Nortel Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.

-- This file defines the MIB for objects for maintenance of the filter
-- tables and statstics.

-- Imports

IMPORTS
	DisplayString
		FROM RFC1213-MIB
	OBJECT-TYPE
		FROM RFC-1212
	StatusIndicator, sysConfig
		FROM CENTILLION-ROOT-MIB;


-- Textual Conventions

-- General filter group names are user-defined ASCII strings up to
-- 8 characters.

GeneralFilterName ::= DisplayString (SIZE (8))

-- NetBIOS filter names are blank padded ASCII strings of 16
-- characters.

NetbiosFilterName ::= DisplayString (SIZE(16))

-- NetBIOS Filter actions. Frames are either discarded or forwarded
-- according to the name and action

NetbiosFilterAction ::=
	INTEGER {
		discard(1),
		forward(2)
	}


-- Groups

filterGroup	OBJECT IDENTIFIER ::= { sysConfig 11 }


-- SECTION 2: General Filter Group Table

-- This section defines the filter group table. Filter groups are composed
-- of some number of filter entries. Each filter group is identified by a
-- unique filter group name.

filterGroupTable OBJECT-TYPE
	SYNTAX	SEQUENCE OF FilterGroupEntry
	ACCESS	not-accessible
	STATUS	mandatory
	DESCRIPTION
		"Filter Group Table. Entries are added into the group by
		specifying values for all objects with the exception
		of the filterGroupMonitorDests and filterGroupAdditionalDests
		objects. Entries are deleted simply by specifying the
		appropriate filterGroupStatus value."
	::= { filterGroup 1 }

filterGroupEntry OBJECT-TYPE
	SYNTAX	FilterGroupEntry
	ACCESS	not-accessible
	STATUS	mandatory
	DESCRIPTION
		"An entry in the filter group table. Table entries are indexed
		by the unique user-defined group name, and the filter entry
		index as assigned by the system."
	INDEX	{ filterGroupName, filterGroupIndex }
	--	INDEX	{ IMPLIED filterGroupName, filterGroupIndex }
	::= { filterGroupTable 1 }

FilterGroupEntry ::= SEQUENCE {
	filterGroupName
		GeneralFilterName,
	filterGroupIndex
		INTEGER,
	filterGroupStatus
		StatusIndicator,
	filterGroupMatch
		INTEGER,
	filterGroupType
		INTEGER,
	filterGroupOffset
		INTEGER,
	filterGroupValue
		OCTET STRING,
	filterGroupForward
		INTEGER,
	filterGroupNextIfMatch
		INTEGER,
	filterGroupNextIfFail
		INTEGER,
	filterGroupMonitorDests
		OCTET STRING,
	filterGroupAdditionalDests
		OCTET STRING,
	filterGroupAlternateDestination
		OCTET STRING,
	filterGroupAdditionalDestinations
		OCTET STRING,
    filterGroupPriority
        INTEGER
	}

filterGroupName OBJECT-TYPE
	SYNTAX	GeneralFilterName
	ACCESS	read-write
	STATUS	mandatory
	DESCRIPTION
		"A user-defined unique ASCII string identifying the filter
		group."
	::= { filterGroupEntry 1 }

filterGroupIndex OBJECT-TYPE
	SYNTAX	INTEGER
	ACCESS	read-write
	STATUS	mandatory
	DESCRIPTION
		"The index of the filter entry within the filter group. Any
		filter group entry is uniquely identifable by the group nam
		and index."
	::= { filterGroupEntry 2 }

filterGroupStatus OBJECT-TYPE
	SYNTAX	StatusIndicator
	ACCESS	read-write
	STATUS	mandatory
	DESCRIPTION
		"The status of this filter group entry. Entries may be
		deleted by setting this object to invalid(2)."
	::= { filterGroupEntry 3 }

filterGroupMatch OBJECT-TYPE
	SYNTAX	INTEGER {
		lt(1),		-- match if less than
		eq(2),		-- match if equal
		le(3),		-- match if less than or equal
		gt(4),		-- match if greater than
		ne(5),		-- match if not equal
		ge(6)		-- match if greater than or equal
		}
	ACCESS	read-write
	STATUS	mandatory
	DESCRIPTION
		"The match condition for the filter. Match conditions are in
		the form of the usual logical operators."
	::= { filterGroupEntry 4 }

filterGroupType OBJECT-TYPE
	SYNTAX	INTEGER {
		macFilter(1),	-- filter offset begins at the MAC header
		llcFilter(2),	-- filter offset from end of RIF
		vlanFilter(3)   -- vlan filter
		}
	ACCESS	read-write
	STATUS	mandatory
	DESCRIPTION
		"The type of filter. MAC filters are defined from the start
		of the MAC frame. LLC filters are defined from the start
                of the LLC header (after RIF). VLAN filters operate on
                a packet's VLAN classification parameters. For a valid
                VLAN filter, filterGroupOffset be set to 0, and
                filterGroupValue must contain exactly four bytes of VLAN 
                filter data as shown below:

            Octet 1
                 Defines the user priority match criteria for VLAN
                 filter. Valid values are 0x01 through 0xFF. Each bit
                 in the octet corresponds to one of the eight available
                 user priority level as defined by the 802.1Q draft
                 specification. The least significant bit represents
                 priority zero, and the most significant bit 
                 represents priority seven.

            Octet 2
                 Defines the Canonical Format Indicator (CFI) match 
                 criteria for VLAN filter. Possible values are 0x00, 0x01 
                 and 0xFF. The value 0xFF indicates the switch should 
                 ignore CFI value when filtering.

            Octet 3 and 4
                 Define 12-bit VLAN ID match criteria for VLAN filter.
                 Valid values are 0x001 through 0xFFF."

	::= { filterGroupEntry 5 }

filterGroupOffset OBJECT-TYPE
	SYNTAX	INTEGER
	ACCESS	read-write
	STATUS	mandatory
	DESCRIPTION
		"The byte offset from the beginning of the header to the 
		value to filter."
	::= { filterGroupEntry 6 }

filterGroupValue OBJECT-TYPE
	SYNTAX	OCTET STRING (SIZE (1..12))
	ACCESS	read-write
	STATUS	mandatory
	DESCRIPTION
		"The filter value field. The value is specified as a 
		hexadecimal string up to 12 bytes."
	::= { filterGroupEntry 7 }

filterGroupForward OBJECT-TYPE
	SYNTAX	INTEGER {
		normClear(1),	-- normal forwarding cleared
		alt(2),		-- forward to alternate card/ports
		add(3),		-- forward to addiitional card/ports
		addAlt(4),	-- forward to additional and alt card/ports
		norm(5),	-- forward using normal rules
		normAlt(6),	-- forward to normal and alt card/ports
		normAdd(7), 	-- forward to normal and add card/ports
		normAddAlt(8),	-- forward to norm+add+alt card/ports
		drop(9)		-- frame is dropped
		}
	ACCESS	read-write
	STATUS	mandatory
	DESCRIPTION
		"The forwarding rule for the filter. Forward to normal
		indicates that the frame should be forwarded as usual."
	::= { filterGroupEntry 8 }

filterGroupNextIfMatch OBJECT-TYPE
	SYNTAX	INTEGER
	ACCESS	read-write
	STATUS	mandatory
	DESCRIPTION
		"The next filter entry as referenced by the filter index
		to apply if the filter match succeeds. An entry of 0 indicates
		that filtering ends for the packet. An entry whose value
		is larger than the number of filters in the group indicates
		that the next filter entry to apply is the next filter
		group (if any) enabled on the port."
	::= { filterGroupEntry 9 }

filterGroupNextIfFail OBJECT-TYPE
	SYNTAX	INTEGER
	ACCESS	read-write
	STATUS	mandatory
	DESCRIPTION
		"The next filter entry as referenced by the filter index
		to apply if the filter match fails. An entry of 0 indicates
		that filtering ends for the packet. An entry whose value
		is larger than the number of filters in the group indicates
		that the next filter entry to apply is the next filter
		group (if any) enabled on the port."
	::= { filterGroupEntry 10 }

filterGroupAdditionalDests OBJECT-TYPE
	SYNTAX	OCTET STRING (SIZE (0..256))
	ACCESS	read-write
	STATUS	deprecated
	DESCRIPTION
		"This will be replaced by filterGroupAdditionalDestions.
		A list of up to 256 pairs of additional cards and ports 
		to send packets matching this filter. Each unsigned int8 
		is formatted as follows: 
		the high-order 4 bits represent the card number, the low
		order 4 bits are the port number."
	::= { filterGroupEntry 11 }

filterGroupMonitorDests OBJECT-TYPE
	SYNTAX	OCTET STRING (SIZE (0..1))
	ACCESS	read-write
	STATUS 	deprecated	
	DESCRIPTION
		"This will be replaced by filterGroupAlternateDestination.
		A pair of the monitoring card and port to send packets
		matching this filter. Each unsigned int8 is formatted 
		as follows:
		the high-order 4 bits represent the card number, the low
		order 4 bits are the port number."
	::= { filterGroupEntry 12 }

filterGroupAdditionalDestinations OBJECT-TYPE
	SYNTAX	OCTET STRING (SIZE (0..512))
	ACCESS	read-write
	STATUS	mandatory
	DESCRIPTION
		"For 24 ports support. This is to replace 
		filterGroupAdditionalDests. Setting either 
		filterGroupAdditionalDests or filterGroupAlternateDestination 
		is enough. And if both are set, the one set later will be 
		in effect. Make sure that even number of octets are given.
		A list of up to 256 pairs of additional cards and ports 
		to send packets matching this filter. Each pair of octets 
		is formatted as follows: 
		the high-order octet represent the card number, the low
		order octet is the port number."
	::= { filterGroupEntry 13 }

filterGroupAlternateDestination OBJECT-TYPE
	SYNTAX	OCTET STRING (SIZE (0..2))
	ACCESS	read-write
	STATUS	mandatory
	DESCRIPTION
		"For 24 ports support. This is to replace 
		filterGroupMonitorDests. Setting either filterGroupMonitorDests
		filterGroupAlternateDestination is enough. And if both
		are set, the one set later will be in effect.
		Make sure that even number of octets are given.
		A pair of the monitoring card and port to send packets
		matching this filter. Each pair of octets is formatted 
		as follows:
		the high-order byte represent the card number, the low
		order byte is the port number."
	::= { filterGroupEntry 14 }
 
filterGroupPriority OBJECT-TYPE
    SYNTAX  INTEGER {
        priUnchanged(1),    -- forward without changing priority
        priNorm(2),         -- forward with normal priority
        priHigh(3)          -- forward with high priority
        }
    ACCESS  read-write
    STATUS  mandatory
    DESCRIPTION
        "The forwarding priority for the filter. A value of (1) indicates
        that forwarding should occur with the native priority defined by
        802.1Q or other priority classification methods.  Values (2) and
        (3) override all previous priority classification methods."
    ::= { filterGroupEntry 15 }

-- Filter Port Table
--
-- This section defines the inbound filter port table. The inbound filter 
-- port table defines the active filter groups associated with the 
-- inbound packets received by a  card and port. Filters are
-- configured by first establishing appropriate filter groups, then
-- applying the groups to some number of cards and ports using this table.


filterPortTable OBJECT-TYPE
	SYNTAX	SEQUENCE OF FilterPortEntry
	ACCESS	not-accessible
	STATUS	mandatory
	DESCRIPTION
		"Input Filter Port Table."
	::= { filterGroup 2 }

filterPortEntry OBJECT-TYPE
	SYNTAX	FilterPortEntry
	ACCESS	not-accessible
	STATUS	mandatory
	DESCRIPTION
		"An entry in the filter group table. Table entries are indexed
		by the unique user-defined group name, and the filter entry
		index as assigned by the system."
	INDEX	{ filterPortCardNumber, filterPortPortNumber, filterPortIndex }
	::= { filterPortTable 1 }

FilterPortEntry ::= SEQUENCE {
	filterPortCardNumber
		INTEGER,
	filterPortPortNumber
		INTEGER,
	filterPortIndex
		INTEGER,
	filterPortStatus
		StatusIndicator,
	filterPortGroupName
		GeneralFilterName
	}

filterPortCardNumber OBJECT-TYPE
	SYNTAX	INTEGER
	ACCESS	read-write
	STATUS	mandatory
	DESCRIPTION
		"The card number to which the filters apply."
	::= { filterPortEntry 1}

filterPortPortNumber OBJECT-TYPE
	SYNTAX	INTEGER
	ACCESS	read-write
	STATUS	mandatory
	DESCRIPTION
		"The port number to which the filters apply."
	::= { filterPortEntry 2 }

filterPortIndex OBJECT-TYPE
	SYNTAX	INTEGER
	ACCESS	read-write
	STATUS	mandatory
	DESCRIPTION
		"A unique value for each filter group within the port."
	::= { filterPortEntry 3 }

filterPortStatus OBJECT-TYPE
	SYNTAX	StatusIndicator
	ACCESS	read-write
	STATUS	mandatory
	DESCRIPTION
		"The status of this filter port entry. Entries may be
		deleted by setting this object to invalid(2)."
	::= { filterPortEntry 4 }

filterPortGroupName OBJECT-TYPE
	SYNTAX	GeneralFilterName
	ACCESS	read-write
	STATUS	mandatory
	DESCRIPTION
		"The filter port group name."
	::= { filterPortEntry 5 }


-- SECTION 3: NetBios Filter Tables

-- This section defines the NetBIOS Name filter table. The table contains
-- a list of NetBIOS names, along with the action taken upon matching
-- the name. There are two tables. One listed by card and port numbers, 
-- the other is based upon virtual ring number.

-- NetBios Filter Port Table

netbiosFilterPortTable OBJECT-TYPE
	SYNTAX	SEQUENCE OF NetbiosFilterPortEntry
	ACCESS	not-accessible
	STATUS	mandatory
	DESCRIPTION
		"The NetBIOS name filter table indexed by card and port
		numbers. "
	::= { filterGroup 3 }

netbiosFilterPortEntry OBJECT-TYPE
	SYNTAX	NetbiosFilterPortEntry
	ACCESS	not-accessible
	STATUS	mandatory
	DESCRIPTION
		"An entry in the NetBios filter port table. Table entries
		are indexed by the card, port and PortIndex as assigned
		by the system."
	INDEX	{ netbiosFilterPortCardNumber, netbiosFilterPortPortNumber,
		  netbiosFilterPortIndex }
	::= { netbiosFilterPortTable 1 }

NetbiosFilterPortEntry ::= SEQUENCE {
	netbiosFilterPortCardNumber
		INTEGER,
	netbiosFilterPortPortNumber
		INTEGER,
	netbiosFilterPortIndex
		INTEGER,
	netbiosFilterPortStatus
		StatusIndicator,
	netbiosFilterPortName
		NetbiosFilterName,
	netbiosFilterPortAction
		NetbiosFilterAction
	}

netbiosFilterPortCardNumber OBJECT-TYPE
	SYNTAX	INTEGER
	ACCESS	read-write
	STATUS	mandatory
	DESCRIPTION
		"The card number to which the filters apply."
	::= { netbiosFilterPortEntry 1}

netbiosFilterPortPortNumber OBJECT-TYPE
	SYNTAX	INTEGER
	ACCESS	read-write
	STATUS	mandatory
	DESCRIPTION
		"The port number to which the filters apply."
	::= { netbiosFilterPortEntry 2 }

netbiosFilterPortIndex OBJECT-TYPE
	SYNTAX	INTEGER
	ACCESS	read-write
	STATUS	mandatory
	DESCRIPTION
		"A unique value for each filter group within the port."
	::= { netbiosFilterPortEntry 3 }

netbiosFilterPortStatus OBJECT-TYPE
	SYNTAX	StatusIndicator
	ACCESS	read-write
	STATUS	mandatory
	DESCRIPTION
		"The status of this NetBIOS filter entry. Entries may be
		deleted by setting this object to invalid(2)."
	::= { netbiosFilterPortEntry 4 }

netbiosFilterPortName OBJECT-TYPE
	SYNTAX	NetbiosFilterName
	ACCESS	read-write
	STATUS	mandatory
	DESCRIPTION
		"The NetBIOS name to match for filtering. The name will
		be blank padded."
	::= { netbiosFilterPortEntry 5 }

netbiosFilterPortAction OBJECT-TYPE
	SYNTAX	NetbiosFilterAction
	ACCESS	read-write
	STATUS	mandatory
	DESCRIPTION
		"The action to take upon matching the name filter."
	::= { netbiosFilterPortEntry 6 }


-- NetBios Filter Ring Table

netbiosFilterRingTable OBJECT-TYPE
	SYNTAX	SEQUENCE OF NetbiosFilterRingEntry
	ACCESS	not-accessible
	STATUS	mandatory
	DESCRIPTION
		"The NetBIOS name filter table indexed by ring number."
	::= { filterGroup 4 }

netbiosFilterRingEntry OBJECT-TYPE
	SYNTAX	NetbiosFilterRingEntry
	ACCESS	not-accessible
	STATUS	mandatory
	DESCRIPTION
		"An entry in the NetBios filter port table. Table entries
		are indexed by ring number and PortIndex as assigned
		by the system."
	INDEX	{ netbiosFilterRingNumber,  netbiosFilterRingIndex }
	::= { netbiosFilterRingTable 1 }

NetbiosFilterRingEntry ::= SEQUENCE {
	netbiosFilterRingNumber
		INTEGER,
	netbiosFilterRingIndex
		INTEGER,
	netbiosFilterRingStatus
		StatusIndicator,
	netbiosFilterRingName
		NetbiosFilterName,
	netbiosFilterRingAction
		NetbiosFilterAction
	}

netbiosFilterRingNumber OBJECT-TYPE
	SYNTAX	INTEGER
	ACCESS	read-write
	STATUS	mandatory
	DESCRIPTION
		"The ring number to which the filters apply."
	::= { netbiosFilterRingEntry 1}

netbiosFilterRingIndex OBJECT-TYPE
	SYNTAX	INTEGER
	ACCESS	read-write
	STATUS	mandatory
	DESCRIPTION
		"A unique value for each filter group within the port."
	::= { netbiosFilterRingEntry 2 }

netbiosFilterRingStatus OBJECT-TYPE
	SYNTAX	StatusIndicator
	ACCESS	read-write
	STATUS	mandatory
	DESCRIPTION
		"The status of this NetBIOS filter entry. Entries may be
		deleted by setting this object to invalid(2)."
	::= { netbiosFilterRingEntry 3 }

netbiosFilterRingName OBJECT-TYPE
	SYNTAX	NetbiosFilterName
	ACCESS	read-write
	STATUS	mandatory
	DESCRIPTION
		"The NetBIOS name to match for filtering. The name will be
		blank padded."
	::= { netbiosFilterRingEntry 4 }

netbiosFilterRingAction OBJECT-TYPE
	SYNTAX	NetbiosFilterAction
	ACCESS	read-write
	STATUS	mandatory
	DESCRIPTION
		"The action to take upon matching the name filter."
	::= { netbiosFilterRingEntry 5 }


-- Output Filter Port Table
--
-- This section defines the output filter port table. The output filter 
-- port table defines the active filter groups associated with the
-- outbound packets forwarded by a card and port. Filters 
-- are configured by first establishing appropriate filter groups, then
-- applying the groups to some number of cards and ports using this table.


outputFilterPortTable OBJECT-TYPE
      SYNTAX  SEQUENCE OF OutputFilterPortEntry
      ACCESS  not-accessible
      STATUS  mandatory
      DESCRIPTION
              "Output Filter Port Table."
      ::= { filterGroup 5 }

outputFilterPortEntry OBJECT-TYPE
      SYNTAX  OutputFilterPortEntry
      ACCESS  not-accessible
      STATUS  mandatory
      DESCRIPTION
              "An entry in the filter group table. Table entries are
              indexed by the unique user-defined group name, and the filter entry
              index as assigned by the system."
      INDEX   { outputFilterPortCardNumber, outputFilterPortPortNumber,
outputFilterPortIndex }
      ::= { outputFilterPortTable 1 }

OutputFilterPortEntry ::= SEQUENCE {
      outputFilterPortCardNumber
              INTEGER,
      outputFilterPortPortNumber
              INTEGER,
      outputFilterPortIndex
              INTEGER,
      outputFilterPortStatus
              StatusIndicator,
      outputFilterPortGroupName
              GeneralFilterName
      }

outputFilterPortCardNumber OBJECT-TYPE
      SYNTAX  INTEGER
      ACCESS  read-write
      STATUS  mandatory
      DESCRIPTION
              "The card number to which the filters apply."
      ::= { outputFilterPortEntry 1}

outputFilterPortPortNumber OBJECT-TYPE
      SYNTAX  INTEGER
      ACCESS  read-write
      STATUS  mandatory
      DESCRIPTION
              "The port number to which the filters apply."
      ::= { outputFilterPortEntry 2 }

outputFilterPortIndex OBJECT-TYPE
      SYNTAX  INTEGER
      ACCESS  read-write
      STATUS  mandatory
      DESCRIPTION
              "A unique value for each filter group within the port."
      ::= { outputFilterPortEntry 3 }

outputFilterPortStatus OBJECT-TYPE
      SYNTAX  StatusIndicator
      ACCESS  read-write
      STATUS  mandatory
      DESCRIPTION
              "The status of this filter port entry. Entries may be
              deleted by setting this object to invalid(2)."
      ::= { outputFilterPortEntry 4 }

outputFilterPortGroupName OBJECT-TYPE
      SYNTAX  GeneralFilterName
      ACCESS  read-write
      STATUS  mandatory
      DESCRIPTION
              "The filter port group name."
      ::= { outputFilterPortEntry 5 }


END


-- SECTION 1: Top Level Definitions


CENTILLION-ATMCFG-MIB DEFINITIONS ::= BEGIN


-- Centillion ATM Configuration MIB Release 2.1.1
-- Revision 06/24/99

-- Copyright 1999 Nortel Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	OBJECT-TYPE
		FROM RFC-1212
	atmConfig, EnableIndicator
		FROM CENTILLION-ROOT-MIB
	VirtualSegmentTypeId
		FROM CENTILLION-VIRTUALSEGMENT-MIB;


-- Groups

atmElanConfig	OBJECT IDENTIFIER ::=	{ atmConfig 1 }
atmCktTable	OBJECT IDENTIFIER ::=	{ atmConfig 2 }
atmPortConfig	OBJECT IDENTIFIER ::=	{ atmConfig 3 }
atmSysConfig	OBJECT IDENTIFIER ::=	{ atmConfig 4 }
atmPortLogConfig OBJECT IDENTIFIER ::=  { atmConfig 5 }


-- SECTION 2: Elan Configuration Group

-- This group contains information pertaining to ATM elan
-- configuration in the system

atmElanConfigTable OBJECT-TYPE
	SYNTAX  SEQUENCE OF AtmElanConfigEntry
	ACCESS  not-accessible
	STATUS  mandatory
	DESCRIPTION
		"ATM elan table"
	::= { atmElanConfig 1 }

atmElanConfigEntry OBJECT-TYPE
	SYNTAX  AtmElanConfigEntry
	ACCESS  not-accessible
	STATUS  mandatory
	DESCRIPTION
		"ATM elan table.
		Each entry is indexed by one field:
		elan id."
	INDEX  { atmElanIndex } 
	::= { atmElanConfigTable 1 }

AtmElanConfigEntry ::= SEQUENCE {
	atmElanIndex
		INTEGER,
	atmElanType
		INTEGER,
	atmElanEnable
		INTEGER,
	atmElanAllCkts
		OCTET STRING,
	atmElanVirtualCard
		INTEGER,
	atmElanVirtualPort
		INTEGER,
	atmElanVirtualSegmentId
		INTEGER,
	atmElanStatus
		INTEGER,
	atmElanVirtualSegmentType
		VirtualSegmentTypeId,
	atmElanBridgeGroupId
		INTEGER,
      	atmElanMaxUnknownFrameCount
              	INTEGER,
      	atmElanMaxUnknownFrameTime
              	INTEGER,
      	atmElanVcBridgingEnable
                EnableIndicator,
	atmElanOneMModemEnable
                EnableIndicator
	}

atmElanIndex OBJECT-TYPE
	SYNTAX 	INTEGER (1..32)
	ACCESS 	read-write
	STATUS  mandatory
	DESCRIPTION 
		"The index to the atm elan table.
		support total of 32 circuits."
	::= { atmElanConfigEntry 1 }

atmElanType OBJECT-TYPE
	SYNTAX 	INTEGER {
		atmElanXob(1),
		atmElanBe(2),
		atmLecXob(3),		-- ATM Forum Circuit Saver LEC
		atmLecBe(4),            -- ATM Forum Turbo LEC
		atm1483Xob(5),		-- RFC 1483 PVC Circuit Saver
		atmNullXob(6)		-- RFC 1483 NULL Encap PVC Circuit Saver
		}
	ACCESS 	read-write
	STATUS  mandatory
	DESCRIPTION 
		"The elan type."
	::= { atmElanConfigEntry 2 }

atmElanEnable OBJECT-TYPE
	SYNTAX  INTEGER {
		enable(1),
		disable(2)
		}
	ACCESS	read-write
	STATUS 	mandatory
	DESCRIPTION
		"Enable bit of the elan.
		1 = enable elan
		2 = disable elan"
	::= { atmElanConfigEntry 3 }

atmElanAllCkts OBJECT-TYPE
	SYNTAX	OCTET STRING
	ACCESS 	read-only
	STATUS 	mandatory
	DESCRIPTION
		"Return all pvc circuits that belong to this elan.
		Each circuit id is a 32 bit field"
	::= { atmElanConfigEntry 4}

atmElanVirtualCard OBJECT-TYPE
	SYNTAX	INTEGER
	ACCESS 	read-only
	STATUS 	mandatory
	DESCRIPTION
		"Virtual card number."
	::= { atmElanConfigEntry 5}

atmElanVirtualPort OBJECT-TYPE
	SYNTAX	INTEGER
	ACCESS 	read-only
	STATUS 	mandatory
	DESCRIPTION
		"Virtual port number. Currently this number is the Elan id"
	::= { atmElanConfigEntry 6}

atmElanVirtualSegmentId OBJECT-TYPE
	SYNTAX	INTEGER
	ACCESS 	read-only
	STATUS 	mandatory
	DESCRIPTION
		"Virtual Segment ID of the segment that this Elan is a member of"
	::= { atmElanConfigEntry 7}

atmElanStatus OBJECT-TYPE
	SYNTAX 	INTEGER {
		add(1),
		delete(2)
		}
	ACCESS 	read-write
	STATUS  mandatory
	DESCRIPTION 
		"The current status of the entry. Entries may be added by 
		specifying a value of valid, and removed by setting the status
		to invalid."
	::= { atmElanConfigEntry 8 }

atmElanVirtualSegmentType OBJECT-TYPE
	SYNTAX	VirtualSegmentTypeId
	ACCESS	read-write
	STATUS 	mandatory
	DESCRIPTION 
		"The virtual segment type."
	::= { atmElanConfigEntry 9 }


atmElanBridgeGroupId OBJECT-TYPE
        SYNTAX  INTEGER
        ACCESS  read-only
        STATUS  mandatory
        DESCRIPTION
                "Spanning Tree Group ID of the spanning tree group that the
                virtual segment and this Elan are members of."
        ::= { atmElanConfigEntry 10}
 

atmElanMaxUnknownFrameCount OBJECT-TYPE
      	SYNTAX  INTEGER(1..10)
      	ACCESS  read-write
      	STATUS  mandatory
      	DESCRIPTION
               	"Maximum Unknown Frame Count.  See the description of
               	atmElanMaxUnknownFrameTime below."
      	DEFVAL { 10 }
      	::= { atmElanConfigEntry 11 }

atmElanMaxUnknownFrameTime OBJECT-TYPE
      	SYNTAX  INTEGER(1..60)
      	ACCESS  read-write
      	STATUS  mandatory
      	DESCRIPTION
               	"Maxinum Unknown Frame Time.  Within the period of time
              	 defined by the Maxinum Unknown Frame Time, a LAN Client
              	 will send no more than Maxinum Unknown Frame Count frames
              	 for a given unicast LAN Destination.
              	 This time value is expressed in seconds."
      	DEFVAL { 1 }
      	::= { atmElanConfigEntry 12 }

atmElanVcBridgingEnable OBJECT-TYPE
      	SYNTAX  EnableIndicator
      	ACCESS  read-write
      	STATUS  mandatory
      	DESCRIPTION
               	"This object is used to enable or disable VC Bridging on the vport.
              	 The default value for this object is disable."
      	DEFVAL { disabled }
      	::= { atmElanConfigEntry 13 }

atmElanOneMModemEnable OBJECT-TYPE
        SYNTAX  EnableIndicator
        ACCESS  read-write
        STATUS  mandatory
        DESCRIPTION
		"Flag to indicate whether the vport supports one meg modem 
		feature.  When this feature is enabled, data received from 
		all LAN ports in the same VLAN as the vport will be 
		forwarded only to the vport. "
        DEFVAL { disabled }
        ::= { atmElanConfigEntry 14 }

-- SECTION 3: Circuit Table Group

-- This group contains information pertaining to ATM pktckt connections
-- in the system.

-- The ATM Packet Circuit Table.

atmPktCktTable OBJECT-TYPE
	SYNTAX	SEQUENCE OF AtmPktCktEntry
	ACCESS	not-accessible
	STATUS	mandatory
	DESCRIPTION
		"ATM virtual circuit table."
	::= { atmCktTable 1 }

atmPktCktEntry OBJECT-TYPE
	SYNTAX	AtmPktCktEntry
	ACCESS	not-accessible
	STATUS	mandatory
	DESCRIPTION
		"ATM Packet Circuit table entry.
		 Each entry is indexed by one field:
		 The circuit index."
	INDEX	{ atmPktCktIndex }
	::= { atmPktCktTable 1 }

AtmPktCktEntry ::= SEQUENCE {
	atmPktCktIndex
		INTEGER, 
	atmPktCktPriority
		INTEGER,
	atmPktCktEnable
		INTEGER,
	atmPktCktType
		INTEGER,
	atmPktCktCost
		INTEGER,
	atmPktCktElanIndex
		INTEGER,
	atmPktCktCardPort
		INTEGER,
	atmPktCktVpi
		INTEGER,
	atmPktCktVci
		INTEGER,
	atmPktCktStatus
		INTEGER,
	atmPktCktCardPort2
		INTEGER
	}

atmPktCktIndex OBJECT-TYPE
	SYNTAX 	INTEGER (1..256)
	ACCESS 	read-write
	STATUS  mandatory
	DESCRIPTION 
		"The index to the packet circuit table.
		support total of 256 circuits."
	::= { atmPktCktEntry 1 }

atmPktCktPriority OBJECT-TYPE
	SYNTAX  INTEGER {
		normalPriority(1),
		highPriority(2)
		}
	ACCESS	read-write
	STATUS 	mandatory
	DESCRIPTION
		"Priority bit of the circuit.
		1 = normal priority
		2 = high priority"
	::= { atmPktCktEntry 2 }

atmPktCktEnable OBJECT-TYPE
	SYNTAX  INTEGER {
		enable(1),
		disable(2)
		}
	ACCESS	read-write
	STATUS 	mandatory
	DESCRIPTION
		"Enable bit of the circuit.
		1 = enable circuit
		2 = disable circuit"
	::= { atmPktCktEntry 3 }

atmPktCktType OBJECT-TYPE
	SYNTAX  INTEGER {
		virtualCkt(1),
		virtualPathCkt(2)
		}
	ACCESS	read-write
	STATUS 	mandatory
	DESCRIPTION
		"type bit of the circuit.
		1 = virtual circuit
		2 = virtual path circuit"
	::= { atmPktCktEntry 4 }

atmPktCktCost OBJECT-TYPE
	SYNTAX 	INTEGER (0..255)
	ACCESS 	read-write
	STATUS  mandatory
	DESCRIPTION 
		"The cost of the circuit.
		range from 0 to 255 with 0 the least cost."
	::= { atmPktCktEntry 5 }

atmPktCktElanIndex OBJECT-TYPE
	SYNTAX 	INTEGER (1..32)
	ACCESS 	read-write
	STATUS  mandatory
	DESCRIPTION 
		"The elan id this circuit belongs to."
	::= { atmPktCktEntry 6 }

atmPktCktCardPort OBJECT-TYPE
	SYNTAX 	INTEGER 
	ACCESS 	read-write
	STATUS  deprecated
	DESCRIPTION 
		"The atm card/port of the circuit. The card/port  
		takes one byte. This will be replaced by
		atmPktCktCardPort2"
	::= { atmPktCktEntry 7 }

atmPktCktVpi OBJECT-TYPE
	SYNTAX 	INTEGER 
	ACCESS 	read-write
	STATUS  mandatory
	DESCRIPTION 
		"The packet circuit vpi number."
	::= { atmPktCktEntry 8 }

atmPktCktVci OBJECT-TYPE
	SYNTAX 	INTEGER
	ACCESS 	read-write
	STATUS  mandatory
	DESCRIPTION 
		"The packet circuit vci number."
	::= { atmPktCktEntry 9 }

atmPktCktStatus OBJECT-TYPE
	SYNTAX 	INTEGER {
		add(1),
		delete(2)
		}
	ACCESS 	read-write
	STATUS  mandatory
	DESCRIPTION 
		"The current status of the entry. Entries may be added by 
		specifying a value of valid, and removed by setting the status
		to invalid."
	::= { atmPktCktEntry 10 }

atmPktCktCardPort2 OBJECT-TYPE
	SYNTAX	INTEGER
	ACCESS	read-write
	STATUS	mandatory
	DESCRIPTION
                "This mib is added for 24 ports card. This will replace 
		atmPktCktCardPort. The atm card/port of the circuit.
		The card and port takes one byte each."
	::= { atmPktCktEntry 11 }
			
-- The ATM Cell Circuit Table.

atmCellCktTable OBJECT-TYPE
	SYNTAX	SEQUENCE OF AtmCellCktEntry
	ACCESS  not-accessible
	STATUS	mandatory
	DESCRIPTION
		"ATM virtual circuit table."
	::= { atmCktTable 2 }

atmCellCktEntry OBJECT-TYPE
	SYNTAX	AtmCellCktEntry
	ACCESS	not-accessible
	STATUS	mandatory
	DESCRIPTION
		"ATM Cell Circuit table entry.
		 Each entry is indexed by one field:
		 The circuit index."
	INDEX	{ atmCellCktIndex }
	::= { atmCellCktTable 1 }

AtmCellCktEntry ::= SEQUENCE {
	atmCellCktIndex
		INTEGER, 
	atmCellCktPriority
		INTEGER,
	atmCellCktEnable
		INTEGER,
	atmCellCktType
		INTEGER,
	atmCellCktNumEndpt
		INTEGER,
	atmCellCktEndptList
		OCTET STRING,
	atmCellCktStatus
		INTEGER
	}

atmCellCktIndex OBJECT-TYPE
	SYNTAX 	INTEGER
	ACCESS 	read-write
	STATUS  mandatory
	DESCRIPTION 
		"The index to the packet circuit table.
		support total of 256 circuits."
	::= { atmCellCktEntry 1 }

atmCellCktPriority OBJECT-TYPE
	SYNTAX  INTEGER {
		normPriority(1),
		highPriority(2)
		}
	ACCESS	read-write
	STATUS 	mandatory
	DESCRIPTION
		"Priority bit of the circuit.
		1 = normal priority
		2 = high priority"
	::= { atmCellCktEntry 2 }

atmCellCktEnable OBJECT-TYPE
	SYNTAX  INTEGER {
		enable(1),
		disable(2)
		}	
	ACCESS	read-write
	STATUS 	mandatory
	DESCRIPTION
		"Enable bit of the cell circuit.
		1 = enable cell circuit
		2 = disable cell circuit"
	::= { atmCellCktEntry 3 }

atmCellCktType OBJECT-TYPE
	SYNTAX  INTEGER {
		virtualCkt(1),
		virtualPathCkt(2)
		}
	ACCESS	read-write
	STATUS 	mandatory
	DESCRIPTION
		"type bit of the circuit.
		1 = virtual circuit
		2 = virtual path circuit"
	::= { atmCellCktEntry 4 }

atmCellCktNumEndpt OBJECT-TYPE
	SYNTAX  INTEGER
	ACCESS	read-write
	STATUS 	mandatory
	DESCRIPTION
		"Number of endpoints in  the circuit.
		An endpoint is defined as a combination of 
		card/port/vpi/vci."
	::= { atmCellCktEntry 5 }

atmCellCktEndptList OBJECT-TYPE
	SYNTAX  OCTET STRING
	ACCESS	read-write
	STATUS 	mandatory
	DESCRIPTION
		"List of endpoints for the circuit.
		Each endpoint includes
			Card 	(32 bit)
			Port 	(32 bit)
			Vpi	(32 bit)
			Vci 	(32 bit)"
	::= { atmCellCktEntry 6 }

atmCellCktStatus OBJECT-TYPE
	SYNTAX 	INTEGER {
		add(1),
		delete(2)
		}
	ACCESS 	read-write
	STATUS  mandatory
	DESCRIPTION 
		"The current status of the entry. Entries may be added by 
		specifying a value of valid, and removed by setting the status
		to invalid."
	::= { atmCellCktEntry 7 }


-- SECTION 4: Port Table  Configuration Group

-- This group contains information pertaining to ATM port
-- configuration in the system

-- The ATM Port Table

atmPortConfigTable	OBJECT-TYPE
	SYNTAX	SEQUENCE OF AtmPortConfigEntry
	ACCESS	not-accessible
	STATUS	mandatory
	DESCRIPTION
		"ATM Hardware Port Configuration Table"
	::= { atmPortConfig 1 }

atmPortConfigEntry OBJECT-TYPE
	SYNTAX	AtmPortConfigEntry
	ACCESS	not-accessible
	STATUS	mandatory
	DESCRIPTION
		"ATM port configuration table.
		 Each entry is indexed by two fields:
		 The card index and the port index."
	INDEX	{atmPortCardIndex, atmPortPortIndex }
	::= { atmPortConfigTable 1 }

AtmPortConfigEntry ::= SEQUENCE {
	atmPortCardIndex
		INTEGER,
	atmPortPortIndex
		INTEGER,
	atmPortEnable
		INTEGER,
	atmPortLoopTimingEnable
		INTEGER,
	atmPortHecCosetEnable
		INTEGER,
	atmPortHecCorrectionEnable
		INTEGER,
	atmPortHardwareFrameMode
		INTEGER,
	atmPortLocalLoopEnable
		INTEGER,
	atmPortRemoteLoopEnable
		INTEGER,
	atmPortForceHecErrorEnable
		INTEGER,
	atmPortScramblingEnable
		INTEGER,
        atmPortSigEntityType
                INTEGER,
        atmPortSigEntityRole
                INTEGER,
        atmPortSigVersion
                INTEGER,
        atmPortSigIlmi
                INTEGER,
	atmPortAdminFrameMode
		INTEGER,
	atmPortSscopStatus
		INTEGER,
        atmPortStatusEnquiryEnable
                EnableIndicator,
        atmPortTimerT309
                INTEGER,
        atmPortTrafficShapingEnable
                INTEGER
	}

atmPortCardIndex OBJECT-TYPE
	SYNTAX	INTEGER (1..16)
	ACCESS	read-write
	STATUS	mandatory
	DESCRIPTION
		"This field indicates the ATM card id."
	::= { atmPortConfigEntry 1 }

atmPortPortIndex OBJECT-TYPE
	SYNTAX	INTEGER (1..16)
	ACCESS	read-write
	STATUS	mandatory
	DESCRIPTION
		"This field indicates ATM port id."
	::= { atmPortConfigEntry 2 }

atmPortEnable OBJECT-TYPE
	SYNTAX	INTEGER {
		enable(1),
		disable(2)
		}
	ACCESS	read-write
	STATUS	mandatory
	DESCRIPTION
		"This field indicates if the ATM port is enabled or disabled.
		 2=Disable, 1=Enable.  When the port is disabled, no cell
		 traffic will be ggenerated nor accepted and not SONET signal
		 is generated.
		 Exception: this field is read-only for 5782 Goldfish
		 Module. That is, the user is not allowed to configure
		 the port on this module."
	::= { atmPortConfigEntry 3 }

atmPortLoopTimingEnable OBJECT-TYPE
	SYNTAX	INTEGER {
		enable(1),
		disable(2)
		}
	ACCESS	read-write
	STATUS	mandatory
	DESCRIPTION
		"This field indicates if loop timing is enabled or disabled.
		 2=Disable, 1=Enable.
		 Exception: this field is read-only for 5782 Goldfish
		 Module. That is, the user is not allowed to configure
		 the port on this module."
	::= { atmPortConfigEntry 4 }

atmPortHecCosetEnable OBJECT-TYPE
	SYNTAX	INTEGER {
		enable(1),
		disable(2)
		}
	ACCESS	read-write
	STATUS	mandatory
	DESCRIPTION
		"This field indicates if heccoset  is enabled or disabled.
		 2=Disable, 1=Enable.  When the port is disabled, no cell
		 traffic will be ggenerated nor accepted and not SONET signal
		 is generated.
		 Exception: this field is read-only for 5782 Goldfish
		 Module. That is, the user is not allowed to configure
		 the port on this module."
	::= { atmPortConfigEntry 5 }

atmPortHecCorrectionEnable OBJECT-TYPE
	SYNTAX	INTEGER {
		enable(1),
		disable(2)
		}
	ACCESS	read-write
	STATUS	mandatory
	DESCRIPTION
		"This field indicates if hec correction is enabled or disabled.
		 2=Disable, 1=Enable.
		 Exception: this field is read-only for 5782 Goldfish
		 Module. That is, the user is not allowed to configure
		 the port on this module."
	::= { atmPortConfigEntry 6 }

atmPortHardwareFrameMode OBJECT-TYPE
	SYNTAX	INTEGER {
		sonet(1),
		sdh(2),
		notapply(3),
		other(4)
		}
	ACCESS	read-only
	STATUS	mandatory
	DESCRIPTION
		"This field indicates the atm frame mode detected by hardware,
                 Sonet, SDH or NotApply (no cable plugged in) or 
  		 other (value other than sonet and sdh)."
	::= { atmPortConfigEntry 7 }

atmPortLocalLoopEnable OBJECT-TYPE
	SYNTAX	INTEGER {
		enable(1),
		disable(2)
		}
	ACCESS	read-write
	STATUS	mandatory
	DESCRIPTION
		"This field indicates if local loop  is enabled or disabled.
		 2=Disable, 1=Enable.
		 Exception: this field is read-only for 5782 Goldfish
		 Module. That is, the user is not allowed to configure
		 the port on this module."
	::= { atmPortConfigEntry 8 }

atmPortRemoteLoopEnable OBJECT-TYPE
	SYNTAX	INTEGER {
		enable(1),
		disable(2)
		}
	ACCESS	read-write
	STATUS	mandatory
	DESCRIPTION
		"This field indicates if loop timing is enabled or disabled.
		 2=Disable, 1=Enable.  When the port is disabled, no cell
		 traffic will be ggenerated nor accepted and not SONET signal
		 is generated.
		 Exception: this field is read-only for 5782 Goldfish
		 Module. That is, the user is not allowed to configure
		 the port on this module."
	::= { atmPortConfigEntry 9 }

atmPortForceHecErrorEnable OBJECT-TYPE
	SYNTAX	INTEGER {
		enable(1),
		disable(2)
		}
	ACCESS	read-write
	STATUS	mandatory
	DESCRIPTION
		"This field indicates if forcing cell header checksum error 
		 is enabled or disabled.
		 2=Disable, 1=Enable.
		 Exception: this field is read-only for 5782 Goldfish
		 Module. That is, the user is not allowed to configure
		 the port on this module."
	::= { atmPortConfigEntry 10 }

atmPortScramblingEnable OBJECT-TYPE
	SYNTAX	INTEGER {
		enable(1),
		disable(2)
		}
	ACCESS	read-write
	STATUS	mandatory
	DESCRIPTION
		"This field indicates if scrambing is enabled or disabled.
		 2=Disable, 1=Enable.
		 Exception: this field is read-only for 5782 Goldfish
		 Module. That is, the user is not allowed to configure
		 the port on this module."
	::= { atmPortConfigEntry 11 }

atmPortSigEntityType OBJECT-TYPE
	SYNTAX	INTEGER {
		noSig(1),            -- no signalling
		uni(2),              -- UNI
                iisp(3)              -- NNI
		}
	ACCESS	read-write
	STATUS	mandatory
	DESCRIPTION
		"This object indicates the type of the siganlling entity
                 that is associated with this ATM port.  The type of
                 a signalling instance can either be no signalling,
                 UNI which is the User-Network Interface, or Network-
                 Network Interface iisp(3).  Note that there are more
                 than one NNI supported by the ATM Forum and we support
                 only IISP.
		 Exception: this field is read-only for 5782 Goldfish
		 Module. That is, the user is not allowed to configure
		 the port on this module."
        ::= { atmPortConfigEntry 12 }

atmPortSigEntityRole OBJECT-TYPE
	SYNTAX	INTEGER {
                other(1),            -- unspecified
                user(2),             -- User side of UNI
                netw(3)              -- Network side of UNI
		}
	ACCESS	read-write
	STATUS	mandatory
	DESCRIPTION
		"This object indicates the role of the signalling entity 
                 that is associated with this ATM port.  When
                 the object atmPortSigEntity is set to a value other
                 than uni(2), this object is set to other(1).
		 Exception: this field is read-only for 5782 Goldfish
		 Module. That is, the user is not allowed to configure
		 the port on this module."
        ::= { atmPortConfigEntry 13 }

atmPortSigVersion OBJECT-TYPE
	SYNTAX	INTEGER {
                other(1),    	     -- unspecified
                auto(2),             -- learn it thru ILMI
                uni30(3),            -- UNI 3.0
                uni31(4)             -- UNI 3.1
		}
	ACCESS	read-write
	STATUS	mandatory
	DESCRIPTION
		"This object indicates the version of the siganlling entity
                 that is associated with this ATM port.  This object is
                 always set to other(1) when the object atmPortSigEntityType
                 is set to a value other than uni(2).  When the value of
                 this object is set to auto(2), the signalling entity will
                 start running with UNI 3.1 and learn the correct version
                 through ILMI.
		 Exception: this field is read-only for 5782 Goldfish
		 Module. That is, the user is not allowed to configure
		 the port on this module."
        ::= { atmPortConfigEntry 14 }

atmPortSigIlmi OBJECT-TYPE
	SYNTAX	INTEGER {
                enabled(1),          -- ILMI enabled
                disabled(2)          -- ILMI disabled
		}
	ACCESS	read-write
	STATUS	mandatory
	DESCRIPTION
		"This object is used to enable/disable ILMI.
		 Exception: this field is read-only for 5782 Goldfish
		 Module. That is, the user is not allowed to configure
		 the port on this module."
        ::= { atmPortConfigEntry 15 }

atmPortAdminFrameMode OBJECT-TYPE
	SYNTAX	INTEGER {
		sonet(1),
		sdh(2),
		invalid(3)
		}
	ACCESS  read-write
	STATUS  mandatory
	DESCRIPTION
                "When read, this object returns the configured atm
                 frame mode.  When set, only modes sonet and sdh
                 are supported."
	::= { atmPortConfigEntry 16 }

atmPortSscopStatus  OBJECT-TYPE
    SYNTAX  INTEGER {
                other(1),
                up(2),
                down(3)
                }
    ACCESS read-only
    STATUS mandatory
    DESCRIPTION
        "Indicates the operational status of the
         service specific connection-oriented protocol
         ( SSCOP ). SSCOP's  function is to correct
        transmission errors or losses by selectively
        retransmitting the missing frames.

         down -  Indicates that the peer protocol has
                 failed to respond to the max number
                 of status polls by its peer.

         up   -  Indicates the peer protocol is responding
                  to the status polls.

         other - is an undetermined state of the SSCOP
                 peer protocol."
    ::= {atmPortConfigEntry 17 }
 
atmPortStatusEnquiryEnable OBJECT-TYPE
        SYNTAX  EnableIndicator
        ACCESS  read-write
        STATUS  mandatory
        DESCRIPTION
                "This object is used to enable or disable the Status
                enquiry for this logical link. The default value for
                this object is enabled except for the UNI links.
                Note that this parameter is used only if the ATM
                signalling is enabled."
        DEFVAL { disabled }
        ::= { atmPortConfigEntry 18 }
 
atmPortTimerT309 OBJECT-TYPE
        SYNTAX  INTEGER
        ACCESS  read-write
        STATUS  mandatory
        DESCRIPTION
                " Timer value of timer T309.T309 is a SAAL disconnect timer.
                The T309 timer is started when SAAL disconnect is sent
                and it is stopped when SAAL disconnect is sent. When the
               timer is expired internal connection will be cleared and
                virtual calls will be released."
        DEFVAL { 10 }
        ::= { atmPortConfigEntry 19 }

atmPortTrafficShapingEnable OBJECT-TYPE
	SYNTAX	INTEGER {
		enable(1),
		disable(2)
		}
        ACCESS  read-write
        STATUS  mandatory
        DESCRIPTION
                " This field indicates if traffic shaping for the ATM
                port is enabled or disabled.  When traffic shaping is 
                disabled, the port operates at full wire rate. 
                When traffic shaping is enabled, the port will operate
		at the configured rate or available pacing rate."
        DEFVAL { disable }
        ::= { atmPortConfigEntry 20 }

-- SECTION 5: System Configuration Group

atmSysSigEnable OBJECT-TYPE
	SYNTAX	INTEGER {
		enable(1),
		disable(2)
		}
	ACCESS	read-write
	STATUS	mandatory
	DESCRIPTION
		"This object is used to enable or disable the ATM signalling
		task within the switch.  Note that by disabling the ATM
		signalling, the switch will not be able to support any ATM
		applications such as the LAN Emulation Client.  The default
		of this value is disable."
	::= { atmSysConfig 1 }




-- SECTION 6: Logical Link Table Configuration Group

-- This group contains information pertaining to ATM logical
-- link configuration in the system

-- The ATM Logical Link Table

atmMaxPortLogConfig OBJECT-TYPE
	SYNTAX	INTEGER (0..65535)
	ACCESS	read-only
	STATUS	mandatory
	DESCRIPTION
		"The maximum number of logical links
		 in the atmPortLogConfigTable."
	::= { atmPortLogConfig 1 }

atmCurPortLogConfig OBJECT-TYPE
	SYNTAX	INTEGER (0..65535)
	ACCESS	read-only
	STATUS	mandatory
	DESCRIPTION
		"The current number of logical links
		 in the atmPortLogConfigTable."
	::= { atmPortLogConfig 2 }


atmPortLogConfigTable	OBJECT-TYPE
	SYNTAX	SEQUENCE OF AtmPortLogConfigEntry
	ACCESS	not-accessible
	STATUS	mandatory
	DESCRIPTION
		"ATM Logical link Configuration Table."
	::= { atmPortLogConfig 3 }

atmPortLogConfigEntry OBJECT-TYPE
	SYNTAX	AtmPortLogConfigEntry
	ACCESS	not-accessible
	STATUS	mandatory
	DESCRIPTION
		"ATM logical link configuration table.
		 Each entry is indexed by three fields:
		 The card index, port index and the VPI."

	INDEX	{atmPortLogConfigCardIndex,
	         atmPortLogConfigPortIndex,
		 atmPortLogConfigVPI }
	::= { atmPortLogConfigTable 1 }

AtmPortLogConfigEntry ::= SEQUENCE {
	atmPortLogConfigCardIndex
		INTEGER,
	atmPortLogConfigPortIndex
		INTEGER,
	atmPortLogConfigVPI
		INTEGER,
	atmPortLogConfigStatus
		INTEGER,
        atmPortLogConfigSigEntityType
                INTEGER,
        atmPortLogConfigSigEntityRole
                INTEGER,
        atmPortLogConfigSigVersion
                INTEGER,
        atmPortLogConfigSigIlmi
                INTEGER,
	atmPortLogConfigAdmWeightCbr
                INTEGER,
	atmPortLogConfigAdmWeightUbr
                INTEGER,
        atmPortLogConfigStatusEnquiryEnable
                EnableIndicator,
        atmPortLogConfigTimerT309
                INTEGER
	}

atmPortLogConfigCardIndex OBJECT-TYPE
	SYNTAX	INTEGER (1..16)
	ACCESS	read-only
	STATUS	mandatory
	DESCRIPTION
		"This field indicates the ATM card id."
	::= { atmPortLogConfigEntry 1 }

atmPortLogConfigPortIndex OBJECT-TYPE
	SYNTAX	INTEGER (1..24)
	ACCESS	read-only
	STATUS	mandatory
	DESCRIPTION
		"This field indicates ATM port id."
	::= { atmPortLogConfigEntry 2 }

atmPortLogConfigVPI OBJECT-TYPE
	SYNTAX	INTEGER (0..15)
	ACCESS	read-only
	STATUS	mandatory
	DESCRIPTION
		"This field indicates ATM virtual path identifier."
	::= { atmPortLogConfigEntry 3 }

atmPortLogConfigStatus OBJECT-TYPE
	SYNTAX	INTEGER {
		other(1),
		up(2),
		add(3),
		modify(4),
		remove(5)
		}
	ACCESS	read-write
	STATUS	mandatory
	DESCRIPTION
                "This object is used to add, modify or delete a logical
                 link. A value of other(1) will be returned for read
                 operations on logical links.

		 The value add(3) is written when setting up a new link
		 and modify(4) is used for modifying an existing link.
                 The value remove(5) is used to release the link."
	::= { atmPortLogConfigEntry 4 }

atmPortLogConfigSigEntityType OBJECT-TYPE
	SYNTAX	INTEGER {
		noSig(1),            -- no signaling
		uni(2),              -- UNI
		iisp(3),             -- IISP
		pnni(4)              -- PNNI
		}
	ACCESS	read-write
	STATUS	mandatory
	DESCRIPTION
		"This object indicates the type of the signaling entity
                 associated with this ATM port. The type of a signaling
		 can either be no signaling, User-Network Interface, 
		 uni(2), Interim Interswitch Signaling Protocol, 
		 iisp(3) or Private Network-Network Interface, pnni(4)."
        ::= { atmPortLogConfigEntry 5 }

atmPortLogConfigSigEntityRole OBJECT-TYPE
	SYNTAX	INTEGER {
                other(1),            -- unspecified
                user(2),             -- User side of UNI
                netw(3)              -- Network side of UNI
		}
	ACCESS	read-write
	STATUS	mandatory
	DESCRIPTION
		"This object indicates the role of the signaling entity 
                 that is associated with this ATM logical port. This
                 object can only be set to user(2) or netw(3).
  
                 A value of other(1) is returned when neither user(2)
                 or netw(3) has been specified."
        ::= { atmPortLogConfigEntry 6 }

atmPortLogConfigSigVersion OBJECT-TYPE
	SYNTAX	INTEGER {
                other(1),    	     -- unspecified
                auto(2),             -- learn it thru ILMI
                uni30(3),            -- UNI 3.0
                uni31(4),            -- UNI 3.1
		pnni10(5)            -- PNNI 1.0
		}
	ACCESS	read-write
	STATUS	mandatory
	DESCRIPTION
		"This object indicates the version of the signaling entity
                 that is associated with this ATM port.
		  
		 When atmPortLogConfigSigEntityType is set to pnni(4), the 
		 signaling entity cannot be set to uni30(3) or uni31(4);
		 It can be set to pnni10(5) or auto(2).
		 		 
		 When this object is set to auto(2), the signaling entity will
		 start running with UNI 3.1 and learn the correct version 
		 through ILMI."
        ::= { atmPortLogConfigEntry 7 }

atmPortLogConfigSigIlmi OBJECT-TYPE
	SYNTAX	INTEGER {
                enabled(1),          -- ILMI enabled
                disabled(2)          -- ILMI disabled
		}
	ACCESS	read-write
	STATUS	mandatory
	DESCRIPTION
		"This object is used to enable or disable ILMI.
  
                 When atmPortLogConfigSigEntityType is set to uni(2) and
                 atmPortLogConfigSigVersion is set to auto(2), this
                 object must be set to enabled(1).
  
                 When atmPortLogConfigSigEntityType is set to iisp(3), this
                 object must be set to disabled(2)."
        ::= { atmPortLogConfigEntry 8 }

atmPortLogConfigAdmWeightCbr OBJECT-TYPE
	SYNTAX	INTEGER 
	ACCESS	read-write
	STATUS	mandatory
	DESCRIPTION
		"The Administrative weight of this VP for
		 the constant bit rate service category. A value
		 of zero is returned if the link is non-PNNI."
       	DEFVAL { 5040 }
        ::= { atmPortLogConfigEntry 9 }

atmPortLogConfigAdmWeightUbr OBJECT-TYPE
	SYNTAX	INTEGER 
	ACCESS	read-write
	STATUS	mandatory
	DESCRIPTION
		"The Administrative weight of this VP for
		 the unspecified bit rate service category.
		 A value of zero is returned if the link is
		 non-PNNI."
       	DEFVAL { 5040 }
        ::= { atmPortLogConfigEntry 10 }

atmPortLogConfigStatusEnquiryEnable OBJECT-TYPE
        SYNTAX  EnableIndicator
        ACCESS  read-write
        STATUS  mandatory
        DESCRIPTION
                "This object is used to enable or disable the Status
                enquiry. Note that this parametwer is used only
                if the ATM signalling is enabled."
        DEFVAL { disabled }
        ::= { atmPortLogConfigEntry 11 }
 
atmPortLogConfigTimerT309 OBJECT-TYPE
        SYNTAX  INTEGER
        ACCESS  read-write
        STATUS  mandatory
        DESCRIPTION
                " Timer value of timer T309.T309 is a SAAL disconnect timer.
                The T309 timer is started when SAAL disconnect is sent
                and it is stopped when SAAL disconnect is sent. When the
               timer is expired internal connection will be cleared and
                virtual calls will be released."
        DEFVAL { 10 }
        ::= { atmPortLogConfigEntry 12 }

END

-- SECTION 1: Top Level Definitions


CENTILLION-ATMMON-MIB DEFINITIONS ::= BEGIN


-- Centillion ATM Monitoring MIB Release 2.0.3
-- Revision 11/30/98

-- Copyright 1995-96 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	OBJECT-TYPE
		FROM RFC-1212
	ifIndex
	    	FROM RFC1213-MIB
	Counter, IpAddress	
		FROM RFC1155-SMI
	MacAddress, atmMonitor, CardId, PortId
		FROM CENTILLION-ROOT-MIB;


-- Groups

atmPortMonitor		OBJECT IDENTIFIER ::=	{ atmMonitor 1 }
atmElanMonitor		OBJECT IDENTIFIER ::=	{ atmMonitor 2 }
atmPvcStatusMonitor	OBJECT IDENTIFIER ::=	{ atmMonitor 3 }
atmSigMonitor        	OBJECT IDENTIFIER ::=	{ atmMonitor 4 }
atmCardMonitor          OBJECT IDENTIFIER ::=   { atmMonitor 5 }
atmStatusEnqMonitor     OBJECT IDENTIFIER ::=   { atmMonitor 6 }

-- SECTION 2: Port Statistics 

-- This group contains information pertaining to ATM port statistics

-- The ATM Port Statistics

atmPortStatTable OBJECT-TYPE
	SYNTAX	SEQUENCE OF AtmPortStatEntry
	ACCESS	not-accessible
	STATUS	mandatory
	DESCRIPTION
		"ATM Port Statistics"
	::= { atmPortMonitor 1 }

atmPortStatEntry OBJECT-TYPE
	SYNTAX	AtmPortStatEntry
	ACCESS	not-accessible
	STATUS	mandatory
	DESCRIPTION
		"ATM Port Statistics.
		 Each entry is indexed by two fields:
		 The card number and the port number."
	INDEX	{ atmStatCardId, atmStatPortId }
	::= { atmPortStatTable 1 }

AtmPortStatEntry ::= SEQUENCE {
	atmStatCardId
		CardId,
	atmStatPortId
		PortId,
	atmSigDetected
		INTEGER,
	atmRxBadHecCell
		Counter,
	atmRxDmaDropCell
		Counter,
	atmRxGoodCell
		Counter,
	atmTxDmaDropCell
		Counter,
	atmTxGoodCell
		Counter,
	atmSuniFifoOverrun
		Counter
	}

atmStatCardId OBJECT-TYPE
	SYNTAX	CardId
	ACCESS	read-only
	STATUS	mandatory
	DESCRIPTION 
		"This field is the card index "
	::= {atmPortStatEntry 1 }

atmStatPortId OBJECT-TYPE
	SYNTAX	PortId
	ACCESS	read-only
	STATUS	mandatory
	DESCRIPTION 
		"This field is the port index "
	::= {atmPortStatEntry 2 }

atmSigDetected OBJECT-TYPE
	SYNTAX	INTEGER {
		signalpresent(1),
		nosignal(2)
		}
	ACCESS	read-only
	STATUS	mandatory
	DESCRIPTION
		"This bit field indicates if the port receives
		 signal from the remote ATM port.
		 1= signal present, 2= no signal."
	::= { atmPortStatEntry 3 }

atmRxBadHecCell OBJECT-TYPE
	SYNTAX	Counter	
	ACCESS	read-only
	STATUS	mandatory
	DESCRIPTION
		"The number of cells received that has a bad ATM
		 cell header (HEC).  The error is usually due to 
		 a physical layer problem.  For example, when the
		 fiber is first connected to the system or a clock
		 mismatch."
	::= { atmPortStatEntry 4 }

atmRxDmaDropCell OBJECT-TYPE
	SYNTAX	Counter	
	ACCESS	read-only
	STATUS	mandatory
	DESCRIPTION
		"The number of cells received but is discarded by
		 the ATM header validation checking.  The error
		 is usually due to a incorrectly configured VPI/VCI
		 or other configuration error."
	::= { atmPortStatEntry 5 }

atmRxGoodCell OBJECT-TYPE
	SYNTAX	Counter	
	ACCESS	read-only
	STATUS	mandatory
	DESCRIPTION
		"The number of cells received that is valid."
	::= { atmPortStatEntry 6 }

atmTxDmaDropCell OBJECT-TYPE
	SYNTAX	Counter	
	ACCESS	read-only
	STATUS	mandatory
	DESCRIPTION
		"The number of outgoing cells dropped due to 
		 congestions."
	::= { atmPortStatEntry 7 }

atmTxGoodCell OBJECT-TYPE
	SYNTAX	Counter	
	ACCESS	read-only
	STATUS	mandatory
	DESCRIPTION
		"The number of cells transmitted."
	::= { atmPortStatEntry 8 }

atmSuniFifoOverrun OBJECT-TYPE
	SYNTAX	Counter	
	ACCESS	read-only
	STATUS	mandatory
	DESCRIPTION
                "The number of times that the SUNI FIFO overrun status bit has been read
                 in the true state."
	::= { atmPortStatEntry 9 }


-- SECTION 3: Elan Statistics 

-- This group contains information pertaining to ATM InterSwitch PVC

-- The ATM Elan PVC Statistics

atmElanPvcStatisticTable OBJECT-TYPE
	SYNTAX	SEQUENCE OF AtmElanPvcStatisticEntry
	ACCESS	not-accessible
	STATUS	mandatory
	DESCRIPTION
		"Tmp ATM Elan PVC statistics"
	::= { atmElanMonitor 1 }

atmElanPvcStatisticEntry OBJECT-TYPE
	SYNTAX	AtmElanPvcStatisticEntry
	ACCESS	not-accessible
	STATUS	mandatory
	DESCRIPTION
		"ATM Elan PVC statistics.
		 The Elan ID is used as
		 the index of the object."
	INDEX	{ atmElanId }
	::= { atmElanPvcStatisticTable 1 }

AtmElanPvcStatisticEntry ::= SEQUENCE {
	atmElanId
		INTEGER,
	atmElanPvcInUcastPkt
		INTEGER,
	atmElanPvcInMcastPkt
		INTEGER,
	atmElanPvcOutUcastPkt
		INTEGER,
	atmElanPvcOutMcastPkt
		INTEGER
	}

atmElanId OBJECT-TYPE
	SYNTAX	INTEGER (1..32)
	ACCESS	read-only
	STATUS	mandatory
	DESCRIPTION
		"The Elan index."
	::= { atmElanPvcStatisticEntry 1 }

atmElanPvcInUcastPkt OBJECT-TYPE
	SYNTAX	INTEGER
	ACCESS	read-only
	STATUS	mandatory
	DESCRIPTION
		"The number of unicast packet that is received from
		 this Elan PVC."
	::= { atmElanPvcStatisticEntry 2 }

atmElanPvcInMcastPkt OBJECT-TYPE
	SYNTAX	INTEGER
	ACCESS	read-only
	STATUS	mandatory
	DESCRIPTION
		"The number of multicast packet that is received from
		 this Elan PVC."
	::= { atmElanPvcStatisticEntry 3 }

atmElanPvcOutUcastPkt OBJECT-TYPE
	SYNTAX	INTEGER
	ACCESS	read-only
	STATUS	mandatory
	DESCRIPTION
		"The number of unicast packet that is transmitted from
		 this Elan PVC."
	::= { atmElanPvcStatisticEntry 4 }

atmElanPvcOutMcastPkt OBJECT-TYPE
	SYNTAX	INTEGER
	ACCESS	read-only
	STATUS	mandatory
	DESCRIPTION
		"The number of unicast packet that is transmitted from
		 this Elan PVC."
	::= { atmElanPvcStatisticEntry 5 }


-- SECTION 4: ATM PVC Status 

atmPvcStatusTable OBJECT-TYPE
	SYNTAX	SEQUENCE OF AtmPvcStatusEntry
	ACCESS	not-accessible
	STATUS	mandatory
	DESCRIPTION
		"Tmp ATM InterSwitch PVC status"
	::= { atmPvcStatusMonitor 1 }

atmPvcStatusEntry OBJECT-TYPE
	SYNTAX	AtmPvcStatusEntry
	ACCESS	not-accessible
	STATUS	mandatory
	DESCRIPTION
		"ATM PVC status.
		 The PVC circuit ID is used as
		 the index of the object."
	INDEX	{ atmPvcCktId }
	::= { atmPvcStatusTable 1 }

AtmPvcStatusEntry ::= SEQUENCE {
	atmPvcCktId
		INTEGER,
	atmPvcElanId
		INTEGER,
	atmPvcRemoteSwitchInfoValid
		INTEGER,
	atmPvcRemoteSwitchMacAddress
		MacAddress,
	atmPvcRemoteSwitchPvcStatus
		INTEGER,
	atmPvcSTPState
		INTEGER,
	atmPvcRemoteElanId
		INTEGER,
	atmPvcRemoteMcpIpAddress
		IpAddress
	}

atmPvcCktId OBJECT-TYPE
	SYNTAX	INTEGER (1..256)
	ACCESS	read-only
	STATUS	mandatory
	DESCRIPTION
		"This field is the index of the circuit."
	::= { atmPvcStatusEntry 1 }

atmPvcElanId OBJECT-TYPE
	SYNTAX	INTEGER (1..32)
	ACCESS	read-only
	STATUS	mandatory
	DESCRIPTION
		"This field is the index of the elan this circuit belongs to."
	::= { atmPvcStatusEntry 2 }

atmPvcRemoteSwitchInfoValid OBJECT-TYPE
	SYNTAX	INTEGER {
		valid(1),
		invalid(2)
		}
	ACCESS	read-only
	STATUS	mandatory
	DESCRIPTION
		"This field is based on the aging timer of a remote
		 switch.  If the local switch has not received any
		 packets from the remote switch for a period of time,
		 then it is declared as non-valid.
			1 = non-valid
			2 = valid (normal state of operation)."
	::= { atmPvcStatusEntry 3 }

atmPvcRemoteSwitchMacAddress OBJECT-TYPE
	SYNTAX	MacAddress
	ACCESS	read-only
	STATUS	mandatory
	DESCRIPTION
		"This field lists the remote switch's MAC address.
		 If the atmInterSwitchPvcRemoteSwitchInfoValid object
		 is 1, then this field contains the valid info.
		 Otherwise, this field contains the last learned info."
	::= { atmPvcStatusEntry 4 }

atmPvcRemoteSwitchPvcStatus OBJECT-TYPE
	SYNTAX	INTEGER {
		up(1),
		down(2)
		}
	ACCESS	read-only
	STATUS	mandatory
	DESCRIPTION
		"This field is set if the remote switch receives packets from
		 this switch.  If atmInterSwitchPvcRemoteSwitchInfoValid
		 objeect is 1, then this field contains the valid info.
		 Otherwise, this field contains the last learned info."
	::= { atmPvcStatusEntry 5 }

atmPvcSTPState OBJECT-TYPE
	SYNTAX	INTEGER {
		disabled(1),
		blocking(2),
		listening(3),
		learning(4),
		forwarding(5)
		}
	ACCESS	read-only
	STATUS	mandatory
	DESCRIPTION
		"This field indicates the STP port state of the circuit."
	::= { atmPvcStatusEntry 6 }

atmPvcRemoteElanId OBJECT-TYPE
	SYNTAX	INTEGER
	ACCESS	read-only
	STATUS	mandatory
	DESCRIPTION
		"This field indicates the elan ID of the circuit."
	::= { atmPvcStatusEntry 7 }

atmPvcRemoteMcpIpAddress OBJECT-TYPE
	SYNTAX	IpAddress
	ACCESS	read-only
	STATUS  mandatory
	DESCRIPTION
		"This is the remote mcp ip address."
	::= { atmPvcStatusEntry 8 }


-- SECTION 5: Signal statistics

-- This group contains information pertaining to ATM signal statistics.

cnCurPtptConns OBJECT-TYPE
      	SYNTAX  INTEGER       
      	ACCESS  read-only
      	STATUS  mandatory
      	DESCRIPTION
              "This counter counts the number of current point-to-point
               calls of the switch." 
      	::= { atmSigMonitor 1 }
 
cnCurPtmptConns OBJECT-TYPE
      	SYNTAX  INTEGER 
      	ACCESS  read-only
      	STATUS  mandatory
      	DESCRIPTION
              "This counter counts the number of current
               point-to-multipoint calls of the switch."
      	::= { atmSigMonitor 2 }

cnCurActiveConns OBJECT-TYPE
      	SYNTAX  INTEGER 
      	ACCESS  read-only
      	STATUS  mandatory
      	DESCRIPTION
              "This counter counts the number of current
               active calls of the switch."
      	::= { atmSigMonitor 3 }

cnCurPortConnsTable OBJECT-TYPE
      	SYNTAX SEQUENCE OF CnCurPortConnsEntry
      	ACCESS  not-accessible
      	STATUS  mandatory
      	DESCRIPTION
              "This table contains the point-to-point,
               point-to-multipoint and active calls per port
               for all the atm ports in the switch."
      	::= { atmSigMonitor 4 }

cnCurPortConnsEntry OBJECT-TYPE
      	SYNTAX CnCurPortConnsEntry
      	ACCESS  not-accessible
      	STATUS  mandatory
      	DESCRIPTION
              "This entry contains the point-to-point,
               point-to-multipoint and active calls per port."
      	INDEX { ifIndex }
      	::= { cnCurPortConnsTable 1 }

CnCurPortConnsEntry ::=
      	SEQUENCE {
      	cnCurPortConnsPtptConns INTEGER,
      	cnCurPortConnsPtmptConns        INTEGER,
      	cnCurPortConnsActiveConns     	INTEGER 
      	}

cnCurPortConnsPtptConns OBJECT-TYPE
      	SYNTAX INTEGER
      	ACCESS  read-only
      	STATUS  mandatory
      	DESCRIPTION
              "This entry counts the number of current point-to-point
               calls per port."
      	::= { cnCurPortConnsEntry 1 }

cnCurPortConnsPtmptConns OBJECT-TYPE
      	SYNTAX INTEGER
      	ACCESS  read-only
      	STATUS  mandatory
      	DESCRIPTION
              "This entry counts the number of current point-to-multipoint
               calls per port."
      	::= { cnCurPortConnsEntry 2 }

cnCurPortConnsActiveConns OBJECT-TYPE
      	SYNTAX INTEGER
      	ACCESS  read-only
      	STATUS  mandatory
      	DESCRIPTION
              "This entry counts the number of current active
               calls per port."
      	::= { cnCurPortConnsEntry 3 }


-- SECTION 6: Card Operational
 
-- This group contains information pertaining to ATM card operational
 
-- The ATM Card Operational

atmCardOperTable OBJECT-TYPE
        SYNTAX  SEQUENCE OF AtmCardOperEntry
        ACCESS  not-accessible
        STATUS  mandatory
        DESCRIPTION
                "ATM Card Operational values"
        ::= { atmCardMonitor 1 }
 
atmCardOperEntry OBJECT-TYPE
        SYNTAX  AtmCardOperEntry
        ACCESS  not-accessible
        STATUS  mandatory
        DESCRIPTION
                "ATM Card Operational values.
                 Each entry is indexed by card number"
        INDEX   { atmCardOperCardId }
        ::= { atmCardOperTable 1 }

AtmCardOperEntry ::= SEQUENCE {
        atmCardOperCardId
                CardId,
        atmCardOperExtClockSource
                INTEGER
        }

atmCardOperCardId OBJECT-TYPE
        SYNTAX  CardId
        ACCESS  read-only
        STATUS  mandatory
        DESCRIPTION
                "This field is the card index "
        ::= {atmCardOperEntry 1 }

atmCardOperExtClockSource OBJECT-TYPE
        SYNTAX  INTEGER
        ACCESS  read-only
        STATUS  mandatory
        DESCRIPTION
                 "This field indicates the operational external
                 clock source.  The following value is read-only:
                 0 = Local Oscillator, 1..N = ATM port id for
                 external clock source.  This object only applies
                 to ATM MDA modules with SM, MM, or UTP media types."
        ::= { atmCardOperEntry 2 }

-- SECTION 7: Status Enquiry Statistics
 
-- This group contains information pertaining to ATM status enquiry statistics.
 
cnStsEnqPTPCalls OBJECT-TYPE
        SYNTAX  INTEGER
        ACCESS  read-only
        STATUS  mandatory
        DESCRIPTION
              "The number of current point-to-point calls 
	      in the status enquiry queue of the switch."
        ::= { atmStatusEnqMonitor 1 }
 
cnStsEnqActiveParties OBJECT-TYPE
        SYNTAX  INTEGER
        ACCESS  read-only
        STATUS  mandatory
        DESCRIPTION
              "The number of current active parties in 
	      the status enquiry queue of the switch. 
	      (This includes point- to-multi-point calls)."
        ::= { atmStatusEnqMonitor 2 }
 
cnStsEnqSent OBJECT-TYPE
        SYNTAX  INTEGER
        ACCESS  read-only
        STATUS  mandatory
        DESCRIPTION
              "The total number of status enquiry requests sent."
        ::= { atmStatusEnqMonitor 3 }

cnStsEnqCfmsRecvd OBJECT-TYPE
        SYNTAX  INTEGER
        ACCESS  read-only
        STATUS  mandatory
        DESCRIPTION
              "The number of current status messages 
	      (in response to status enquiry) received."
        ::= { atmStatusEnqMonitor 4 }
 
cnStsEnqRetried OBJECT-TYPE
        SYNTAX  INTEGER
        ACCESS  read-only
        STATUS  mandatory
        DESCRIPTION
              "The total number of status enquiry commands retried."
        ::= { atmStatusEnqMonitor 5 }
 
cnStsEnqTimeOuts OBJECT-TYPE
        SYNTAX  INTEGER
        ACCESS  read-only
        STATUS  mandatory
        DESCRIPTION
              "The total number of status enquiry commands 
	      timed out i.e The number of calls for which 
	      status (in response to status enquiry) was 
	      not received."
        ::= { atmStatusEnqMonitor 6 }
 
cnStsEnqQueueSize OBJECT-TYPE
        SYNTAX  INTEGER
        ACCESS  read-only
        STATUS  mandatory
        DESCRIPTION
              "The size of the status enquiry queue."
        ::= { atmStatusEnqMonitor 7 }
 
cnStsEnqCallsCleared OBJECT-TYPE
        SYNTAX  INTEGER
        ACCESS  read-only
        STATUS  mandatory
        DESCRIPTION
              "The number of calls cleared by status enquiry. "
        ::= { atmStatusEnqMonitor 8 }
END
-- SECTION 1: Top Level Definitions

REDUND-TRAP-MIB DEFINITIONS ::= BEGIN


-- Copyright 1997 Bay Networks, Inc.
-- All rights reserved.
-- This Bay Networks SNMP Management Information Base Specification 
-- (Specification) embodies Bay Networks' confidential and
-- proprietary intellectual property. Bay Networks retains all
-- title and ownership in the Specification, including any
-- revisions. 
 
-- This Specification is supplied "AS IS," and Bay Networks makes
-- no warranty, either express or implied, as to the use,
-- operation, condition, or performance of the Specification.    


-- Imports  

IMPORTS     
	TRAP-TYPE  	 FROM RFC-1215     
	sysMcpRedundIndx, sysMcpRedundOperState
			 FROM CENTILLION-CONFIG-MIB          
	sysMcpRedundTrap FROM CENTILLION-ROOT-MIB;

-- SECTION 2: Redundant traps definitions    

sysMcpRedundDown  TRAP-TYPE
    ENTERPRISE  	sysMcpRedundTrap
    VARIABLES   	{ sysMcpRedundIndx, 
			  sysMcpRedundOperState }
--  STATUS      mandatory
    DESCRIPTION 
	"When two MCP's are participating in redundancy,
	 they are aware of each other through a
	 mechanism based on heart beat protocol.  
                   
         When primary MCP detects the failure of the
         secondary, it will send the trap immediately.
  
  	 When the secondary MCP detects the primary has
	 failed, it will take control, reset the switch
	 and then send the trap.

 	 Varbind information returned with this trap:
         1. sysMcpRedundIndx  represents the slot where
            active MCP resides.
         2. sysMcpRedundOperState represents the state of
            the failed MCP."

 ::= 1 -- 0x01
 
END

-- SECTION 1: Top Level Definitions
 
ATM-TRAP-MIB DEFINITIONS ::= BEGIN

-- Centillion Atm Trap MIB Release 1.0.1
-- Revision 01/12/2000
-- rcr     04/03/01 CR147311  - add SscopUp trap
 
-- Copyright 1998 Bay Networks, Inc.
-- All rights reserved.
-- This Bay Networks SNMP Management Information Base Specification
-- (Specification) embodies Bay Networks' confidential and
-- proprietary intellectual property. Bay Networks retains all
-- title and ownership in the Specification, including any
-- revisions.
 
-- This Specification is supplied "AS IS," and Bay Networks makes
-- no warranty, either express or implied, as to the use,
-- operation, condition, or performance of the Specification.
 
 
-- Imports
  
IMPORTS
      TRAP-TYPE   FROM RFC-1215
      atmTraps    FROM S5-ROOT-MIB
      atmPortCardIndex,atmPortPortIndex,atmPortSscopStatus
	          FROM CENTILLION-ATMCFG-MIB;
      
  
  
-- SECTION 2: ATM traps definitions
  
  
s5CtrSscopDown  TRAP-TYPE
     ENTERPRISE  atmTraps
     VARIABLES   {atmPortCardIndex,
                  atmPortPortIndex,
                  atmPortSscopStatus }
--   STATUS      mandatory
     DESCRIPTION
         " This trap is sent when the SSCOP goes down
           i.e., when the peer protocol has failed to
           respond to the max number of status polls
           by its peer.
             atmPortCardIndex.........the ATM card id.
             atmPortPortIndex.........the ATM port id.
             atmPortSscopStatus ..........the status of the
           SSCOP protocol."
     ::= 1

s5CtrAdmaLockup  TRAP-TYPE
     ENTERPRISE  atmTraps
     VARIABLES   {atmPortCardIndex,
                  atmPortPortIndex}
--   STATUS      mandatory
     DESCRIPTION
         " This trap is sent when a ADMA lockup condition
           is detected on the MCP.  The MCP must be reset
           to clear this condition.
             atmPortCardIndex.........the ATM card id.
             atmPortPortIndex.........the ATM port id."
     ::= 2

s5CtrAcmaLockup  TRAP-TYPE
     ENTERPRISE  atmTraps
     VARIABLES   {atmPortCardIndex}
--   STATUS      mandatory
     DESCRIPTION
         " This trap is sent when a ACMA queue stuck
           condition is detected on the MCP.  The 
           MCP must be reset to clear this condition.
             atmPortCardIndex.........the ATM card id."
     ::= 3

s5CtrSscopUp  TRAP-TYPE
     ENTERPRISE  atmTraps
     VARIABLES   {atmPortCardIndex,
                  atmPortPortIndex,
                  atmPortSscopStatus }
--   STATUS      mandatory
     DESCRIPTION
         " This trap is sent when the SSCOP uomes up.
             atmPortCardIndex.........the ATM card id.
             atmPortPortIndex.........the ATM port id.
             atmPortSscopStatus ..........the status of the
           SSCOP protocol."
     ::= 4

END

ATM-SOFT-PVC-TRAP-MIB DEFINITIONS ::= BEGIN


-- Copyright 1998 Bay Networks, Inc.
-- All rights reserved.
-- This Bay Networks SNMP Management Information Base Specification 
-- (Specification) embodies Bay Networks' confidential and
-- proprietary intellectual property. Bay Networks retains all
-- title and ownership in the Specification, including any
-- revisions. 
 
-- This Specification is supplied "AS IS," and Bay Networks makes
-- no warranty, either express or implied, as to the use,
-- operation, condition, or performance of the Specification.    


IMPORTS
	TRAP-TYPE				FROM RFC-1215
	atmSoftPvcTrapsPrefix,  
	atmSoftPvcCallFailures, 			
	atmSoftPvcCurrentlyFailingSoftPVccs,
	atmSoftPvcCurrentlyFailingSoftPVpcs	FROM ATM-SOFT-PVC-MIB;

atmSoftPvcCallFailuresTrap	TRAP-TYPE
	ENTERPRISE	atmSoftPvcTrapsPrefix
	VARIABLES	{ atmSoftPvcCallFailures, atmSoftPvcCurrentlyFailingSoftPVccs,
	atmSoftPvcCurrentlyFailingSoftPVpcs}
--	STATUS	mandatory
	DESCRIPTION
		"A notification indicating that one or more series of
		call attempts in trying to establish a Soft PVPC or
		Soft PVCC have failed since the last
		atmSoftPvcCallFailureTrap was sent. If this trap has
		not been sent for the last atmSoftPvcNotificationInterval,
		then it will be sent on the next increment of
		atmSoftPvcCallFailures."
	::= 1
END
-- SECTION 1: Top Level Definitions

PVC-TRAP-MIB DEFINITIONS ::= BEGIN


-- Copyright 1999 Nortel Networks, Inc.
-- All rights reserved.
-- This Nortel Networks SNMP Management Information Base Specification
-- (Specification) embodies Nortel Networks' confidential and
-- proprietary intellectual property. Nortel Networks retains all
-- title and ownership in the Specification, including any
-- revisions.

-- This Specification is supplied "AS IS," and Nortel Networks makes
-- no warranty, either express or implied, as to the use,
-- operation, condition, or performance of the Specification.


-- Imports

IMPORTS
    TRAP-TYPE    FROM RFC-1215
    cnPvcTraps   FROM CENTILLION-ROOT-MIB
    atmPortCardIndex, atmPortPortIndex
                 FROM CENTILLION-ATMCFG-MIB
    atmPvcCktId  FROM CENTILLION-ATMMON-MIB;

-- SECTION 2: PVC traps definitions

remotePvcDown  TRAP-TYPE
    ENTERPRISE      cnPvcTraps
    VARIABLES       { atmPortCardIndex,
                      atmPortPortIndex,
                      atmPvcCktId
                      }
--  STATUS      mandatory
    DESCRIPTION
        " This trap is sent when a CLC PVC goes down
          i.e. the RemotePvcStatus indicator is set to
          down.
            atmPortCardIndex.........the ATM card id.
            atmPortPortIndex.........the ATM port id.
            atmPvcCktId..............the PVC ckt id."
 ::= 1

END


-- SECTION 1: Top Level Definitions
 
STP-TOPOLOGY-CHANGE-TRAP-MIB DEFINITIONS ::= BEGIN

-- Centillion STP notification trap MIB release 1.0.0
-- Revision 04/13/2000  
 
-- Copyright 2000 Nortel Networks, Inc.
-- All rights reserved.
-- This Nortel Networks SNMP Management Information Base Specification
-- (Specification) embodies Nortel Networks' confidential and
-- proprietary intellectual property. Nortel Networks retains all
-- title and ownership in the Specification, including any
-- revisions.
 
-- This Specification is supplied "AS IS," and Nortel Networks makes
-- no warranty, either express or implied, as to the use,
-- operation, condition, or performance of the Specification.
 
 
-- Imports
  
IMPORTS
      TRAP-TYPE       FROM RFC-1215
      stpChangeTrap   FROM S5-ROOT-MIB
      bridgeGroupIdentifier  FROM CENTILLION-BRIDGEGROUP-MIB;
  
  
-- SECTION 2: Topology Change traps definitions
  
  
stpRxTopologyChg   TRAP-TYPE
     ENTERPRISE  stpChangeTrap
     VARIABLES   { bridgeGroupIdentifier }
--   STATUS      mandatory
     DESCRIPTION
         " This trap is sent when a spanning tree group receives a 
           topology change notification."

     ::= 1 

END

-- SECTION 1: Top Level Definitions

CENTILLION-MCAST-MIB DEFINITIONS ::= BEGIN

-- Centillion VLAN MIB Release 2.0.1
-- Revision 05/05/98 
 
-- Copyright 1998 Bay Networks, Inc.
-- All rights reserved.
-- This Bay Networks SNMP Management Information Base Specification
-- (Specification) embodies Bay Networks' confidential and
-- proprietary intellectual property. Bay Networks retains all
-- title and ownership in the Specification, including any
-- revisions.
 
-- This Specification is supplied "AS IS," and Bay Networks makes
-- no warranty, either express or implied, as to the use,
-- operation, condition, or performance of the Specification.
 
 
-- Imports

IMPORTS
        OBJECT-TYPE FROM RFC-1212
        IpAddress FROM RFC1155-SMI
        Boolean, EnableIndicator, StatusIndicator, 
	PortId, CardId, sysConfig FROM CENTILLION-ROOT-MIB;

-- Textual Conventions
 
--
-- C100/BH switches support Virtual LAN,
-- which are identified by a unique VLAN identifier
-- as specified by this textual convention.
-- This VLAN identifier corresponds to the lower 12
-- bits in the IEEE VLAN field:

VlanId ::= INTEGER (1..4095)

-- Groups

vlan OBJECT IDENTIFIER ::= { sysConfig 31 }


-- SECTION 2:  VLAN Multicast configuration/information table

vlanMcastProtocolGroup OBJECT IDENTIFIER ::= { vlan 1 }

-- SECTION 3: VLAN IGMP Protocol Group

vlanIGMPProtocolGroup  OBJECT IDENTIFIER ::= { vlanMcastProtocolGroup 1 }

-- SECTION 4: VLAN igmp configuration table

vlanIGMPConfig OBJECT IDENTIFIER ::= { vlanIGMPProtocolGroup 1 }

-- SECTION 5:  IGMP configuration table 

igmpGeneralConfigTable OBJECT-TYPE
        SYNTAX  SEQUENCE OF IgmpGeneralConfigEntry
        ACCESS  not-accessible
        STATUS  mandatory
        DESCRIPTION
              "IP IGMP general configuration table which includes
               pseudo query, IRAP query configuration, and maximum 
               number of groups supported in this VLAN."
        ::= { vlanIGMPConfig 1 }
 
igmpGeneralConfigEntry OBJECT-TYPE
        SYNTAX  IgmpGeneralConfigEntry
        ACCESS  not-accessible
        STATUS  mandatory
        DESCRIPTION
              "IP IGMP general configuration entry.
               Each entry is indexed by a vlan id.
               An example to create the entry is:
               set igmpGeneralConfigIgmpSupport.3=I2 and
                   igmpGeneralConfigMaxGroup.3=I20  to
                   a switch ip address. 
               (where 3 is vlan Id; 2 is enabled; 20 is maximum  
                multicast groups to be supported for this vlan. "
        INDEX { igmpGeneralConfigVlanId }
        ::= { igmpGeneralConfigTable 1 }
 
 
IgmpGeneralConfigEntry ::= SEQUENCE {
        igmpGeneralConfigVlanId
             VlanId,
        igmpGeneralConfigPseudoQuery
             EnableIndicator,
	igmpGeneralConfigIrapQuery
	     EnableIndicator,	
        igmpGeneralConfigIgmpSupport
             EnableIndicator,
        igmpGeneralConfigMaxGroup
             INTEGER
        }

igmpGeneralConfigVlanId OBJECT-TYPE
        SYNTAX  VlanId
        ACCESS  read-only 
        STATUS  mandatory
        DESCRIPTION
             "The unique VLAN identifier of this IGMP configuration
              entry. "
        ::= { igmpGeneralConfigEntry 1 }
 
igmpGeneralConfigPseudoQuery  OBJECT-TYPE
        SYNTAX  EnableIndicator
        ACCESS  read-write
        STATUS  mandatory
        DESCRIPTION
             "In the absence of a true IGMP router, the switch may be
              configured to issue general queries. This provides the 
	      capability for multicast pruning with an isoloated subnet.
              The mode defaults to disabled in a VLAN configured for
              IGMP support"
        ::= { igmpGeneralConfigEntry 2 }

igmpGeneralConfigIrapQuery  OBJECT-TYPE
        SYNTAX  EnableIndicator
        ACCESS  read-write
        STATUS  mandatory
        DESCRIPTION
	     "Control whether IGMP Router Advertisement Protocol 
              messages will be used to determine the existence of 
              a router in a remote switch. Default is 'enabled'."
        ::= { igmpGeneralConfigEntry 3 }

igmpGeneralConfigIgmpSupport OBJECT-TYPE
        SYNTAX  EnableIndicator
        ACCESS  read-write
        STATUS  mandatory
        DESCRIPTION
             " When 'enabled' is specified, it indicates that the IGMP
               is supported  in this VLAN."

                
        ::= { igmpGeneralConfigEntry 4 }
 
igmpGeneralConfigMaxGroup  OBJECT-TYPE
        SYNTAX  INTEGER
        ACCESS  read-write
        STATUS  mandatory
        DESCRIPTION
             " The maximum number of multicast groups supported in 
	       this VLAN.  If the VLAN supports only manually 
	       configured multicast groups, then the value of this
               field equals the length of the IGMP multicast group
               if the multicast group is an inclusive set.
               A value of 0 indicates that IGMP multicasting is not
	       supported in this VLAN"
        ::= { igmpGeneralConfigEntry 5 }
 

igmpTimerConfigTable OBJECT-TYPE
	SYNTAX  SEQUENCE OF IgmpTimerConfigEntry
	ACCESS  not-accessible
	STATUS  mandatory
	DESCRIPTION
	      "IP IGMP Multicast timer configuration table"
	::= { vlanIGMPConfig 2 } 	 

igmpTimerConfigEntry OBJECT-TYPE
	SYNTAX  IgmpTimerConfigEntry
	ACCESS  not-accessible
	STATUS  mandatory
        DESCRIPTION
              "IP IGMP Multicast timer configuration entry.  
               Each entry is indexed by a vlan id. This entry will
               be created when the corresponding igmpGeneralConfigEntry
               is created. All the values of the mibs in this entry 
               will be set to default  at the time of creation. "
	INDEX { igmpTimerConfigVlanId }
        ::= { igmpTimerConfigTable 1 } 


IgmpTimerConfigEntry ::= SEQUENCE {
	igmpTimerConfigVlanId
	     VlanId,
	igmpTimerConfigTimerRobustness
	     INTEGER,
	igmpTimerConfigQueryInterval
	     INTEGER,
	igmpTimerConfigQueryResponse
	     INTEGER
        }

igmpTimerConfigVlanId OBJECT-TYPE
	SYNTAX  VlanId
	ACCESS  read-only 
	STATUS  mandatory
	DESCRIPTION
             "The unique VLAN identifier of this multicast timer 
              configuration entry."
	::= { igmpTimerConfigEntry 1 }


igmpTimerConfigTimerRobustness OBJECT-TYPE
        SYNTAX  INTEGER 
        ACCESS  read-write
        STATUS  mandatory
        DESCRIPTION
             "The robustness variable for the multicast group. 
              A value of zero indicates the default value should
              be taken. If the value specified is non-zero, it should
              be equal or greater than 2"
        DEFVAL { 2 }
        ::= { igmpTimerConfigEntry 2 }

igmpTimerConfigQueryInterval OBJECT-TYPE
        SYNTAX  INTEGER 
        ACCESS  read-write
        STATUS  mandatory
        DESCRIPTION
             "The query interval configured for the multicast group.
              A value of zero indicates the default value should be 
              used. The value should be less than 0xffff"
        DEFVAL { 125 }
        ::= { igmpTimerConfigEntry 3 }

igmpTimerConfigQueryResponse OBJECT-TYPE
        SYNTAX  INTEGER 
        ACCESS  read-write
        STATUS  mandatory
        DESCRIPTION
             "The response interval configured for the multicast group. 
              A value of zero indicates the default value should be used. 
	      The value should be less than 0xffff. "
        DEFVAL { 100 }
        ::= { igmpTimerConfigEntry 4 }


--
--  The multicast group address table
--

igmpGroupTable OBJECT-TYPE
        SYNTAX  SEQUENCE OF IgmpGroupEntry
        ACCESS  not-accessible
        STATUS  mandatory
        DESCRIPTION
              "IP IGMP Multicast group address configuration table. "
        ::= { vlanIGMPConfig 3 }
 
igmpGroupEntry OBJECT-TYPE
        SYNTAX  IgmpGroupEntry
        ACCESS  not-accessible
        STATUS  mandatory
        DESCRIPTION
              "IP IGMP Multicast group configuration entry.
               Each entry is indexed by  igmpGroupVlanId, 
               igmpGroupStatic, and igmpGroupAddress"
        INDEX { igmpGroupVlanId, igmpGroupStatic, igmpGroupAddress}
        ::= { igmpGroupTable 1 }

IgmpGroupEntry ::= SEQUENCE {
        igmpGroupVlanId
             VlanId,  
        igmpGroupStatic
             Boolean,
        igmpGroupAddress
             IpAddress,
        igmpGroupIncluded
             INTEGER,
        igmpGroupStatus
             StatusIndicator
        }

igmpGroupVlanId OBJECT-TYPE
        SYNTAX  VlanId
        ACCESS  read-only 
        STATUS  mandatory
        DESCRIPTION
             "The unique VLAN identifier of this IGMP multicast group 
	      address entry. "
        ::= { igmpGroupEntry 1 }

igmpGroupStatic OBJECT-TYPE
        SYNTAX  Boolean
        ACCESS  read-only 
        STATUS  mandatory
        DESCRIPTION
             " Indicates whether the IGMP multicast group was created 
               statically(TRUE) by a management entity, or dynamically 
               learned"
        ::= { igmpGroupEntry 2 }

igmpGroupAddress OBJECT-TYPE
        SYNTAX  IpAddress
        ACCESS  read-only 
        STATUS  mandatory
        DESCRIPTION
             "The multicast group address(Class D). The range is from
              224.0.0.0 to 239.255.255.255. The addresses from
              224.0.0.0 to 224.0.0.255 are reserved IP multicast addresses."
        ::= { igmpGroupEntry 3 }

igmpGroupIncluded OBJECT-TYPE
        SYNTAX  INTEGER {
             included(1),
             excluded(2)
             }
        ACCESS  read-write
        STATUS  mandatory
        DESCRIPTION
             "Indicates the multicast addresses are to be included or
	      excluded from the group. Dynamic entries are always included
              and can not be modified, while static entries may be
              either included or excluded. For each VLAN, it only 
              allows to configure either 'included' as static or
              'excluded' as static. "
        ::= { igmpGroupEntry 4 }

igmpGroupStatus OBJECT-TYPE
        SYNTAX  StatusIndicator
        ACCESS  read-write
        STATUS  mandatory
        DESCRIPTION
             "The status of this multicast group entry: 'valid' and
	      'invalid'. This object enables the user to add or delete 
	      this multicast group. Setting the status as 'valid' is to
	      add the entry; otherwise as 'invalid' is to delete the 
              entry.
              An example to create an multicast group entry is:
              set igmpGroupStatus.3.1.224.0.0.1= valid
              where 3: vlan id; 1: static; 224.0.0.1: multicast group IP 
              address"
        ::= { igmpGroupEntry 5 }

--
--  The multicast router port table
--
 
igmpRouterPortTable OBJECT-TYPE
        SYNTAX  SEQUENCE OF IgmpRouterPortEntry
        ACCESS  not-accessible
        STATUS  mandatory
        DESCRIPTION
              "IP IGMP Multicast router port table. It contains a list of
	       the ports containing configured IGMP routers. These 
	       ports initialize the IPrDtag and IPmDtag for the group."
        ::= { vlanIGMPConfig 4 }
 
igmpRouterPortEntry OBJECT-TYPE
        SYNTAX  IgmpRouterPortEntry
        ACCESS  not-accessible
        STATUS  mandatory
        DESCRIPTION
              "IP IGMP Multicast router port entry. Each entry is 
               indexed by igmpRouterPortVlanId, igmpRouterPortStatic,
               igmpRouterPortCard, igmpRouterPortPort"
        INDEX { igmpRouterPortVlanId, igmpRouterPortStatic,
                igmpRouterPortCard, igmpRouterPortPort}
        ::= { igmpRouterPortTable 1 }
 
IgmpRouterPortEntry ::= SEQUENCE {
        igmpRouterPortVlanId
             VlanId,
        igmpRouterPortStatic
             Boolean,
        igmpRouterPortCard
	     CardId,
        igmpRouterPortPort
	     PortId,
        igmpRouterPortStatus
	     StatusIndicator
        }


igmpRouterPortVlanId OBJECT-TYPE
        SYNTAX  VlanId
        ACCESS  read-only 
        STATUS  mandatory
        DESCRIPTION
             "The unique VLAN identifier of this IGMP multicast 
	      router port entry. "
        ::= { igmpRouterPortEntry 1 }

igmpRouterPortStatic OBJECT-TYPE
        SYNTAX  Boolean
        ACCESS  read-only 
        STATUS  mandatory
        DESCRIPTION
             " Indicates whether the IGMP multicast router port was 
               created statically(TRUE) by a management entity, or 
	       dynamically learned. "
        ::= { igmpRouterPortEntry 2 }

igmpRouterPortCard OBJECT-TYPE
        SYNTAX  CardId
        ACCESS  read-only 
        STATUS  mandatory
        DESCRIPTION
             "The card id of this multicast router port entry. "
        ::= { igmpRouterPortEntry 3 }

igmpRouterPortPort OBJECT-TYPE
        SYNTAX  PortId
        ACCESS  read-only 
        STATUS  mandatory
        DESCRIPTION
             "The port id of this multicast router port entry. "
        ::= { igmpRouterPortEntry 4 }

igmpRouterPortStatus OBJECT-TYPE
        SYNTAX  StatusIndicator
        ACCESS  read-write
        STATUS  mandatory
        DESCRIPTION
             "The status of this multicast router port entry: 'valid'
	      and 'invalid'. This object enables the user to add or 
	      delete this multicast group. Setting the status as 'valid'
	      is to add the entry; otherwise as 'invalid' is to delete
	      the entry. 
              An example to create an multicast router port entry is:
              set igmpRouterPortStatus.3.1.5.2 = valid
              where 3: vlan id; 1: static; 5.2 : card/port that is 
	      connected with igmp router"
        ::= { igmpRouterPortEntry 5 }


END

-- SECTION 1: Top Level Definitions
 
RFC1407-EXT-MIB DEFINITIONS ::= BEGIN
 
 
-- RFC1407(DS3/E3) Extensions MIB Release 2.0.0
-- Revision 12/01/97
 
-- Copyright 1997 Bay Networks, Inc.
-- All rights reserved.
-- This Bay Networks SNMP Management Information Base Specification
-- (Specification) embodies Bay Networks' confidential and
-- proprietary intellectual property. Bay Networks retains all
-- title and ownership in the Specification, including any
-- revisions.
 
-- This Specification is supplied "AS IS," and Bay Networks makes
-- no warranty, either express or implied, as to the use,
-- operation, condition, or performance of the Specification.
 
 
 
-- Imports
 
IMPORTS
        OBJECT-TYPE
                FROM RFC-1212
        Gauge
                FROM RFC1155-SMI
        extensions, EnableIndicator
                FROM CENTILLION-ROOT-MIB
        dsx3TotalIndex
                FROM RFC1407-MIB;
 
 
cnds3e3Ext         OBJECT IDENTIFIER ::= { extensions 6 }
 
cndsx3Oper         OBJECT IDENTIFIER ::= { cnds3e3Ext 1 }
cndsx3TotalExt     OBJECT IDENTIFIER ::= { cnds3e3Ext 2 }
cndsx3ConfigExt    OBJECT IDENTIFIER ::= { cnds3e3Ext 3 }
 
-- SECTION 2: MIB Objects
 
-- DS3/E3 Total Extention Table
 
cndsx3TotalExtTable    OBJECT-TYPE
       SYNTAX SEQUENCE OF  Cndsx3TotalExtEntry
       ACCESS not-accessible
       STATUS mandatory
       DESCRIPTION
               "This table contains the counters
                that are additional to the 
                existing dsx3TotalTable"
       ::= { cndsx3TotalExt 1}
 
cndsx3TotalExtEntry OBJECT-TYPE
       SYNTAX Cndsx3TotalExtEntry
       ACCESS not-accessible
       STATUS mandatory
       DESCRIPTION
               "An entry in the DS3/E3 TotalExt table."
       INDEX { dsx3TotalIndex }
       ::= { cndsx3TotalExtTable 1 }
 
Cndsx3TotalExtEntry ::= SEQUENCE {
       cndsx3CellPayloadHECError
               Gauge
       }
 
cndsx3CellPayloadHECError OBJECT-TYPE
       SYNTAX  Gauge
       ACCESS  read-only
       STATUS  mandatory
       DESCRIPTION
               "A counter of Payload HEC errors."
       ::= { cndsx3TotalExtEntry 1 }
 
-- DS3/E3 Configuration Extention Table
 
cndsx3ConfigExtTable    OBJECT-TYPE
       SYNTAX SEQUENCE OF  Cndsx3ConfigExtEntry
       ACCESS not-accessible
       STATUS mandatory
       DESCRIPTION
               "This table contains the configurable parameters
                that are additional to the
                existing dsx3ConfigTable"
       ::= { cndsx3ConfigExt 1}
 
cndsx3ConfigExtEntry OBJECT-TYPE
	SYNTAX Cndsx3ConfigExtEntry
       	ACCESS not-accessible
       	STATUS mandatory
       	DESCRIPTION
		"An entry in the DS3/E3 ConfigExt table."
	INDEX { cndsx3LineIndex }
       	::= { cndsx3ConfigExtTable 1 }
 
Cndsx3ConfigExtEntry ::= SEQUENCE {
       	cndsx3LineBuildOut
               	EnableIndicator,
       	cndsx3LineIndex
               	INTEGER,
       	cndsx3ScramblingEnable
		EnableIndicator,
	cndsx3E3ConfigType
		INTEGER
       	}

cndsx3LineBuildOut OBJECT-TYPE
       SYNTAX  EnableIndicator
       ACCESS  read-write
       STATUS  mandatory
       DESCRIPTION
                "Indicates LineBuild Out status"
       ::= { cndsx3ConfigExtEntry 1 }
 
cndsx3LineIndex OBJECT-TYPE
        SYNTAX  INTEGER (1..65535)
        ACCESS  read-only
        STATUS  mandatory
        DESCRIPTION
            "This object is the identifier of a DS3/E3
            Interface on a managed device."
        ::= { cndsx3ConfigExtEntry 2 }

cndsx3ScramblingEnable OBJECT-TYPE
	SYNTAX  EnableIndicator
       	ACCESS  read-write
       	STATUS  mandatory
       	DESCRIPTION
       		"This field indicates if scrambing is enabled or
		disabled."
       	::= { cndsx3ConfigExtEntry 3 }

cndsx3E3ConfigType OBJECT-TYPE
      	SYNTAX INTEGER {
              	other(1),
              	g751(2),
              	g832(3)
              	}
      	ACCESS read-write
      	STATUS mandatory
      	DESCRIPTION
      		"This object allows to switch between E3 G751 and G832 mode.
      		The following value is read-only:
              		other(1).......other than g751 and g832
      		The following value is read-write:
              		g751(2)........E3ConfigType is G751
              		g832(3)........E3ConfigType is G832"
	::= { cndsx3ConfigExtEntry 4 }


-- DS3/E3 Operational Configuration Table
 
cndsx3OperTable    OBJECT-TYPE
       SYNTAX SEQUENCE OF  Cndsx3OperEntry
       ACCESS not-accessible
       STATUS mandatory
       DESCRIPTION
               "This table contains the configuration
               information that are operational currently. 
               This table contains all the objects defined
               in dsx3ConfigTable plus some additional.
               This table is read only"
       ::= { cndsx3Oper 1}
 
cndsx3OperEntry OBJECT-TYPE
	SYNTAX Cndsx3OperEntry
       	ACCESS not-accessible
       	STATUS mandatory
       	DESCRIPTION
               "An entry in the DS3/E3 Operational Configuration table."
       	INDEX { cndsx3OperLineIndex }
       	::= { cndsx3OperTable 1 }
 
Cndsx3OperEntry ::= SEQUENCE {
        cndsx3OperLineIndex
            	INTEGER,
        cndsx3OperLineType
            	INTEGER,
        cndsx3OperLoopbackConfig
            	INTEGER,
        cndsx3OperLineStatus
            	INTEGER,
        cndsx3OperTransmitClockSource
            	INTEGER,
        cndsx3OperPlcpLOFEvent
            	INTEGER,
        cndsx3OperG832CellDelineation
            	INTEGER,
        cndsx3OperLineBuildOut
            	EnableIndicator,
       	cndsx3OperScramblingEnable
               	EnableIndicator,
	cndsx3OperE3ConfigType
		INTEGER
       	}
 
cndsx3OperLineIndex OBJECT-TYPE
        SYNTAX  INTEGER (1..65535)
        ACCESS  read-only
        STATUS  mandatory
        DESCRIPTION
            "This object is the identifier of a DS3/E3
            Interface on a managed device."
        ::= { cndsx3OperEntry 1 }
  
cndsx3OperLineType OBJECT-TYPE
        SYNTAX  INTEGER {
                dsx3other(1),
                dsx3M23(2),
                dsx3SYNTRAN(3),
                dsx3CbitParity(4),
                dsx3ClearChannel(5),
                e3other(6),
                e3Framed(7),
                e3Plcp(8)
               	}
        ACCESS  read-only
        STATUS  mandatory
        DESCRIPTION
             	"This variable indicates the variety of DS3 C-bit
              	or E3 application implementing this interface.  
              	The type of interface affects the interpretation of the
              	usage and error statistics.
 
              	The rate of DS3 is 44.736 Mbps and E3 is 34.368 Mbps.
              	The dsx3ClearChannel value means that the C-bits
              	are not used except for sending/receiving AIS.
 
              	The values, in sequence, describe:
 
              	TITLE:            	SPECIFICATION:
              	dsx3M23      		ANSI T1.107-1988
              	dsx3SYNTRAN        	ANSI T1.107-1988
              	dsx3CbitParity     	ANSI T1.107a-1989
              	dsx3ClearChannel   	ANSI T1.102-1987
              	e3Framed           	CCITT G.751
              	e3Plcp             	ETSI T/NA(91)18."
        ::= { cndsx3OperEntry 2 }
 
cndsx3OperLoopbackConfig OBJECT-TYPE
        SYNTAX  INTEGER {
                  dsx3NoLoop(1),
                  dsx3PayloadLoop(2),
                  dsx3LineLoop(3),
                  dsx3OtherLoop(4)
                }
        ACCESS  read-only
        STATUS  mandatory
        DESCRIPTION
           "This variable represents the loopback configuration
            of the DS3/E3 interface.  
 
           dsx3NoLoop
              Not in the loopback state.  A device that is
              not capable of performing a loopback on
              the interface shall always return this as
              it's value.
 
           dsx3PayloadLoop
              The received signal at this interface is looped
              through the device.  Typically the received signal
              is looped back for retransmission after it has
              passed through the device's framing function.
 
           dsx3LineLoop
              The received signal at this interface does not
              go through the device (minimum penetration) but
              is looped back out.
 
            dsx3OtherLoop
              Loopbacks that are not defined here."
        ::= { cndsx3OperEntry 3 }
 
cndsx3OperLineStatus OBJECT-TYPE
        SYNTAX  INTEGER (1..1023)
        ACCESS  read-only
        STATUS  mandatory
        DESCRIPTION
          "This variable indicates the
          Line Status of the interface.
          It contains loopback state information
          and failure state information.
          The dsx3LineStatus is a bit map represented
          as a sum, therefore, it can represent multiple failures
          and a loopback (see dsx3LoopbackConfig object for the 
          type of loopback) simultaneously.
          The dsx3NoAlarm should be set if and only if
          no other flag is set.
 
          The various bit positions are:
             1     dsx3NoAlarm       No alarm present
             2     dsx3RcvRAIFailure Receiving Yellow/Remote
                   Alarm Indication
             4     dsx3XmitRAIAlarm Transmitting Yellow/Remote
                   Alarm Indication
             8     dsx3RcvAIS        Receiving AIS failure state
            16     dsx3XmitAIS       Transmitting AIS
            32     dsx3LOF           Receiving LOF failure state
            64     dsx3LOS           Receiving LOS failure state
           128     dsx3LoopbackState Looping the received signal
           256     dsx3RcvTestCode   Receiving a Test Pattern
           512     dsx3OtherFailure any line status not defined here"
        ::= { cndsx3OperEntry 4 }
 
cndsx3OperTransmitClockSource OBJECT-TYPE
        SYNTAX  INTEGER {
                  loopTiming(1),
                  localTiming(2),
                  throughTiming(3)
        }
        ACCESS  read-only
        STATUS  mandatory
        DESCRIPTION
           "The source of Transmit Clock.
           is derived from the recovered receive clock of
           another DS3 interface."
        ::= { cndsx3OperEntry 5 }
 
cndsx3OperPlcpLOFEvent OBJECT-TYPE
       SYNTAX  INTEGER {
               on(1),
               off(2)
               }
       ACCESS  read-only
       STATUS  mandatory
       DESCRIPTION
               "Indicates PLCP Loss of Frame event. 
               The following value is read-only:
                 on(1).......Loss of Frame event is present
                 off(2)......Loss of Frame event is not present"
       ::= { cndsx3OperEntry 6 }
 
cndsx3OperG832CellDelineation OBJECT-TYPE
       SYNTAX  INTEGER {
               on(1), 
               off(2)
               }
       ACCESS  read-only
       STATUS  mandatory
       DESCRIPTION
               "Indicates Cell Delineation events.
               The following value is read-only:
                 on(1).......Cell Delineation event is present
                 off(2)......Cell Delineation event is not present"
       ::= { cndsx3OperEntry 7 }
 
cndsx3OperLineBuildOut OBJECT-TYPE
       SYNTAX  EnableIndicator
       ACCESS  read-only
       STATUS  mandatory
       DESCRIPTION
                "Indicates line buildout status"
       ::= { cndsx3OperEntry 8 }
 
cndsx3OperScramblingEnable OBJECT-TYPE
       SYNTAX  EnableIndicator
       ACCESS  read-only
       STATUS  mandatory
       DESCRIPTION
                "This field indicates if scrambing is enabled or
		disabled."
       ::= { cndsx3OperEntry 9 }

cndsx3OperE3ConfigType OBJECT-TYPE
	SYNTAX INTEGER {
		other(1),
		g751(2),
		g832(3)
		}
	ACCESS read-only
	STATUS mandatory
	DESCRIPTION
		"This object shows E3Config mode.
		The following value is read-only:
			other(1).......other than g751 and g832
			g751(2)........E3ConfigType is G751
			g832(3)........E3ConfigType is G832"
	::= { cndsx3OperEntry 10 }


END
 
-- SECTION 1: Top Level Definitions


CENTILLION-VLAN-MIB DEFINITIONS ::= BEGIN


-- Centillion VLAN MIB Release 0.0.0
-- Revision 2/24/98

-- Copyright 1998 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	OBJECT-TYPE
	    FROM RFC-1212
    RowStatus, TruthValue
        FROM SNMPv2-TC-v1
    InterfaceIndex
        FROM IF-MIB
    vlan, VlanId
        FROM CENTILLION-MCAST-MIB;


-- Groups

cnVlanMemberGroup   OBJECT IDENTIFIER ::= { vlan 2 }

-- SECTION 2: VLAN Port Membership Configuration Table
--
-- This table defines the VLAN membership and configuration for each port.
-- It is used as a substitute for the cnVlanPortTable to provide
-- configuration support for agents that handle token ring ports
-- in source routing VLANs and/or define a port's ingress
-- classification method by VLAN.
--

cnVlanPortMemberTable OBJECT-TYPE
        SYNTAX        SEQUENCE OF CnVlanPortMemberEntry
        ACCESS        not-accessible
        STATUS        mandatory
        DESCRIPTION   "The VLAN port membership configuration table. This 
                      table contains membership information pertaining to the
                      ports belonging to a VLAN." 
        ::= { cnVlanMemberGroup 1 }

cnVlanPortMemberEntry OBJECT-TYPE
        SYNTAX        CnVlanPortMemberEntry
        ACCESS        not-accessible
        STATUS        mandatory
        DESCRIPTION   "An entry containing VLAN membership information 
                      for a particular port.  Entries are added by
                      specifying the cnVlanPortMemberCard,
                      cnVlanPortMemberPort, cnVlanPortMemberVID,
					  and the cnVlanPortMemberIngressType.
                      Entries are deleted simply by setting the
                      cnVlanPortMemberStatus object to destroy."
        INDEX         { cnVlanPortMemberCard,
                        cnVlanPortMemberPort,
                        cnVlanPortMemberVID }
        ::= { cnVlanPortMemberTable 1 }

CnVlanPortMemberEntry ::= SEQUENCE {
	cnVlanPortMemberCard
		INTEGER,
	cnVlanPortMemberPort
		INTEGER,
	cnVlanPortMemberVID
		VlanId,
	cnVlanPortMemberStatus
		RowStatus,
	cnVlanPortMemberIngressType
		INTEGER,
	cnVlanPortMemberDynamic
		TruthValue,
	cnVlanPortMemberIfIndex
		InterfaceIndex,
	cnVlanPortMemberRing
		INTEGER
	}

cnVlanPortMemberCard OBJECT-TYPE
	SYNTAX	INTEGER
	ACCESS	read-only
	STATUS	mandatory
	DESCRIPTION
            "The card number for this port in the VLAN."
	::= { cnVlanPortMemberEntry 1 }

cnVlanPortMemberPort OBJECT-TYPE
	SYNTAX	INTEGER
	ACCESS	read-only
	STATUS	mandatory
	DESCRIPTION
            "The port number for this port in the VLAN."
	::= { cnVlanPortMemberEntry 2 }

cnVlanPortMemberVID OBJECT-TYPE
	SYNTAX	VlanId
	ACCESS	read-only
	STATUS	mandatory
	DESCRIPTION
            "The VLAN ID of which this port is a member."
	::= { cnVlanPortMemberEntry 3 }

cnVlanPortMemberStatus OBJECT-TYPE
	SYNTAX	RowStatus
	ACCESS	read-write
	STATUS	mandatory
	DESCRIPTION
            "The current status of the entry. Entries may be added by
            specifying a value of createAndGo, and removed by setting
            the status to destroy."
	::= { cnVlanPortMemberEntry 4 }

cnVlanPortMemberIngressType OBJECT-TYPE
	SYNTAX	INTEGER {
	        pvid(1),         -- classify by configured PVID
	        tag(2),          -- classify by 802.1Q tag (VID)
	        protocolId(3)    -- classify by ingress protocol type
	        }
	ACCESS	read-write
	STATUS	mandatory
	DESCRIPTION
            "The method used to classify ingress frames on this
            port into this VLAN.  The allowed values are specific to
            the cnVlanType of the VLAN as follows:
                byPort:         pvid or tag
                byProtocolId:   pvid, tag, or protocolId
            Allowable values may also be restricted by the
            VLAN capabilities of this port."
	::= { cnVlanPortMemberEntry 5 }

cnVlanPortMemberDynamic OBJECT-TYPE
	SYNTAX	TruthValue
	ACCESS	read-only
	STATUS	mandatory
	DESCRIPTION
            "The value for this object indicates whether the
            switch learned this port's VLAN membership dynamically."
	::= { cnVlanPortMemberEntry 6 }

cnVlanPortMemberIfIndex OBJECT-TYPE
	SYNTAX	InterfaceIndex
	ACCESS	read-only
	STATUS	mandatory
	DESCRIPTION
            "The value for this object identifies the instance of
            the ifIndex object, defined in MIB-II, for the interface
            corresponding to this port and VLAN. If no such entry
            exists, the value 0 may be returned."
	::= { cnVlanPortMemberEntry 7 }


cnVlanPortMemberRing OBJECT-TYPE
	SYNTAX	INTEGER
	ACCESS	read-write
	STATUS	mandatory
	DESCRIPTION
            "The ring number for this port if this VLAN uses source
            route or source route transparent bridging."
	::= { cnVlanPortMemberEntry 8 }



-- SECTION 3: Default Management Vlan Configuration
--

cnVlanENETMgt OBJECT-TYPE
        SYNTAX        VlanId
        ACCESS        read-write
        STATUS        mandatory
        DESCRIPTION   "VID of the Ethernet management VLAN. The null
	              VID indicates that an Ethernet management VLAN
		      is not configured."
        ::= { vlan 3 }

cnVlanTRMgt OBJECT-TYPE
        SYNTAX        VlanId
        ACCESS        read-write
        STATUS        mandatory
        DESCRIPTION   "VID of the Token Ring management VLAN. The null
	              VID indicates that an Token Ring management VLAN
		      is not configured."
        ::= { vlan 4 }


END

-- SECTION 1: Top Level Definitions

CENTILLION-SONET-MIB DEFINITIONS ::= BEGIN


-- Centillion SONET MIB Release 1.0.0
-- Revision 02/12/98

-- Copyright 1998 Bay Networks Communications, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
   Counter32
         FROM SNMPv2-SMI-v1
   OBJECT-TYPE
         FROM RFC-1212
   ifIndex
         FROM RFC1213-MIB
   atmSonet
         FROM CENTILLION-ROOT-MIB;


-- Groups

atmSonetConfig          OBJECT IDENTIFIER ::=   { atmSonet 1 }


-- SECTION 2: SONET Section Table

-- Centillion SONET/SDH Section group contains additional
-- information not contained in RFC SONET/SDH Section groups.

cnSonetSectionTable OBJECT-TYPE
   SYNTAX  SEQUENCE OF CnSonetSectionEntry
   ACCESS  not-accessible
   STATUS  mandatory
   DESCRIPTION
           "The Centillion SONET/SDH Section table."
   ::= { atmSonetConfig 1 }

cnSonetSectionEntry OBJECT-TYPE
   SYNTAX  CnSonetSectionEntry
   ACCESS  not-accessible
   STATUS  mandatory
   DESCRIPTION
           "An entry in the Centillion SONET/SDH
           Section table."
   INDEX   { ifIndex }
   ::= { cnSonetSectionTable 1 } 

CnSonetSectionEntry ::=
   SEQUENCE {
      cnSonetSectionBip8Errors   Counter32
   }

cnSonetSectionBip8Errors OBJECT-TYPE
   SYNTAX  Counter32
   ACCESS  read-only 
   STATUS  mandatory
   DESCRIPTION
      "Section Bit Interleaved Parity.
       Number of STS-3(c) frames with BIP-8 errors."
   ::= { cnSonetSectionEntry 1 }

END
-- SECTION 1: Top Level Definitions


CENTILLION-SYSTEM-EVENT-LOG-MIB DEFINITIONS ::= BEGIN


-- Centillion System Event Log Management MIB Release 1.0.0
-- Revision 11/03/98

-- Copyright 1998 Nortel Networks, Inc.
-- All rights reserved.
-- This Nortel Networks SNMP Management Information Base Specification
-- (Specification) embodies Nortel Networks' confidential and
-- proprietary intellectual property. Nortel Networks retains all
-- title and ownership in the Specification, including any
-- revisions.

-- This Specification is supplied "AS IS," and Nortel Networks makes
-- no warranty, either express or implied, as to the use,
-- operation, condition, or performance of the Specification.


-- Imports

IMPORTS
	IpAddress
		FROM RFC1155-SMI
	OBJECT-TYPE
		FROM RFC-1212
	DisplayString
		FROM RFC1213-MIB
	TimeIntervalSec
		FROM S5-TCS-MIB
	CardId, PortId,
	sysEvtLogMgmt
		FROM CENTILLION-ROOT-MIB;


-- SECTION 2: System Event Log Management MIB Objects


 sysEvtLogDuration OBJECT-TYPE
 	SYNTAX	TimeIntervalSec 
 	ACCESS	read-write
 	STATUS	mandatory
 	DESCRIPTION
 		"This value indicates the remaining duration of Event Logging. 
 		The unit is in seconds. The maximum value is equal to 1000 days
		(86,400,000 seconds). A set value of greater than 1000 days will result 
		BADVALUE return. A value of 0 indicates the Event Logging is now stopped
		and disabled. A non-zero value indicates that Event Logging is enabled.
		Default value is set at system cold start only.
 		"
     DEFVAL { 0 }
 	::= { sysEvtLogMgmt 1  }
 
 sysEvtLogPreFilterEntityMap OBJECT-TYPE
 	SYNTAX	OCTET STRING (SIZE (8))
 	ACCESS	read-write
 	STATUS	mandatory
 	DESCRIPTION
 		"The bit array that contains the bit map of all possible entities for
 		event logging pre-filter control. There are total of 64 entities.
 		Each entity represented	by one bit. A bit with a value of 1 means
 		that the corresponding Entity is enabled for event logging, 
 		0 when the event logging is disabled for the corresponding entity.
 		
 		The following show the bit position and associated entity.
 			Bit 0 - SNMP_ENT_ATM_PORT
 			Bit 1 - SNMP_ENT_BOOTP
 			Bit 2 - SNMP_ENT_CLC
 			Bit 3 - SNMP_ENT_CLI
 			Bit 4 - SNMP_ENT_CONFIG
 			Bit 5 - SNMP_ENT_ETHERNET
 			Bit 6 - SNMP_ENT_FDB
 			Bit 7 - SNMP_ENT_HW
 			Bit 8 - SNMP_ENT_IISP
 			Bit 9 - SNMP_ENT_ILMI
 			Bit 10 - SNMP_ENT_IP
 			Bit 11 - SNMP_ENT_LANE
 			Bit 12 - SNMP_ENT_LEC
 			Bit 13 - SNMP_ENT_MCP
 			Bit 14 - SNMP_ENT_SIGNL
 			Bit 15 - SNMP_ENT_SNMP
 			Bit 16 - SNMP_ENT_STP
 			Bit 17 - SNMP_ENT_TELNET
 			Bit 18 - SNMP_ENT_TFTP
 			Bit 19 - SNMP_ENT_TOKENRING
 			Bit 20 - SNMP_ENT_VPORT
 			Bit 21 - SNMP_ENT_MPOA
 
 		When a new entity is created, a new bit position should also be defined.
 		The order of bit is defined as bit 0-7 in the lowest oder of byte
 		(first byte), bit 8-15 in the second lowest order of byte(second bye),
 		and so on. The lower number of bit is the least significant bit within 
 		the byte.
 		"
 	DEFVAL { 'FFFFFFFFFFFFFFFF'h }
 	::= { sysEvtLogMgmt 2  }
 
 sysEvtLogPreFilterSeverity OBJECT-TYPE
 	SYNTAX	INTEGER {
 		emergency (1),
 		alert (2),
 		critical (3),
 		error (4),
 		warning (5),
 		notice (6),
 		info (7),
 		debug(8)
 		}
  	ACCESS	read-write
 	STATUS	mandatory
 	DESCRIPTION
 		"This value indicates the severity level for event log 
 		pre-filtering control. An event message with less severity level
 		will not be logged into event message buffer.
 		All messages with equal or greater severity level are logged
 		into the message buffer. The emergency level is also named as panic
		level inc CLI command.  
 		"
 	DEFVAL { error }
 	::= { sysEvtLogMgmt 3  }
 
 
 sysEvtLogSlotPreFilterTable OBJECT-TYPE
 	SYNTAX	SEQUENCE OF SysEvtLogSlotPreFilterEntry
 	ACCESS	not-accessible
 	STATUS	mandatory
 	DESCRIPTION
 		"A slot table for controlling pre-filter setting for all slots.
 		This table is managed by Event Log application only. Table entries cannot be 
 		created or deleted.
 		"
 	::= { sysEvtLogMgmt 4 }
 
 sysEvtLogSlotPreFilterEntry OBJECT-TYPE
 	SYNTAX	SysEvtLogSlotPreFilterEntry
 	ACCESS	not-accessible
 	STATUS	mandatory
 	DESCRIPTION
 		"An entry of the slot pre-filter table.
 		"
 	INDEX	{ sysEvtLogSlotPreFilterCardId }
 	::= { sysEvtLogSlotPreFilterTable 1 }
 
 SysEvtLogSlotPreFilterEntry ::= SEQUENCE {
 	sysEvtLogSlotPreFilterCardId CardId,
 	sysEvtLogSlotPreFilterControl INTEGER
 	}
 
 sysEvtLogSlotPreFilterCardId OBJECT-TYPE
 	SYNTAX	CardId 
 	ACCESS	read-only
 	STATUS	mandatory
 	DESCRIPTION
 		"The slot index varies by system. It is chassis dependent.
 		For C100, valid number is 1-6. For BH left, valid number is 2-7.
 		For BH right, valid number is 8-13. etc.
 		"
 	::= { sysEvtLogSlotPreFilterEntry 1 }
 
 
 sysEvtLogSlotPreFilterControl OBJECT-TYPE
 	SYNTAX	INTEGER {
 			disable(1),
 			enable(2)
 			}
 	ACCESS	read-write
 	STATUS	mandatory
 	DESCRIPTION
 		"This value indicates the pre-filter setting for the specified slot.
 		"
 	DEFVAL { enable }
 	::= { sysEvtLogSlotPreFilterEntry 2 }
 
 sysEvtLogPortPreFilterTable OBJECT-TYPE
 	SYNTAX	SEQUENCE OF SysEvtLogPortPreFilterEntry
 	ACCESS	not-accessible
 	STATUS	mandatory
 	DESCRIPTION
 		"A port table for controlling pre-filter setting for all ports.
 		This table is managed by Event Log application only. 
		Table entries cannot be created or deleted.
 		"
 	::= { sysEvtLogMgmt 5 }
 
 sysEvtLogPortPreFilterEntry OBJECT-TYPE
 	SYNTAX	SysEvtLogPortPreFilterEntry
 	ACCESS	not-accessible
 	STATUS	mandatory
 	DESCRIPTION
 		"An entry for port table for controlling pre-filter 
 setting for all ports.
 		"
 	INDEX	{ sysEvtLogPortPreFilterCardId, sysEvtLogPortPreFilterPortId }
 	::= { sysEvtLogPortPreFilterTable 1 }
 
 SysEvtLogPortPreFilterEntry ::= SEQUENCE {
 	sysEvtLogPortPreFilterCardId CardId,
 	sysEvtLogPortPreFilterPortId PortId,
 	sysEvtLogPortPreFilterControl INTEGER
 	}
 
 sysEvtLogPortPreFilterCardId OBJECT-TYPE
 	SYNTAX	CardId 
 	ACCESS	read-only
 	STATUS	mandatory
 	DESCRIPTION
 		"The slot index varies by system. It is chassis dependent.
 		For C100, valid number is 1-6. For BH left, valid number is 2-7.
 		For BH right, valid number is 8-13. etc.
 		"
 	::= { sysEvtLogPortPreFilterEntry 1 }
 
 sysEvtLogPortPreFilterPortId OBJECT-TYPE
 	SYNTAX	PortId 
 	ACCESS	read-only
 	STATUS	mandatory
 	DESCRIPTION
 		"The port index of the specified slot.
 		"
 	::= { sysEvtLogPortPreFilterEntry 2 }
 
 sysEvtLogPortPreFilterControl OBJECT-TYPE
 	SYNTAX	INTEGER {
 			disable(1),
 			enable(2)
 			}
 	ACCESS	read-write
 	STATUS	mandatory
 	DESCRIPTION
 		"This value indicates the pre-filter setting for the specified port.	
 		Note: A module must be properly configured before any port of the 
		module can be set with a value of sysEvtLogPortPreFilterControl.
		A BADVALUE is returned when one enables a port in a disabled slot.
 		"
 	DEFVAL { enable }
 	::= { sysEvtLogPortPreFilterEntry 3 }
 
 sysEvtLogDestMap OBJECT-TYPE
 	SYNTAX	INTEGER 
 	ACCESS	read-write
 	STATUS	mandatory
 	DESCRIPTION
 		"This value is a bit map of each destination that Event Log 
 		can forward messages to, where
			bit 0 for console CLI
			bit 1 for Syslogd
			bit 2 for Tftpsave
 		The value of other bits has no effect.
 		A bit value of 1 means the destination is enabled. 
 		Otherwise, disabled.
		Note: Enabling Syslogd prior setting sysEvtLogSysLogHostIp will return
		BADVALUE for set.  Enabling Tftpsave prior setting 
		sysEvtLogTftpsaveHostIp will return BADVALUE for set.
 		"
 	DEFVAL { 0 }
 	::= { sysEvtLogMgmt 6 }
 
-- Event Log SysLogd Destination Group

 sysEvtLogSysLogCfg OBJECT IDENTIFIER ::= { sysEvtLogMgmt 7 }

 sysEvtLogSysLogHostIp OBJECT-TYPE
 	SYNTAX  IpAddress	
 	ACCESS	read-write
 	STATUS	mandatory
 	DESCRIPTION
 		"The IP address of Unix system that runs Syslogd.
 		The event messages are redirect to Syslogd only when this IP address is 
 		valid and the bit value of Syslogd of sysEvtLogDestMap is enabled.
		Note: Set an invalid IP address results a BADVALUE return.
 		"
 	DEFVAL { '00000000'h }
 	::= { sysEvtLogSysLogCfg 1  }
 
 sysEvtLogSysLogSeverity OBJECT-TYPE
 	SYNTAX 	INTEGER {
 		panic (1),
 		alert (2),
 		critical (3),
 		error (4),
 		warning (5),
 		notice (6),
 		info (7),
 		debug(8)
 		}
 	ACCESS	read-write
 	STATUS	mandatory
 	DESCRIPTION
 		"This value indicates the severity level for Event Log to forward
 		events to SysLogd in Unix system. An event message
 		with less severity level will not be forwarded to SysLogd.
 		All messages with equal or greater severity level are forwarded to 
		SysLogd. 
 		"
 	DEFVAL { error }
 	::= { sysEvtLogSysLogCfg 2  }
 
 
 sysEvtLogSysLogFacility OBJECT-TYPE
 	SYNTAX	INTEGER {
 		local0 (1),
 		local1 (2),
 		local2 (3),
 		local3 (4),
 		local4 (5),
 		local5 (6),
 		local6 (7),
 		local7 (8)
 		}
 	ACCESS	read-write
 	STATUS	mandatory
 	DESCRIPTION
 		"This value indicates the facility number for the event messages to
 		be logged by syslogd. The supported values are from local0 to
 		local7 only (refer to syslogd manual of Unix system)
 		"
 	DEFVAL { local0 }
 	::= { sysEvtLogSysLogCfg 3  }
 
-- Event Log Tftpsave Destination Group

 sysEvtLogTftpsaveCfg OBJECT IDENTIFIER ::= { sysEvtLogMgmt 8 }

 sysEvtLogTftpsaveHostIp OBJECT-TYPE
 	SYNTAX  IpAddress	
 	ACCESS	read-write
 	STATUS	mandatory
 	DESCRIPTION
 		"The IP address of TFTP server system.
 		The event messages file is transfered from event log buffer to server
		system only when this IP is valid and the event message count reach its
 		threshold. (refer to sysEvtLogTftpsaveMaxMsgCount) and the bit value
		of Tftpsave of sysEvtLogDestMap is enabled.
		Note: Set an invalid IP address results a BADVALUE return.
 		"
 	DEFVAL { '00000000'h }
 	::= { sysEvtLogTftpsaveCfg 1 }
 
 sysEvtLogTftpsaveFileName OBJECT-TYPE
 	SYNTAX  DisplayString (SIZE(0..255))	
 	ACCESS	read-write
 	STATUS	mandatory
 	DESCRIPTION
 		"This octet string indicates the file name for the Tftpsave option of 
 		event log function. The filename will be appended with an extension  
 		nnn, where nnn ranges from 000 to 999, as each TFTP 
		file transfer occurs. The filename is default to the last three bytes
		of MAC address of the switch in hexadecimal format.
 		"
 	::= { sysEvtLogTftpsaveCfg 2 }
 
 
 sysEvtLogTftpsaveMaxMsgCount OBJECT-TYPE
 	SYNTAX	INTEGER 
 	ACCESS	read-write
 	STATUS	mandatory
 	DESCRIPTION
 		"This value indicates how many messages in the event log buffer will
 		trigger the TFTP file transfer for logged messages to TFTP host.
 		the default value is maximum messages count for the event log
 		buffer, which is currently equal to 680. If the value is set to 
 		zero or greater than the maximum value, it returns a BADVALUE.
 		"
 	::= { sysEvtLogTftpsaveCfg 3 }
 

END
-- SECTION 1: Top Level Definitions
 
MPOA-EXT-MIB DEFINITIONS ::= BEGIN
 
-- Centillion MPOA Extensions MIB Release 1.0.4
-- Revision 10/10/00
 
-- Copyright 1998-2000 Nortel Networks, Inc.
-- All rights reserved.
-- This Bay Networks SNMP Management Information Base Specification
-- (Specification) embodies Bay Networks' confidential and
-- proprietary intellectual property. Bay Networks retains all
-- title and ownership in the Specification, including any
-- revisions.
 
-- This Specification is supplied "AS IS," and Bay Networks makes
-- no warranty, either express or implied, as to the use,
-- operation, condition, or performance of the Specification.
 
-- Imports

IMPORTS
	OBJECT-TYPE
		FROM RFC-1212
	TruthValue, RowStatus
		FROM SNMPv2-TC-v1
	IpAddress
		FROM RFC1155-SMI
	mpcIndex
		FROM MPOA-MIB
	extensions, Boolean, BitField, EnableIndicator
		FROM CENTILLION-ROOT-MIB;



cnMpoaExt	OBJECT IDENTIFIER ::= { extensions 7 }
 
cnMpcConfigTable OBJECT-TYPE
    SYNTAX  SEQUENCE OF CnMpcConfigEntry
    ACCESS  not-accessible
    STATUS  mandatory
    DESCRIPTION
           "The MPOA Bay Networks proprietary Client Configuration Table.
                 This table contains configuration information
                 for all MPOA Clients which this agent manages."
    ::= { cnMpoaExt  2 }

cnMpcConfigEntry OBJECT-TYPE
    SYNTAX  CnMpcConfigEntry
    ACCESS  not-accessible
    STATUS  mandatory
    DESCRIPTION
           "MPOA Client Bay Networks Configuration Entry.
                 Each entry contains configuration information
                 for one MPOA Client."
    INDEX   { mpcIndex }
    ::= { cnMpcConfigTable  1 }

CnMpcConfigEntry ::=
    SEQUENCE {
        cnMpcShareControlVccs          TruthValue,
        cnMpcShareDataVccs             TruthValue,
        cnMpcValidEntryCheckInterval   INTEGER,
        cnMpcMinFlowPacketCount        INTEGER,
		cnMpcCfgEnable                 EnableIndicator

    }

cnMpcShareControlVccs OBJECT-TYPE
    SYNTAX  TruthValue
    ACCESS  read-write
    STATUS  mandatory
    DESCRIPTION
	"This Parameter enables VCC sharing for MPOA Control VCCs if set
	to true.

	LLC encapsulation is always signaled, regardless of sharing."
    ::= {cnMpcConfigEntry 1}

cnMpcShareDataVccs OBJECT-TYPE
    SYNTAX  TruthValue
    ACCESS  read-write
    STATUS  mandatory
    DESCRIPTION
	"This parameter enables VCC sharing for MPOA Data VCCs if set to
	true.
	LLC encapsulation is always signaled, regardless of sharing."

    ::= {cnMpcConfigEntry 2}

cnMpcValidEntryCheckInterval OBJECT-TYPE
    SYNTAX  INTEGER (1..2147483647)
    ACCESS  read-write
    STATUS  mandatory
    DESCRIPTION
	"This parameter specifies the interval in seconds, to check LOCAL
	IP FDB entries in the Valid state for minimum activity."
    ::= {cnMpcConfigEntry 3}

cnMpcMinFlowPacketCount OBJECT-TYPE
    SYNTAX  INTEGER
    ACCESS  read-write
    STATUS  mandatory
    DESCRIPTION
	"This parameter specifies the minimum number of packets to be
	forwarded by a Local FDB Entry in the Valid state in
	cnMpcValidEntryCheckInterval to maintain minimum activity level.
	If minimum activity is not maintained, the entry is deleted."
    ::= {cnMpcConfigEntry 4}

cnMpcCfgEnable OBJECT-TYPE
    SYNTAX  EnableIndicator
    ACCESS  read-write
    STATUS  mandatory
    DESCRIPTION
        "This parameter specifies the user configured state of the MPOA
        client.  1 equals Disabled, 2 equals Enabled. Default is Enabled."
    ::= {cnMpcConfigEntry 5}
 
--
-- cnMpoaIpVerification Group
--
-- This group is implemented to provide security features that are
-- inherently lacking in the MPOA specification.  The security
-- is provided using a table of IP addresses that limits the 
-- IP addresses serviced by the MPOA Client (MPC).  The table is
-- either an inclusion or exclusion list that allows or dissallows
-- MPOA shortcuts for the identified range of addresses.
--

cnMpoaIpVerification		OBJECT IDENTIFIER ::= { cnMpoaExt 3 }

cnMpoaIpVerificationTableType	OBJECT-TYPE
	SYNTAX	INTEGER {
		unknown(1),
		exclusion(2),
		inclusion(3)
		}
	ACCESS	read-write
	STATUS	mandatory
	DESCRIPTION
		"This object controls the type of verification table that
		is being used.  This object is used in combination with
		the status and download object and the IP verification
		table.  Any change made to this object must be downloaded to
		the switch cards using the cnMpoaIpVerificationTableDownload
		object before the settings actually take effect. 
		
		To enable a verification table, the table type must be set 
		to exclusion or inclusion, enabled using the table status 
		object and then downloaded to the cards using the download 
		object.  
		
		To delete the IP verification information, you must set 
		the table status object to clear and then downloaded to 
		the cards using the download object.  When the information
		is deleted, the table type is read as unknown.
		
		To change the table type between exclusion and inclusion,
		you must first delete the IP verification information and
		then recreate it."
	::= { cnMpoaIpVerification 1 }

cnMpoaIpVerificationTableStatus	OBJECT-TYPE
	SYNTAX	INTEGER {
		disable(1),
		enable(2),
		clear(3)
		}
	ACCESS	read-write
	STATUS	mandatory
	DESCRIPTION
		"This object is used to enable, disable or clear the IP
		Verification information.  Any change to this object
		information must be downloaded to the switch cards using
		the cnMpoaIpVerificationTableDownload object.  An empty 
		IP verification table will yield disable on a get."
	::= { cnMpoaIpVerification 2 }

cnMpoaIpVerificationTableDownload OBJECT-TYPE
	SYNTAX  Boolean
	ACCESS  read-write
	STATUS  mandatory
	DESCRIPTION
		"Setting this object to true(1) causes the MPOA IP
		Verification Table information to be downloaded to 
		all of the cards in the switch that support MPOA
		Clients (MPCs).  You must download the IP Verification 
		Table information to the cards before it will become
		effective when you are dynamically configuring this 
		feature.  The IP Verification Table is automatically
		downloaded to the MPC configured cards at card 
		initialization.
 
		When read, this object always returns false(2)."
	::= { cnMpoaIpVerification 3 }

cnMpoaIpVerificationTable	OBJECT-TYPE
	SYNTAX	SEQUENCE OF CnMpoaIpVerificationEntry
	ACCESS	not-accessible
	STATUS	mandatory
	DESCRIPTION
		"The MPC IP Verification Table is either an
		inclusion or exclusion list as indicated by the
		cnMpoaIpVerificationTableType object.  Any change 
		to this table must be downloaded to the switch 
		cards using the cnMpoaIpVerificationTableDownload 
		object."
	::= { cnMpoaIpVerification 4 }

cnMpoaIpVerificationEntry	OBJECT-TYPE
	SYNTAX	CnMpoaIpVerificationEntry
	ACCESS	not-accessible
	STATUS	mandatory
	DESCRIPTION
		"Each row of the cnMpoaIpVerificationTable 
		consists of an IP address and IP mask that 
		is used to identify a range of addresses that
		are included or excluded when creating MPOA
		IP shortcuts.  This cnMpoaIpVerificationStatus
		object is used to control adding or deleting
		each row."
	INDEX	{ cnMpoaIpVerificationAddress,
	     	  cnMpoaIpVerificationMask }
	::= { cnMpoaIpVerificationTable 1 }

CnMpoaIpVerificationEntry ::=
	SEQUENCE {
		cnMpoaIpVerificationAddress	IpAddress,
		cnMpoaIpVerificationMask	IpAddress,
		cnMpoaIpVerificationStatus	RowStatus
	}

cnMpoaIpVerificationAddress	OBJECT-TYPE
	SYNTAX	IpAddress
	ACCESS	read-only
	STATUS	mandatory
	DESCRIPTION
		"This object is one of the two keys used
		to access the cnMpoaIpVerificationTable
		entries.  This object contains an IP 
		address used in conjunction with the 
		cnMpoaIpVerificationMask to identify a
		range of one or more IP addresses."
	::= { cnMpoaIpVerificationEntry 1 }

cnMpoaIpVerificationMask	OBJECT-TYPE
	SYNTAX	IpAddress
	ACCESS	read-only
	STATUS	mandatory
	DESCRIPTION
		"This object is one of the two keys used
		to access the cnMpoaIpVerificationTable
		entries.  This object contains an IP 
		mask used in conjunction with the 
		cnMpoaIpVerificationAddress to identify a
		range of one or more IP addresses."
	::= { cnMpoaIpVerificationEntry 2 }

cnMpoaIpVerificationStatus	OBJECT-TYPE
	SYNTAX	RowStatus
	ACCESS	read-write
	STATUS	mandatory
	DESCRIPTION
		"Use this object to add or delete rows in the
		 cnMpoaIpVerificationTable.  To create new rows,
		 use createAndGo(4) or createAndWait(5).  To
		 delete entries use destroy(6).  A valid row
		 will have the status of active(1) on a get."
	::= { cnMpoaIpVerificationEntry 3 }

cnMpoaQosDscpToPriorityGroup OBJECT IDENTIFIER ::= { cnMpoaExt 4 }
-- OBJECT-GROUP
--  Status
--    mandatory
--  Descr
--  A collection of objects to facilitate the default and the user
--  configured download of Diffserv Code Point to 802.1p Priority 
--  mapping table into the switch.
--  Users will be able to see and modify this table only when the MPOA
--  capable option is enabled for at least one LEC in the switch.
-- Objects
-- cnMpoaQosDscpToPriorityDefaults,
-- cnMpoaQosDscpToPriorityDownload,
-- cnMpoaQosDscpToPriorityTable


cnMpoaQosDscpToPriorityDefaults OBJECT-TYPE
        SYNTAX  BitField
        ACCESS  read-write
        STATUS  mandatory
        DESCRIPTION
		"When this object is set to 1, it causes the 
		 switch internal cnMpoaQosDscpToPriorityTable
		 to be set to its factory default. Value will
		 always be read as zero, when doing the SNMP
		 get operation on the object.  Network Management
                 System can use this object to restore the mapping
		 table to its default values."
	::= { cnMpoaQosDscpToPriorityGroup 1 }

cnMpoaQosDscpToPriorityDownload OBJECT-TYPE
        SYNTAX  BitField
        ACCESS  read-write
        STATUS  mandatory
        DESCRIPTION
		"When this object is set to 1, it causes any
		 changes that were made with the
		 CnMpoaQosDscpToPriorityOutPriority object, to
		 be activated. If no changes were made, setting
		 this object has no effect. Value will always be
		 read as zero, when doing the SNMP get operation
		 on the object. The changes made by the user to
		 the DSCP to 802.1p mapping table will not come
		 into effect for the switching cards until this
		 object is set to 1."
        ::= { cnMpoaQosDscpToPriorityGroup 2 }

cnMpoaQosDscpToPriorityTable OBJECT-TYPE
        SYNTAX          SEQUENCE OF CnMpoaQosDscpToPriorityEntry
        ACCESS          not-accessible
        STATUS          mandatory
        DESCRIPTION
		"This table is used to specify the DS
		 Code Point to 802.1p priority mapping on
		 the egress MPC switch."
        ::= { cnMpoaQosDscpToPriorityGroup 3 }

cnMpoaQosDscpToPriorityEntry OBJECT-TYPE
        SYNTAX       CnMpoaQosDscpToPriorityEntry
        ACCESS        not-accessible
        STATUS        mandatory
        DESCRIPTION
		"Entry containing an individual DS code point
		 to 802.1p priority mapping."
        INDEX           {cnMpoaQosDscpToPriorityIndex}
        ::= { cnMpoaQosDscpToPriorityTable 1 } 

 CnMpoaQosDscpToPriorityEntry ::= SEQUENCE {
                cnMpoaQosDscpToPriorityIndex  INTEGER,
                cnMpoaQosDscpToPriorityInDscp INTEGER,
                cnMpoaQosDscpToPriorityOutPriority INTEGER
        }

cnMpoaQosDscpToPriorityIndex OBJECT-TYPE
        SYNTAX        INTEGER (1..64)
        ACCESS        read-only
        STATUS        mandatory
        DESCRIPTION
		"Used to uniquely identify a row in DSCP to 802.1p
		 table."
        ::= { cnMpoaQosDscpToPriorityEntry 1 }

cnMpoaQosDscpToPriorityInDscp OBJECT-TYPE
        SYNTAX        INTEGER (0..63) 
        ACCESS        read-only
        STATUS        mandatory
        DESCRIPTION
		"Six-bit Diffserv code point supplied in IP packet
		 header."
        ::= { cnMpoaQosDscpToPriorityEntry 2 }

cnMpoaQosDscpToPriorityOutPriority  OBJECT-TYPE
        SYNTAX        INTEGER (0..7)
        ACCESS        read-write
        STATUS        mandatory
        DESCRIPTION
		"802.1p priority value which can be mapped from
		 the DS code point supplied in the IP packet header.
		 Default mappings are always provided. However, if
		 the user would like to change the mappings, it is
		 recommended to follow the rules specified in RFC 2474
		 (Definition of the Differentiated Services Field in
		 the IPv4 and IPv6 Headers)."
        ::= { cnMpoaQosDscpToPriorityEntry 3 }

END
