-- ***************************************************************************
--  
-- Name: 3Com wireless LAN Object Identifier Registrations MIB
--  
-- The MIB is derived from an OEM product. 
--
-- History
-- Date         Who         Reason for Change
-- 09/06/2001   Yuli      	Initial Draft 
--  
-- ***************************************************************************
--      Copyright 3Com Technologies Limited. ( 2001 )

SRAP-GLOBAL-REG DEFINITIONS ::= BEGIN

IMPORTS
	MODULE-IDENTITY
		FROM SNMPv2-SMI
	wlan-mib 
		FROM A3Com-products-MIB;

srAPGlobalRegModule MODULE-IDENTITY
	LAST-UPDATED	"0105260000Z"
	ORGANIZATION	"3Com"
	CONTACT-INFO	"
		 Name: 		Yuli Hou
		 Mail Stop: 4240
		 Address:	5400 Bayfront Plaza
		 Zip:		CA 95052
		 City:		Santa Clara, 
		 Country:	USA
		 Phone:		+001-408-326-1191
		 Fax:		+001-408-326-6555
		 e-mail:	Yuli_Hou@3com.com"
	DESCRIPTION
		"The 3Com wireless LAN central registration module."
	::= { srAPModules 1 }

--
-- Start of the 3Com branch for proprietary MIBs
--
srAP			OBJECT IDENTIFIER ::= { wlan-mib 1 }
ecb			OBJECT IDENTIFIER ::= { wlan-mib 2 }
deltaFlyer		OBJECT IDENTIFIER ::= { wlan-mib 3 }
idefix   		OBJECT IDENTIFIER ::= { wlan-mib 4 }
addabbo   		OBJECT IDENTIFIER ::= { wlan-mib 5 }
rollo   		OBJECT IDENTIFIER ::= { wlan-mib 6 }
verazanno   	OBJECT IDENTIFIER ::= { wlan-mib 7 }
rivet     	      OBJECT IDENTIFIER ::= { wlan-mib 8 }

-- subtree for modules
srAPModules	OBJECT IDENTIFIER ::= { srAP 1 }

-- subtree for company-wide objects and events
srAPSNMPGen	OBJECT IDENTIFIER ::= { srAP 2 }

-- subtree for product-specific objects and events
srAPDot11Ext	OBJECT IDENTIFIER ::= { srAP 3 }

-- subtree for agent capabilities
srAPCapabilities	OBJECT IDENTIFIER ::= { srAP 4 }

-- subtree for requirement specifications
srAPReqs 	OBJECT IDENTIFIER ::= { srAP 5 }

-- subtree for experiments
srAPExperimental	OBJECT IDENTIFIER ::= { srAP 6 }

-- subtree for webapi
srAPWCM	OBJECT IDENTIFIER ::= { srAP 7 }


END



--
--  Textual Conventions - none at the moment
--
