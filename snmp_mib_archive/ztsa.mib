ZTSAMIB DEFINITIONS ::= BEGIN
--
-- This MIB defines Tandem TCP/IP Subagent configuration related objects
-- and traps.
--
-- 22AUG97 SAI - modified all displaystring(m..n) to displaystring(size(m..n))
-- since the strings appear on HPOV screen as hexadecimal characters otherwise
-- 13OCT97 SAI - add blanks as required by HPOV MIB compiler
-- 13SEP01 Prathi - Added new private MIB objects for TCPIP/SA enhancement
--                  to monitor subnets associated with multiple TCP/IP
--                  subsystems.

IMPORTS
        Counter
                FROM RFC1155-SMI
        OBJECT-TYPE
                FROM RFC-1212
        TRAP-TYPE
                FROM RFC-1215
        DisplayString
                FROM RFC1213-MIB;

--
--  TSAMIB
--
--   private         OBJECT IDENTIFIER ::= { iso(1) org(3) dod(6) internet(1) 4}
   enterprises     OBJECT IDENTIFIER ::= { private 1 }

   -- iso                OBJECT IDENTIFIER ::= { 1 }
   -- org                OBJECT IDENTIFIER ::= { iso 3 }
   -- dod                OBJECT IDENTIFIER ::= { org 6 }
   -- internet           OBJECT IDENTIFIER ::= { dod 1 }
   -- directory          OBJECT IDENTIFIER ::= { internet 1 }
   -- mgmt               OBJECT IDENTIFIER ::= { internet 2 }
   -- experimental       OBJECT IDENTIFIER ::= { internet 3 }
   -- private            OBJECT IDENTIFIER ::= { internet 4 }
   -- enterprises        OBJECT IDENTIFIER ::= { private 1 }

   tandem          OBJECT IDENTIFIER ::= { enterprises 169 }
   nonstopsystems  OBJECT IDENTIFIER ::= { tandem 3 }
   ztsa            OBJECT IDENTIFIER ::= { nonstopsystems 202 }

--
-- agent        reflects -a
--

ztsaAgentName OBJECT-TYPE
   SYNTAX      DisplayString (SIZE (0..31))
   ACCESS      read-only
   STATUS      mandatory
   DESCRIPTION
"the name of the SNMP Agent process."
   ::= { ztsa 1 }

ztsaAgentState OBJECT-TYPE
   SYNTAX      INTEGER {
                        connected   (1),
                        disconnected(2)
                       }
   ACCESS      read-only
   STATUS      mandatory
   DESCRIPTION
"current status of the agent interface. The state of this variable
will always be connected(1) when returned in a management request"
   ::= { ztsa 2 }

--
-- subagent process control area
--
ztsaProcessName OBJECT-TYPE
   SYNTAX      DisplayString (SIZE (0..49))
   ACCESS      read-only
   STATUS      mandatory
   DESCRIPTION
"the fully qualified NSK process name of this subagent."
   ::= {ztsa  3 }

ztsaProcessVersion OBJECT-TYPE
   SYNTAX      DisplayString (SIZE (0..255))
   ACCESS      read-only
   STATUS      mandatory
   DESCRIPTION
"the version of this subagent process object file. Format:
 T7862xxx_ddmmmyy_TCPIPSA"
   ::= {ztsa  4 }

ztsaProgramFile OBJECT-TYPE
   SYNTAX      DisplayString (SIZE (0..36))
   ACCESS      read-only
   STATUS      mandatory
   DESCRIPTION
"the TCP/IP subagent program file name"
   ::= {ztsa  5 }

ztsaProcessPriority  OBJECT-TYPE
   SYNTAX      INTEGER (0..199)
   ACCESS      read-write
   STATUS      mandatory
   DESCRIPTION
"the current NSK process priority of this subagent process."
   ::= {ztsa  6 }

ztsaProcessGroupID  OBJECT-TYPE
   SYNTAX      INTEGER (0..255)
   ACCESS      read-only
   STATUS      mandatory
   DESCRIPTION
"the NSK process group ID part of the PAID for this subagent process."
   ::= {ztsa  7 }

ztsaProcessUserID  OBJECT-TYPE
   SYNTAX      INTEGER (0..255)
   ACCESS      read-only
   STATUS      mandatory
   DESCRIPTION
"the NSK process user ID part of the PAID for this subagent process."
   ::= {ztsa  8 }

ztsaPrimaryCPU  OBJECT-TYPE
   SYNTAX      INTEGER (0..255)
   ACCESS      read-only
   STATUS      mandatory
   DESCRIPTION
"The CPU number of the primary process of this subagent"
   ::= {ztsa  9 }

ztsaPrimaryPIN  OBJECT-TYPE
   SYNTAX      INTEGER (0..255)
   ACCESS      read-only
   STATUS      mandatory
   DESCRIPTION
"The process number of the primary process of this subagent"
   ::= {ztsa  10 }

--
-- reflects -b startup parameter at startup
--
ztsaBackupCPU  OBJECT-TYPE
   SYNTAX      INTEGER (-1..255)
   ACCESS      read-write
   STATUS      mandatory
   DESCRIPTION
"The CPU the backup process will start in or is running in.
ztsaBackupState must be set to disabled(3) prior to setting this object"
   ::= {ztsa  11 }

ztsaBackupPIN  OBJECT-TYPE
   SYNTAX      INTEGER (-1..255)
   ACCESS      read-only
   STATUS      mandatory
   DESCRIPTION
"The process number of the backup process of this subagent. Its value
is -1 when the backup is not running"
   ::= {ztsa  12 }

ztsaBackupState OBJECT-TYPE
   SYNTAX      INTEGER {
                        connected   (1),
                        disconnected(2),
                        disabled    (3),
                        enabled     (4)
                       }
   ACCESS      read-write
   STATUS      mandatory
   DESCRIPTION
"The state of the backup process of this subagent. The settable values
for this object are disabled(3) and enabled(4). The connected(1) and
disconnected(2) states are set by the subagent to reflect the running
state of the backup resource"
   ::= {ztsa  13 }

ztsaSwitchToBackupNow  OBJECT-TYPE
   SYNTAX      INTEGER {
                        autoProcessPairControl(0),
                        forceBackupTakeover   (1)
                       }
   ACCESS      read-write
   STATUS      mandatory
   DESCRIPTION
"This object normally reads 0 (autoProcessPairControl) .  Setting this
object to 1 (forceBackupTakeover) causes the subagent to switch to its
backup process immediately after replying OK. Setting this object is
only permitted if the ztsaBackupState is connected(1)"
   ::= {ztsa  14 }

--
-- reflects -c startup parameter
--

ztsaEmsCollectorName  OBJECT-TYPE
   SYNTAX      DisplayString (SIZE (0..15))
   ACCESS      read-write
   STATUS      mandatory
   DESCRIPTION
"the process name of the EMS Collector the subagent should send
its EMS events to. ztsaEmsCollectorState must be set to disabled(3)
prior to setting this object"
   ::= {ztsa  15 }

ztsaEmsCollectorState  OBJECT-TYPE
   SYNTAX      INTEGER {
                        connected   (1),
                        disconnected(2),
                        disabled    (3),
                        enabled     (4)
                       }
   ACCESS      read-write
   STATUS      mandatory
   DESCRIPTION
"The state of the connection to the EMS Collector. The settable values
for this object are disabled(3) and enabled(4). The connected(1) and
disconnected(2) states are set by the subagent to reflect the running
state of the EMS collector interface"
   ::= {ztsa  16 }

--
-- reflects -k startup parameter
--

ztsaKeepAliveTimer  OBJECT-TYPE
   SYNTAX      INTEGER (0..32000)
   ACCESS      read-write
   STATUS      mandatory
   DESCRIPTION
"The number of seconds between attempts the subagent makes to connect
to an SNMP Agent, TCP/IP, or restart the backup process."
   ::= {ztsa  17 }

ztsaRefreshNow  OBJECT-TYPE
   SYNTAX      INTEGER {
                        autoDynamicRefresh (0),
                        forceDynamicRefresh(1)
                       }
   ACCESS      read-write
   STATUS      mandatory
   DESCRIPTION
"This object normally reads 0 (autoDynamicRefresh).  Setting this object to
1 (forceDynamicRefresh) causes the subagent to update the MIB tables and
generate traps (if needed). The object will return a value of 1 until the
refresh is complete."
   ::= {ztsa  18 }

--
-- reflects the -stats startup parameter
--

ztsaStatsCache  OBJECT-TYPE
   SYNTAX      INTEGER (0..32000)
   ACCESS      read-write
   STATUS      mandatory
   DESCRIPTION
"The cache update interval (in seconds) for SPI STATISTICS command
based objects. Value 0 disables cache timing such that updates occur
to objects derived from STATISTICS only when the ztsaRefreshNow object is set"
   ::= { ztsa  19 }

--
-- reflects the -status startup parameter
--

ztsaStatusCache OBJECT-TYPE
   SYNTAX      INTEGER (0..32000)
   ACCESS      read-write
   STATUS      mandatory
   DESCRIPTION
"The cache update interval (in seconds) for SPI STATUS command based objects.
Value 0 disables cache timing such that updates occur to objects derived
from STATUS only when the ztsaRefreshNow object is set. This value is also used
to control the interval for determining if a linkUp or linkDown trap should be
generated"
   ::= { ztsa  20 }

--
-- reflects the -info startup parameter
--

ztsaInfoCache OBJECT-TYPE
   SYNTAX      INTEGER (0..32000)
   ACCESS      read-write
   STATUS      mandatory
   DESCRIPTION
"The cache update interval for SPI INFO command based objects. Value 0 disables
cache timing such that updates occur to objects derived from INFO
only when the refreshNow object is set"
   ::= { ztsa  21 }

--
-- reflects the -t startup parameter
--

ztsaTcpIpProcess OBJECT-TYPE
   SYNTAX      DisplayString (SIZE (0..32))
   ACCESS      read-write
   STATUS      mandatory
   DESCRIPTION
"The TCP/IP process being monitored by the subagent. ztsaTcpIpState must be
set to disabled(3) prior to setting this object"
   ::= { ztsa  22 }

ztsaTcpIpState OBJECT-TYPE
   SYNTAX      INTEGER {
                        connected   (1),
                        disconnected(2),
                        disabled    (3),
                        enabled     (4)
                       }
   ACCESS      read-write
   STATUS      mandatory
   DESCRIPTION
"The state of the connection to the monitored TCP/IP process. The settable
values for this object are disabled(3) and enabled(4). The connected(1) and
disconnected(2) states are set by the subagent to reflect the running
state of the TCP/IP resource interface"
   ::= {ztsa 23 }

--
-- reflects the -rfc startup parameter
--
-- ztsaRfcStrict OBJECT-TYPE
--    SYNTAX     INTEGER {
--                        off(0),
--                        on(1)
--                       }
--    ACCESS     read-write
--    STATUS     mandatory
--    DESCRIPTION
-- "Convention control for unsupported MIB-II objects. Setting strict to on(1)
-- causes a noSuchName error to be returned for specific requests on
-- unsupported objects. If set to off(0) a 0 or null value is returned."
--    ::= { ztsa 24 }

--
-- reflects the -scp startup parameter
--
ztsaScpProcess OBJECT-TYPE
   SYNTAX      DisplayString (SIZE (0..32))
   ACCESS      read-only
   STATUS      mandatory
   DESCRIPTION
"the name of the SCP process used for SPI requests. Value is set
by the -scp startup parameter. Default is $ZNET"
   ::= { ztsa 25 }


ztsaTcpIpTable OBJECT-TYPE
   SYNTAX      SEQUENCE OF ZtsaTableEntry
   ACCESS      not-accessible
   STATUS      mandatory

   DESCRIPTION
               "This table holds information about the TCP/IP
                processes"
                ::= { ztsa 26 }

ztsaTableEntry OBJECT-TYPE
   SYNTAX      ZtsaTableEntry
   ACCESS      not-accessible
   STATUS      mandatory
   DESCRIPTION
               "This entry contains information related to TCP/IP
               processes"
   INDEX       { ztsaTcpIpName }
               ::= { ztsaTcpIpTable 1 }

ZtsaTableEntry ::=
         SEQUENCE{
               ztsaTcpIpName
                   DisplayString,
               ztsaTcpIpStatus
                   INTEGER
                   }

ztsaTcpIpName   OBJECT-TYPE
   SYNTAX       DisplayString
   ACCESS       read-only
   STATUS       mandatory
   DESCRIPTION
                "The TCP/IP process name monitored by the
                 TCP/IP SA"
                ::= { ztsaTableEntry 1 }

ztsaTcpIpStatus OBJECT-TYPE
   SYNTAX       INTEGER{
                         up(1),
                         down(2)
                       }
   ACCESS       read-only
   STATUS       mandatory
   DESCRIPTION
                "The status of TCP/IP process monitored by the
                 TCP/IP SA"
                ::= { ztsaTableEntry 2 }

ztsaSubnetTable   OBJECT-TYPE
   SYNTAX         SEQUENCE OF ZtsaSubnetEntry
   ACCESS         not-accessible
   STATUS         mandatory
   DESCRIPTION
                  "This table holds the subnets information
                   associated with the TCP/IP processes"
                  ::= { ztsa 27 }

ztsaSubnetEntry   OBJECT-TYPE
   SYNTAX         ZtsaSubnetEntry
   ACCESS         not-accessible
   STATUS         mandatory
   DESCRIPTION
                  "This entry contains information related
                  to the subnets  associated with the TCP/IP processes"
   INDEX          { ztsaTcpIpName, ztsaSubnetName }
                  ::= { ztsaSubnetTable 1 }

ZtsaSubnetEntry ::=
                  SEQUENCE {
                             ztsaSubnetName
                             DisplayString,
                             ztsaSubnetStatus
                             INTEGER,
                             ztsaSubnetAddr
                             IpAddress
                           }

ztsaSubnetName     OBJECT-TYPE
   SYNTAX          DisplayString
   ACCESS          read-only
   STATUS          mandatory
   DESCRIPTION
                   "The Subnet name corresponding to the
                   TCP/IP process monitored by TCP/IP SA"
                   ::= { ztsaSubnetEntry 1 }

ztsaSubnetStatus   OBJECT-TYPE
   SYNTAX          INTEGER{
                             aborting(0),
                             defined(1),
                             diagnosis(2),
                             started(3),
                             starting(4),
                             stopped(5),
                             stopping(6),
                             suspended(7),
                             unknown(8),
                             suspending(9)
                          }
   ACCESS          read-only
   STATUS          mandatory
   DESCRIPTION
                   "The status of the Subnet corresponding to the
                    TCP/IP process monitored by TCP/IP SA"
                   ::= { ztsaSubnetEntry 2 }

ztsaSubnetAddr     OBJECT-TYPE
   SYNTAX          IpAddress
   ACCESS          read-only
   STATUS          mandatory
   DESCRIPTION
                   "The IP address of the Subnet corresponding
                    to the TCP/IP process monitored by TCP/IP SA"
                   ::= { ztsaSubnetEntry 3 }


END
