-- Copyright(c) 1996, American Megatrends Inc. 
-- File: Ver1.06

RAID-Adapter-MIB DEFINITIONS ::= BEGIN
IMPORTS
    enterprises, Counter    FROM RFC1155-SMI
    DisplayString           FROM RFC1213-MIB
    OBJECT-TYPE             FROM RFC-1212;

perc OBJECT IDENTIFIER ::= { enterprises 16 }
percRAID OBJECT IDENTIFIER ::= { perc 1 }

percRaidMib OBJECT IDENTIFIER ::= { percRAID 1 }

-- Adapter Table Definition
adapterTable OBJECT-TYPE
	SYNTAX	SEQUENCE OF AdapterEntry
	ACCESS	not-accessible
	STATUS	mandatory
	DESCRIPTION
		"A List of Adapter Entries containing Information/Properties
		about the Adapters in the System."
	::= { percRaidMib 1 }

	adapterEntry OBJECT-TYPE
		SYNTAX	AdapterEntry
		ACCESS	not-accessible
		STATUS	mandatory
		DESCRIPTION
			"An entry in the Adapter Table. Each Entry corresponds 
			to one Adapter in the System."
		INDEX	{ adpAdapterNumber }
		::= { adapterTable 1 }

	AdapterEntry ::=
		SEQUENCE {
			adpAdapterNumber
				INTEGER,
			numLogicalDrives
				INTEGER,
			firmwareVersion
				DisplayString,
			biosVersion
				DisplayString,
			dramSizeInMB
				INTEGER,	
			chipSetType
				INTEGER,
			rebuildRateInPercent
				INTEGER,
			flushInterval
				INTEGER,
			maxConcurrentCmds
				INTEGER,
			spinupDelay
				INTEGER,
			spinupCount
				INTEGER,
			adpIOReadsPerSec
				INTEGER,
			adpIOWritesPerSec
				INTEGER,
			adpReadKBsPerSec
				INTEGER,
			adpWriteKBsPerSec
				INTEGER,
			adpReadFailuresPerSec
				INTEGER,
			adpWriteFailuresPerSec
				INTEGER,
			scanChannels
				INTEGER
		}

-- defines for each attribute in AdpaterEntry

adpAdapterNumber  OBJECT-TYPE
	SYNTAX	INTEGER
	ACCESS	read-only
	STATUS	mandatory
	DESCRIPTION
		"The Adapter Number for this Instance of Adapter Object. This
		Entry in the Table, contains Information about the Adapter 
		Number specified by this variable."
::= { adapterEntry 1 }

numLogicalDrives OBJECT-TYPE
	SYNTAX	INTEGER (0..8)
	ACCESS	read-only
	STATUS	mandatory
	DESCRIPTION
		"Number of Logical Drives Configured on this Adapter."
::= { adapterEntry 2 }

firmwareVersion  OBJECT-TYPE
	SYNTAX	DisplayString
	ACCESS	read-only
	STATUS	mandatory
	DESCRIPTION
		"The Firmware Version of the Firmware running on this Adapter."
::= { adapterEntry 3 }
				
biosVersion  OBJECT-TYPE
	SYNTAX	DisplayString
	ACCESS	read-only
	STATUS	mandatory
	DESCRIPTION
		"The Bios Version of the BIOS Present in the Flash ROM on 
		this Adapter."
::= { adapterEntry 4 }
				
dramSizeInMB  OBJECT-TYPE
	SYNTAX	INTEGER
	ACCESS	read-only
	STATUS	mandatory
	DESCRIPTION
		"Amount of DRAM in Mega Bytes present on this Adapter."
::= { adapterEntry 5 }

chipSetType  OBJECT-TYPE
	SYNTAX	INTEGER {
		intelneptuneormercury(225),
		triton(226),
		others(97)
		}
	ACCESS	read-only
	STATUS	mandatory
	DESCRIPTION
		"Motherboard Chipset Type for which the Adapter ASIC is 
		Configured."
::= { adapterEntry 6 }
				
rebuildRateInPercent  OBJECT-TYPE
	SYNTAX	INTEGER (0..100)
	ACCESS	read-write
	STATUS	mandatory
	DESCRIPTION
		"Rebuild Rate for this Adapter. This determines the Priority of 
		Rebuild/Check-Consistency/Reconstruct Operations versus the 
		Read-Write Operations."
::= { adapterEntry 7 }
				
flushInterval OBJECT-TYPE
	SYNTAX	INTEGER {
		twosec(2),
		foursec(4),
		sixsec(6),
		eightsec(8),
		tensec(10)
		}
	ACCESS	read-write
	STATUS	mandatory
	DESCRIPTION
		"Internal Cache Flush Interval for Logical Drives in WriteBack 
		Mode."
::= { adapterEntry 8 }
				
maxConcurrentCmds  OBJECT-TYPE
	SYNTAX	INTEGER
	ACCESS	read-only
	STATUS	mandatory
	DESCRIPTION
		"Maximum Concurrent Commands Supported by the Adapter."
::= { adapterEntry 9 }
				
spinupDelay  OBJECT-TYPE
	SYNTAX	INTEGER
	ACCESS	read-only
	STATUS	mandatory
	DESCRIPTION
		"This is the Spinup Delay for Spinning Up Physical Drives 
		at Firmware Initialization Time. The Physical Drives are 
		divided into Groups, each containing the number of drives 
		indicated by the spinupCount variable. spinupDelay 
		variable is the amount of delay used before the drives in 
		the next group are issued a SPINUP Command."

::= { adapterEntry 10 }

spinupCount  OBJECT-TYPE
	SYNTAX	INTEGER
	ACCESS	read-only
	STATUS	mandatory
	DESCRIPTION
		"This is the Spinup Count for Spinning up Physical Drives at 
		Firmware Initialization Time. The Physical Drives are divided 
		into Groups, each containing the number of drives indicated 
		by this variable. All the drives in a group are issued SPINUP 
		Command without any delay. Next group is given SPINUP Commands
		after a delay indicated by the spinupDelay variable."
::= { adapterEntry 11 }

adpIOReadsPerSec  OBJECT-TYPE
	SYNTAX	INTEGER
	ACCESS	read-only
	STATUS	mandatory
	DESCRIPTION
		"Number of IO Reads/sec statistics for this adapter."
::= { adapterEntry 12 }

adpIOWritesPerSec  OBJECT-TYPE
	SYNTAX	INTEGER
	ACCESS	read-only
	STATUS	mandatory
	DESCRIPTION
		"Number of IO Writes/sec statistics for this adapter."
::= { adapterEntry 13 }

adpReadKBsPerSec  OBJECT-TYPE
	SYNTAX	INTEGER
	ACCESS	read-only
	STATUS	mandatory
	DESCRIPTION
		"Amount of Data Transferred in KBs/sec due to READ Transfers."
::= { adapterEntry 14 }

adpWriteKBsPerSec  OBJECT-TYPE
	SYNTAX	INTEGER
	ACCESS	read-only
	STATUS	mandatory
	DESCRIPTION
		"Amount of Data Transferred in KBs/sec due to WRITE Transfers."
::= { adapterEntry 15 }

adpReadFailuresPerSec  OBJECT-TYPE
	SYNTAX	INTEGER
	ACCESS	read-only
	STATUS	mandatory
	DESCRIPTION
		"Number of Read-Failures/sec statistics for this adapter."
::= { adapterEntry 16 }

adpWriteFailuresPerSec  OBJECT-TYPE
	SYNTAX	INTEGER
	ACCESS	read-only
	STATUS	mandatory
	DESCRIPTION
		"Number of Write-Failures/sec statistics for this adapter."
::= { adapterEntry 17 }

scanChannels OBJECT-TYPE
	SYNTAX	INTEGER {
		scanover(1),
		startscan(2),
		scaninprog(3)
		}
	ACCESS	read-write
	STATUS	mandatory
	DESCRIPTION
		"Use this Variable to Discover the Non-Disk Devices attached
		to the Adapter. Set this Variable to startscan (an integer 
		value of 2) to start the Channel Scanning."
::= { adapterEntry 18 }


-- Logical Drive Table Definition
logicaldriveTable OBJECT-TYPE
	SYNTAX	SEQUENCE OF LogicaldriveEntry
	ACCESS	not-accessible
	STATUS	mandatory
	DESCRIPTION
		"A List of Logical Drive Entries containing Information/Properties
		about the Logical Drives Configured in the System."
	::= { percRaidMib 2 }

	logicaldriveEntry OBJECT-TYPE
		SYNTAX	LogicaldriveEntry
		ACCESS	not-accessible
		STATUS	mandatory
		DESCRIPTION
			"An Entry in the Logical Drive Table."
		INDEX		{ ldAdapterNumber, logicalDriveNumber }
		::= { logicaldriveTable 1 }

	LogicaldriveEntry ::=
		SEQUENCE {
			ldAdapterNumber
				INTEGER,
			logicalDriveNumber
				INTEGER,
			status
				INTEGER,
			sizeInMB
				INTEGER,
			raidLevel
				INTEGER,
			stripeSize
				INTEGER,
			readPolicy
				INTEGER,
			writePolicy
				INTEGER,
			cachePolicy
				INTEGER,
			enquiryString
				DisplayString,
			numberOfSpans
				INTEGER,
			numberOfStripes
				INTEGER,
			checkConsistencyOrInitializeProgress
				DisplayString,
			ldIOReadsPerSec
				INTEGER,
			ldIOWritesPerSec
				INTEGER,
			ldReadKBsPerSec
				INTEGER,
			ldWriteKBsPerSec
				INTEGER,
			ldReadFailuresPerSec
				INTEGER,
			ldWriteFailuresPerSec
				INTEGER
		}

-- defines for each attribute in LogicaldriveEntry

ldAdapterNumber  OBJECT-TYPE
	SYNTAX	INTEGER
	ACCESS	read-only
	STATUS	mandatory
	DESCRIPTION
		"The Adapter Number for this Instance of Adapter/LogicalDrive 
		object."
::= { logicaldriveEntry 1 }

logicalDriveNumber OBJECT-TYPE
	SYNTAX	INTEGER
	ACCESS	read-only
	STATUS	mandatory
	DESCRIPTION
		"Logical Drive Number for this Logical Drive Entry."
::= { logicaldriveEntry 2 }

status  OBJECT-TYPE
	SYNTAX	INTEGER {
		offline(0),
		degraded(1),
		optimal(2),
		initialize(3),
		checkconsistency(4)
		}
	ACCESS	read-write
	STATUS	mandatory
	DESCRIPTION
		"The Status of this Logical Drive."
::= { logicaldriveEntry 3 }
				
sizeInMB  OBJECT-TYPE
	SYNTAX	INTEGER
	ACCESS	read-only
	STATUS	mandatory
	DESCRIPTION
		"The Configured Size of this Logical Drive."
::= { logicaldriveEntry 4 }
				
raidLevel  OBJECT-TYPE
	SYNTAX	INTEGER {
		raid0(0),
		raid1(1),
		raid3(3),
		raid5(5)
		}
	ACCESS	read-only
	STATUS	mandatory
	DESCRIPTION
		"Configured Raid Level for this Logical Drive."
::= { logicaldriveEntry 5 }
				
stripeSize  OBJECT-TYPE
	SYNTAX	INTEGER {
		oneKB(1),
		twoKB(2),
		fourKB(4),
		eightKB(8),
		sixteenKB(16),
		thirtytwoKB(32),
		sixtyfourKB(64),
		onetwentyeightKB(128)
		}
	ACCESS	read-only
	STATUS	mandatory
	DESCRIPTION
		"Configured Stripe Size for this Logical Drive."
::= { logicaldriveEntry 6 }
				
readPolicy  OBJECT-TYPE
	SYNTAX	INTEGER {
		normal(0),
		readahead(1),
		adaptive(2)
		}
	ACCESS	read-write
	STATUS	mandatory
	DESCRIPTION
		"Configured Read Policy for this Logical Drive."
::= { logicaldriveEntry 7 }
				
writePolicy OBJECT-TYPE
	SYNTAX	INTEGER {
		writethru(0),
		writeback(1)
		}
	ACCESS	read-write
	STATUS	mandatory
	DESCRIPTION
		"Configured Write Policy for this Logical Drive."
::= { logicaldriveEntry 8 }
				
cachePolicy  OBJECT-TYPE
	SYNTAX	INTEGER {
		cachedio(0),
		directio(1)
		}
	ACCESS	read-write
	STATUS	mandatory
	DESCRIPTION
		"Configured Cache Policy for this Logical Drive."
::= { logicaldriveEntry 9 }
				
enquiryString  OBJECT-TYPE
	SYNTAX	DisplayString (SIZE(29..29))
	ACCESS	read-only
	STATUS	mandatory
	DESCRIPTION
		"SCSI Inquiry String for this Logical Drive."
::= { logicaldriveEntry 10 }
				
numberOfSpans  OBJECT-TYPE
	SYNTAX	INTEGER (1..4)
	ACCESS	read-only
	STATUS	mandatory
	DESCRIPTION
		"Number of Arrays across which this Logical Drive is Spanning."
::= { logicaldriveEntry 11 }

numberOfStripes  OBJECT-TYPE
	SYNTAX	INTEGER (1..8)
	ACCESS	read-only
	STATUS	mandatory
	DESCRIPTION
		"Configured Number of Stripes for this Logical Drive."
::= { logicaldriveEntry 12 }

checkConsistencyOrInitializeProgress  OBJECT-TYPE
	SYNTAX	DisplayString (SIZE(1..20))
	ACCESS	read-only
	STATUS	mandatory
	DESCRIPTION
		"Check Consistency or Initialize Progress for this Logical Drive
		if the Logical Drive Status is checkconsistencyinprogress or 
		initializeinprogress."
::= { logicaldriveEntry 13 }

ldIOReadsPerSec  OBJECT-TYPE
	SYNTAX	INTEGER
	ACCESS	read-only
	STATUS	mandatory
	DESCRIPTION
		"Number of IO Reads/sec Statistics for this Logical Drive."
::= { logicaldriveEntry 14 }

ldIOWritesPerSec  OBJECT-TYPE
	SYNTAX	INTEGER
	ACCESS	read-only
	STATUS	mandatory
	DESCRIPTION
		"Number of IO Writes/sec Statistics for this Logical Drive."
::= { logicaldriveEntry 15 }

ldReadKBsPerSec  OBJECT-TYPE
	SYNTAX	INTEGER
	ACCESS	read-only
	STATUS	mandatory
	DESCRIPTION
		"Amount of Data Transferred in KBs/sec due to READ Transfers."
::= { logicaldriveEntry 16 }

ldWriteKBsPerSec  OBJECT-TYPE
	SYNTAX	INTEGER
	ACCESS	read-only
	STATUS	mandatory
	DESCRIPTION
		"Amount of Data Transferred in KBs/sec due to WRITE Transfers."
::= { logicaldriveEntry 17 }

ldReadFailuresPerSec  OBJECT-TYPE
	SYNTAX	INTEGER
	ACCESS	read-only
	STATUS	mandatory
	DESCRIPTION
		"Number of Read-Failures/sec Statistics for this Logical Drive."
::= { logicaldriveEntry 18 }

ldWriteFailuresPerSec  OBJECT-TYPE
	SYNTAX	INTEGER
	ACCESS	read-only
	STATUS	mandatory
	DESCRIPTION
		"Number of Write-Failures/sec Statistics for this Logical Drive."
::= { logicaldriveEntry 19 }

-- Physical Drive Table Definition
physicaldriveTable OBJECT-TYPE
	SYNTAX	SEQUENCE OF PhysicaldriveEntry
	ACCESS	not-accessible
	STATUS	mandatory
	DESCRIPTION
		"A List of Physical Device Entries containing Information
		about the Physical Devices in the System."
	::= { percRaidMib 3 }

	physicaldriveEntry OBJECT-TYPE
		SYNTAX	PhysicaldriveEntry
		ACCESS	not-accessible
		STATUS	mandatory
		DESCRIPTION
			"An Entry in the Physical Drive Table."
		INDEX	{ physAdapterNumber, physChannel, targetID  }
		::= { physicaldriveTable 1 }

	PhysicaldriveEntry ::=
		SEQUENCE {
			physAdapterNumber
				INTEGER,
			physChannel
				INTEGER,
			targetID
				INTEGER,
			state
				INTEGER,
			arrayPosition
				DisplayString,
			sizeMB
				INTEGER,
			deviceType
				INTEGER,
			inquiryString
				DisplayString,
			scsiLevel
				INTEGER,
			syncNegotiation
				INTEGER,
			qtags
				INTEGER,
			rebuildProgress
				DisplayString,
			mediumErrors
				INTEGER,
			otherErrors
				INTEGER
		}

-- defines for each attribute in PhysicaldriveEntry

physAdapterNumber  OBJECT-TYPE
	SYNTAX	INTEGER
	ACCESS	read-only
	STATUS	mandatory
	DESCRIPTION
		"The Adapter Number for this Instance of Adapter/Physical-Drive 
		Instance."
::= { physicaldriveEntry 1 }

physChannel OBJECT-TYPE
	SYNTAX	INTEGER
	ACCESS	read-only
	STATUS	mandatory
	DESCRIPTION
		"Channel Number at Which this Physical Drive is Present."
::= { physicaldriveEntry 2 }

targetID OBJECT-TYPE
	SYNTAX	INTEGER(0..15)
	ACCESS	read-only
	STATUS	mandatory
	DESCRIPTION
		"SCSI Target ID at Which This Physical Drive is Present."
::= { physicaldriveEntry 3 }
				
state OBJECT-TYPE
	SYNTAX	INTEGER {
		ready(1),
		online(3),
		failed(4),
		rebuild(5),
		hotspare(6),
		nondisk(20)
		}
	ACCESS	read-write
	STATUS	mandatory
	DESCRIPTION
		"Current State of this Physical Drive."
::= { physicaldriveEntry 4 }

arrayPosition OBJECT-TYPE
	SYNTAX 	DisplayString (SIZE(4..20))
	ACCESS	read-only
	STATUS	mandatory
	DESCRIPTION
		"Array is a group of Physical Drives used to Configure Logical 
		Drives. This String Variable has values of the type Ai-j.
		Example: A1-2 implies that this drive is 2nd member of Array-1."
::= { physicaldriveEntry 5 }

sizeMB  OBJECT-TYPE
	SYNTAX	INTEGER
	ACCESS	read-only
	STATUS	mandatory
	DESCRIPTION
		"Actual Size of this Physical Drive."
::= { physicaldriveEntry 6 }
				
deviceType  OBJECT-TYPE
	SYNTAX	INTEGER {
		disk(0),
		tape(1),
		printer(2),
		processor(3),
		worm(4),
		cdrom(5),
		scanner(6),
		optical(7),
		changer(8),
		communication(9),
		asynchronouslow(10),
		asunchronoushigh(11),
		reservedlow(12)
		}
	ACCESS	read-only
	STATUS	mandatory
	DESCRIPTION
		"Device Type of this Physical Drive."
::= { physicaldriveEntry 7 }
				
inquiryString  OBJECT-TYPE
	SYNTAX	DisplayString (SIZE(29..29))
	ACCESS	read-only
	STATUS	mandatory
	DESCRIPTION
		"SCSI Inquiry String for this Device."
::= { physicaldriveEntry 8 }
				
scsiLevel OBJECT-TYPE
	SYNTAX	INTEGER {
		scsi1(1),
		scsi2(2)
		}
	ACCESS	read-only
	STATUS	mandatory
	DESCRIPTION
		"ANSI SCSI Level Conformance of this Device."
::= { physicaldriveEntry 9 }
				
syncNegotiation  OBJECT-TYPE
	SYNTAX	INTEGER {
		enable(1),
		disable(2)
		}
	ACCESS	read-only
	STATUS	mandatory
	DESCRIPTION
		"This indicates whether Firmware is Enabled or Disabled to 
		perform the Synchronous Negotiation for this Device."
::= { physicaldriveEntry 10 }

qtags  OBJECT-TYPE
	SYNTAX	INTEGER {
		one(1),
		two(2),
		three(3),
		four(4),
		enhancedqtagscheduling(5)
		}
	ACCESS	read-only
	STATUS	mandatory
	DESCRIPTION
		"This indicates the Maximum Number of Concurrent Commands
		Firmware Issues to this Drive."
::= { physicaldriveEntry 11 }

rebuildProgress  OBJECT-TYPE
	SYNTAX	DisplayString (SIZE(1..25))
	ACCESS	read-only
	STATUS	mandatory
	DESCRIPTION
		"Rebuild Progress for this Physical Drive if the Physical 
		Drive State is Rebuild."
::= { physicaldriveEntry 12 }

mediumErrors  OBJECT-TYPE
	SYNTAX	INTEGER
	ACCESS	read-only
	STATUS	mandatory
	DESCRIPTION
		"Medium Errors Occurred on this Drive Since it was Configured."
::= { physicaldriveEntry 13 }

otherErrors  OBJECT-TYPE
	SYNTAX	INTEGER
	ACCESS	read-only
	STATUS	mandatory
	DESCRIPTION
		"Other Errors Occurred on this Drive Since it was Configured."
::= { physicaldriveEntry 14 }


-- Channel Table Definition
channelTable OBJECT-TYPE
	SYNTAX	SEQUENCE OF ChannelEntry
	ACCESS	not-accessible
	STATUS	mandatory
	DESCRIPTION
		"A List of Channel Entries containing Information/Properties
		about the Channels on the Adapter."
	::= { percRaidMib 4 }

	channelEntry OBJECT-TYPE
		SYNTAX	ChannelEntry
		ACCESS	not-accessible
		STATUS	mandatory
		DESCRIPTION
			"An Entry in the channel table."
		INDEX	{ chanAdapterNumber, channel }
		::= { channelTable 1 }

	ChannelEntry ::=
		SEQUENCE {
			chanAdapterNumber
				INTEGER,
			channel
				INTEGER,
			terminations
				INTEGER,
			channelStatus
				INTEGER
		}

-- defines for each attribute in ChannelEntry

chanAdapterNumber  OBJECT-TYPE
	SYNTAX	INTEGER
	ACCESS	read-only
	STATUS	mandatory
	DESCRIPTION
		"The Adapter Number for this Instance of Adapter/Channel Instance."
::= { channelEntry 1 }

channel OBJECT-TYPE
	SYNTAX	INTEGER
	ACCESS	read-only
	STATUS	mandatory
	DESCRIPTION
		"Channel Number for this Channel."
::= { channelEntry 2 }

terminations OBJECT-TYPE
	SYNTAX	INTEGER {
		disabled(0),
		higher8bits(1),
		wideterminations(2)
		}
	ACCESS	read-only
	STATUS	mandatory
	DESCRIPTION
		"Current Terminations Effective on this Channel"
::= { channelEntry 3 }
				
channelStatus OBJECT-TYPE
	SYNTAX	INTEGER {
		quiet(1),
		active(2)
		}
	ACCESS	read-only
	STATUS	mandatory
	DESCRIPTION
		"Current Activity Status (QUIET/ACTIVE) for this Channel."
::= { channelEntry 4 }

ioReadsPerSec  OBJECT-TYPE
	SYNTAX	INTEGER
	ACCESS	read-only
	STATUS	mandatory
	DESCRIPTION
		"The Total IO-Reads/Sec Statistics on all Adapters."
::= { percRaidMib 9 }


-- Scalar MIB Variables
ioWritesPerSec  OBJECT-TYPE
	SYNTAX	INTEGER
	ACCESS	read-only
	STATUS	mandatory
	DESCRIPTION
		"The Total IO-Writes/Sec Statistics on all Adapters."
::= { percRaidMib 10 }

readKBsPerSec  OBJECT-TYPE
	SYNTAX	INTEGER
	ACCESS	read-only
	STATUS	mandatory
	DESCRIPTION
		"The Total Read KBs Per Second Statistics on all Adapters."
::= { percRaidMib 11 }

writeKBsPerSec  OBJECT-TYPE
	SYNTAX	INTEGER
	ACCESS	read-only
	STATUS	mandatory
	DESCRIPTION
		"The Total Write KBs Per Second Statistics on all Adapters."
::= { percRaidMib 12 }

readFailuresPerSec  OBJECT-TYPE
	SYNTAX	INTEGER
	ACCESS	read-only
	STATUS	mandatory
	DESCRIPTION
		"The Total Read Failures Per Second Statistics on all Adapters."
::= { percRaidMib 13 }

writeFailuresPerSec  OBJECT-TYPE
	SYNTAX	INTEGER
	ACCESS	read-only
	STATUS	mandatory
	DESCRIPTION
		"The Total Write Failures Per Second Statistics on all Adapters."
::= { percRaidMib 14 }

-- Following are the Objects defined for Traps

raidTraps OBJECT IDENTIFIER ::= { percRaidMib 200 }

rtAdapterNumber  OBJECT-TYPE
	SYNTAX	INTEGER
	ACCESS	read-only
	STATUS	mandatory
	DESCRIPTION
		"Adapter Number for which Trap is generated."
::= { raidTraps 1001 }

rtLogicalDriveNumber  OBJECT-TYPE
	SYNTAX	INTEGER
	ACCESS	read-only
	STATUS	mandatory
	DESCRIPTION
		"Logical Drive Number for which Trap is generated."
::= { raidTraps 1002 }

rtChannelNumber  OBJECT-TYPE
	SYNTAX	INTEGER
	ACCESS	read-only
	STATUS	mandatory
	DESCRIPTION
		"Channel Number on the Adapter for which Trap is Generated."
::= { raidTraps 1003 }

rtTargetID  OBJECT-TYPE
	SYNTAX	INTEGER
	ACCESS	read-only
	STATUS	mandatory
	DESCRIPTION
		"Device ID of the Physical Drive for which Trap is Generated."
::= { raidTraps 1004 }

rtOldDriveState  OBJECT-TYPE
	SYNTAX	DisplayString
	ACCESS	read-only
	STATUS	mandatory
	DESCRIPTION
		"Old State of Logical/Physical Drive, when a State Change Trap 
		is Generated."
::= { raidTraps 1005 }

rtNewDriveState  OBJECT-TYPE
	SYNTAX	DisplayString
	ACCESS	read-only
	STATUS	mandatory
	DESCRIPTION
		"New State of Logical/Physical Drive, when a State Change Trap 
		is Generated."
::= { raidTraps 1006 }

rtSenseKey  OBJECT-TYPE
	SYNTAX	INTEGER
	ACCESS	read-only
	STATUS	mandatory
	DESCRIPTION
		"Check Condition Sense-Key reported by Physical Drive for which 
		Trap is Generated."
::= { raidTraps 1007 }

rtASC  OBJECT-TYPE
	SYNTAX	INTEGER
	ACCESS	read-only
	STATUS	mandatory
	DESCRIPTION
		"Check Condition Additional Sense Code (ASC) reported by Physical 
		Drive for which Trap is Generated."
::= { raidTraps 1008 }

rtASCQ  OBJECT-TYPE
	SYNTAX	INTEGER
	ACCESS	read-only
	STATUS	mandatory
	DESCRIPTION
		"Check Condition Additional Sense Code Qualifier (ASCQ) reported by 
		Physical Drive for which Trap is Generated."
::= { raidTraps 1009 }

rtDriveVendor  OBJECT-TYPE
	SYNTAX	DisplayString
	ACCESS	read-only
	STATUS	mandatory
	DESCRIPTION
		"Vendor Identification String from the SCSI Inquiry Data for the
		Drive."
::= { raidTraps 1010 }

-- Following are the trap definitions, which use variables defined
-- within the object percRaidMib.
rtConfigUpdated TRAP-TYPE
	ENTERPRISE raidTraps
	VARIABLES { rtAdapterNumber }
	DESCRIPTION
		"Adapter-%d: A New Configuration has been written."
	--#TYPE "RAID Trap: Configuration Updated"
	--#SUMMARY "Host Adapter-%d: A New Configuration has been written."
	--#ARGUMENTS { 0 }
	--#SEVERITY INFORMATIONAL
	--#STATE OPERATIONAL
	::= 9001

rtPhysicalDriveStateChange TRAP-TYPE
	ENTERPRISE raidTraps
	VARIABLES 
		{ 
		rtAdapterNumber,
		rtChannelNumber,
		rtTargetID,
		rtOldDriveState,
		rtNewDriveState
		}
	DESCRIPTION
		"Adapter-%d, Channel-%d, Target-%d: Drive State Changed from %s to %s."
	--#TYPE "RAID Trap: Physical Drive State Change"
	--#SUMMARY "Adapter-%d, Channel-%d, Target-%d: Drive State Changed from %s to %s."
	--#ARGUMENTS { 0, 1, 2, 3, 4 }
	--#SEVERITY INFORMATIONAL
	--#STATE OPERATIONAL
	::= 9002

rtLogicalDriveStateChange TRAP-TYPE
	ENTERPRISE raidTraps
	VARIABLES 
		{ 
		rtAdapterNumber,
		rtLogicalDriveNumber,
		rtOldDriveState,
		rtNewDriveState
		}
	DESCRIPTION
		"Adapter-%d, Logical Drive-%d: State Changed from %s to %s."
	--#TYPE "RAID Trap: Logical Drive State Change"
	--#SUMMARY "Adapter-%d, Logical Drive-%d: State Changed from %s to %s."
	--#ARGUMENTS { 0, 1, 2, 3 }
	--#SEVERITY INFORMATIONAL
	--#STATE OPERATIONAL
	::= 9003

rtInitializeStarted TRAP-TYPE
	ENTERPRISE raidTraps
	VARIABLES 
		{ 
		rtAdapterNumber,
		rtLogicalDriveNumber
		}
	DESCRIPTION
		"Adapter-%d, Logical Drive-%d: Initialization Started."
	--#TYPE "RAID Trap: Initialize Started"
	--#SUMMARY "Adapter-%d, Logical Drive-%d: Initialization Started."
	--#ARGUMENTS { 0, 1 }
	--#SEVERITY INFORMATIONAL
	--#STATE OPERATIONAL
	::= 9004

rtInitializeCompleted TRAP-TYPE
	ENTERPRISE raidTraps
	VARIABLES 
		{ 
		rtAdapterNumber,
		rtLogicalDriveNumber
		}
	DESCRIPTION
		"Adapter-%d, Logical Drive-%d: Initialization Completed Successfully."
	--#TYPE "RAID Trap: Initialize Completed"
	--#SUMMARY "Adapter-%d, Logical Drive-%d: Initialization Completed Successfully."
	--#ARGUMENTS { 0, 1 }
	--#SEVERITY INFORMATIONAL
	--#STATE OPERATIONAL
	::= 9005

rtInitializeAborted TRAP-TYPE
	ENTERPRISE raidTraps
	VARIABLES 
		{ 
		rtAdapterNumber,
		rtLogicalDriveNumber
		}
	DESCRIPTION
		"Adapter-%d, Logical Drive-%d: Initialization Aborted by User."
	--#TYPE "RAID Trap: Initialize Aborted"
	--#SUMMARY "Adapter-%d, Logical Drive-%d: Initialization Aborted by User."
	--#ARGUMENTS { 0, 1 }
	--#SEVERITY INFORMATIONAL
	--#STATE OPERATIONAL
	::= 9006

rtInitializeFailed TRAP-TYPE
	ENTERPRISE raidTraps
	VARIABLES 
		{ 
		rtAdapterNumber,
		rtLogicalDriveNumber
		}
	DESCRIPTION
		"Adapter-%d, Logical Drive-%d: Initialization Failed."
	--#TYPE "RAID Trap: Initialize Failed"
	--#SUMMARY "Adapter-%d, Logical Drive-%d: Initialization Failed."
	--#ARGUMENTS { 0, 1 }
	--#SEVERITY INFORMATIONAL
	--#STATE OPERATIONAL
	::= 9007

rtCheckConsistencyStarted TRAP-TYPE
	ENTERPRISE raidTraps
	VARIABLES 
		{ 
		rtAdapterNumber,
		rtLogicalDriveNumber
		}
	DESCRIPTION
		"Adapter-%d, Logical Drive-%d: Check Consistency Started."
	--#TYPE "RAID Trap: Check Consistency Started"
	--#SUMMARY "Adapter-%d, Logical Drive-%d: Check Consistency Started."
	--#ARGUMENTS { 0, 1 }
	--#SEVERITY INFORMATIONAL
	--#STATE OPERATIONAL
	::= 9008

rtCheckConsistencyCompleted TRAP-TYPE
	ENTERPRISE raidTraps
	VARIABLES 
		{ 
		rtAdapterNumber,
		rtLogicalDriveNumber
		}
	DESCRIPTION
		"Adapter-%d, Logical Drive-%d: Check Consistency Completed. No 
		Inconsistencies Found."
	--#TYPE "RAID Trap: Check Consistency Completed"
	--#SUMMARY "Adapter-%d, Logical Drive-%d: Check Consistency Completed. No"
	--#SUMMARY "Inconsistencies Found."
	--#ARGUMENTS { 0, 1 }
	--#SEVERITY INFORMATIONAL
	--#STATE OPERATIONAL
	::= 9009

rtCheckConsistencyAborted TRAP-TYPE
	ENTERPRISE raidTraps
	VARIABLES 
		{ 
		rtAdapterNumber,
		rtLogicalDriveNumber
		}
	DESCRIPTION
		"Adapter-%d, Logical Drive-%d: Check Consistency Aborted by User."
	--#TYPE "RAID Trap: Check Consistency Aborted"
	--#SUMMARY "Adapter-%d, Logical Drive-%d: Check Consistency Aborted by User."
	--#ARGUMENTS { 0, 1 }
	--#SEVERITY INFORMATIONAL
	--#STATE OPERATIONAL
	::= 9010

rtConsistencyCorrected TRAP-TYPE
	ENTERPRISE raidTraps
	VARIABLES 
		{ 
		rtAdapterNumber,
		rtLogicalDriveNumber
		}
	DESCRIPTION
		"Adapter-%d, Logical Drive-%d: Check Consistency Operation Completed. 
		Inconsistencies have been Cured." 
	--#TYPE "RAID Trap: Check Consistency Corrected"
	--#SUMMARY "Adapter-%d, Logical Drive-%d: Check Consistency Operation"
	--#SUMMARY "Completed. Inconsistencies have been Cured." 
	--#ARGUMENTS { 0, 1 }
	--#SEVERITY INFORMATIONAL
	--#STATE OPERATIONAL
	::= 9011

rtCheckConsistencyFailed TRAP-TYPE
	ENTERPRISE raidTraps
	VARIABLES 
		{ 
		rtAdapterNumber,
		rtLogicalDriveNumber
		}
	DESCRIPTION
		"Adapter-%d, Logical Drive-%d: Check Consistency Failed."
	--#TYPE "RAID Trap: Check Consistency Failed"
	--#SUMMARY "Adapter-%d, Logical Drive-%d: Check Consistency Failed."
	--#ARGUMENTS { 0, 1 }
	--#SEVERITY INFORMATIONAL
	--#STATE OPERATIONAL
	::= 9012

rtReconstructionStarted TRAP-TYPE
	ENTERPRISE raidTraps
	VARIABLES 
		{ 
		rtAdapterNumber,
		rtLogicalDriveNumber
		}
	DESCRIPTION
		"Adapter-%d, Logical Drive-%d: Reconstruction Started."
	--#TYPE "RAID Trap: Reconstruction Started"
	--#SUMMARY "Adapter-%d, Logical Drive-%d: Reconstruction Started."
	--#ARGUMENTS { 0, 1 }
	--#SEVERITY INFORMATIONAL
	--#STATE OPERATIONAL
	::= 9013

rtReconstructionCompleted TRAP-TYPE
	ENTERPRISE raidTraps
	VARIABLES 
		{ 
		rtAdapterNumber,
		rtLogicalDriveNumber
		}
	DESCRIPTION
		"Adapter-%d, Logical Drive-%d: Reconstruction Completed Successfully."
	--#TYPE "RAID Trap: Reconstruction Completed"
	--#SUMMARY "Adapter-%d, Logical Drive-%d: Reconstruction Completed Successfully."
	--#ARGUMENTS { 0, 1 }
	--#SEVERITY INFORMATIONAL
	--#STATE OPERATIONAL
	::= 9014

rtReconstructionFailed TRAP-TYPE
	ENTERPRISE raidTraps
	VARIABLES 
		{ 
		rtAdapterNumber,
		rtLogicalDriveNumber
		}
	DESCRIPTION
		"Adapter-%d, Logical Drive-%d: Reconstruction Failed."
	--#TYPE "RAID Trap: Reconstruction Failed"
	--#SUMMARY "Adapter-%d, Logical Drive-%d: Reconstruction Failed."
	--#ARGUMENTS { 0, 1 }
	--#SEVERITY INFORMATIONAL
	--#STATE OPERATIONAL
	::= 9015

rtPredictiveFailuresExceeded TRAP-TYPE
	ENTERPRISE raidTraps
	VARIABLES 
		{ 
		rtAdapterNumber,
		rtChannelNumber,
		rtTargetID,
		rtDriveVendor,
		rtSenseKey,
		rtASC,
		rtASCQ
		}
	DESCRIPTION
		"Adapter-%d, Channel-%d, Target-%d: Reported Predictive Failure.
		Drive Identification String = %s
		Sense Key = 0x%x, ASC = 0x%x, ASCQ = 0x%x."
	--#TYPE "RAID Trap: Physical Drive Failure Prediction Threshold Exceeded"
	--#SUMMARY "Adapter-%d, Channel-%d, Target-%d: Reported Predictive 
	--#SUMMARY "Failure. (Failure Threshold Exceeded)"
	--#SUMMARY "Drive Identification String = %s"
	--#SUMMARY "Sense Key = 0x%x, ASC = 0x%x, ASCQ = 0x%x."
	--#ARGUMENTS { 0, 1, 2, 3, 4, 5, 6 }
	--#SEVERITY INFORMATIONAL
	--#STATE OPERATIONAL
	::= 9016

rtPredictiveFailuresFalse TRAP-TYPE
	ENTERPRISE raidTraps
	VARIABLES 
		{ 
		rtAdapterNumber,
		rtChannelNumber,
		rtTargetID,
		rtDriveVendor,
		rtSenseKey,
		rtASC,
		rtASCQ
		}
	DESCRIPTION
		"Adapter-%d, Channel-%d, Target-%d: Reported Failure Prediction
		Threshold Exceeded [FALSE].
		Drive Identification String = %s
		Sense Key = 0x%x, ASC = 0x%x, ASCQ = 0x%x."
	--#TYPE "RAID Trap: Physical Drive Predictive Failures [FALSE]"
	--#SUMMARY "Adapter-%d, Channel-%d, Target-%d: Reported Predictive 
	--#SUMMARY "Failure. (Failure Prediction Threshold Exceeded [FALSE])"
	--#SUMMARY "Drive Identification String = %s"
	--#SUMMARY "Sense Key = 0x%x, ASC = 0x%x, ASCQ = 0x%x."
	--#ARGUMENTS { 0, 1, 2, 3, 4, 5, 6 }
	--#SEVERITY INFORMATIONAL
	--#STATE OPERATIONAL
	::= 9017

rtCheckConditionStatus TRAP-TYPE
	ENTERPRISE raidTraps
	VARIABLES 
		{ 
		rtAdapterNumber,
		rtChannelNumber,
		rtTargetID,
		rtSenseKey,
		rtASC,
		rtASCQ
		}
	DESCRIPTION
		"Adapter-%d, Channel-%d, Target-%d: Command Completed with 
		Sense_Key-0x%x ASC-0x%x ASCQ-0x%x."
	--#TYPE "RAID Trap: Physical Drive Check Conditions"
	--#SUMMARY "Adapter-%d, Channel-%d, Target-%d: Command Completed with"
	--#SUMMARY "Sense_Key-0x%x ASC-0x%x ASCQ-0x%x."
	--#ARGUMENTS { 0, 1, 2, 3, 4, 5 }
	--#SEVERITY INFORMATIONAL
	--#STATE OPERATIONAL
	::= 9018

rtNewDriveInserted TRAP-TYPE
	ENTERPRISE raidTraps
	VARIABLES 
		{ 
		rtAdapterNumber,
		rtChannelNumber,
		rtTargetID
		}
	DESCRIPTION
		"Adapter-%d, Channel-%d, Target-%d: New Device Inserted."
	--#TYPE "RAID Trap: New Drive Inserted"
	--#SUMMARY "Adapter-%d, Channel-%d, Target-%d: New Device Inserted."
	--#ARGUMENTS { 0, 1, 2 }
	--#SEVERITY INFORMATIONAL
	--#STATE OPERATIONAL
	::= 9019

rtBatteryMissing TRAP-TYPE
	ENTERPRISE raidTraps
	VARIABLES 
		{ rtAdapterNumber }
	DESCRIPTION
		"Adapter-%d: Battery Module is missing."
	--#TYPE "RAID Trap: Battery Missing"
	--#SUMMARY "Adapter-%d: Battery Module is missing."
	--#ARGUMENTS { 0 }
	--#SEVERITY INFORMATIONAL
	--#STATE OPERATIONAL
	::= 9020

rtBatteryVolatageLow TRAP-TYPE
	ENTERPRISE raidTraps
	VARIABLES 
		{ rtAdapterNumber }
	DESCRIPTION
		"Adapter-%d: Battery Module Voltage is Low."
	--#TYPE "RAID Trap: Battery Voltage Low"
	--#SUMMARY "Adapter-%d: Battery Module Voltage is Low."
	--#ARGUMENTS { 0 }
	--#SEVERITY INFORMATIONAL
	--#STATE OPERATIONAL
	::= 9021

rtBatteryTemperatureHigh TRAP-TYPE
	ENTERPRISE raidTraps
	VARIABLES 
		{ rtAdapterNumber }
	DESCRIPTION
		"Adapter-%d: Battery Module Temperature Exceeded Danger Threshold."
	--#TYPE "RAID Trap: Battery Temperature High"
	--#SUMMARY "Adapter-%d: Battery Module Temperature Exceeded Danger Threshold."
	--#ARGUMENTS { 0 }
	--#SEVERITY INFORMATIONAL
	--#STATE OPERATIONAL
	::= 9022

-- This marks end of the MIB definitions
END
