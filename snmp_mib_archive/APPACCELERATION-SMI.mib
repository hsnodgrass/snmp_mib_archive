-- *****************************************************************
-- APPACCELERATION-SMI.txt: Citrix Systems Application Acceleration
--                          Structure of Management Information
--
--
-- Copyright (c) 2004-2009 by Citrix Systems, Inc.
-- All rights reserved.
--
-- *****************************************************************
--

APPACCELERATION-SMI DEFINITIONS ::= BEGIN

IMPORTS
    MODULE-IDENTITY,
    OBJECT-IDENTITY,
    citrix
        FROM CITRIX-COMMON-MIB;

appAcceleration MODULE-IDENTITY
    LAST-UPDATED "200905110000Z"
    ORGANIZATION "www.citrix.com"
    CONTACT-INFO
            "       Citrix Systems, Inc.

            Postal: 851 West Cypress Creek Road
                    Fort Lauderdale, Florida  33309
                    United States"

    DESCRIPTION
        "The Structure of Management Information for the
        Citrix Systems Application Acceleration."
    ::= { citrix 30 }


appAccelerationProducts OBJECT-IDENTITY
    STATUS  current
    DESCRIPTION
        "appAccelerationProducts is the root OBJECT IDENTIFIER from
        which sysObjectID values are assigned. Actual values
        are defined in APPACCELERATION-PRODUCTS-MIB."
    ::= { appAcceleration 1 }

appAccelerationAgentCapability OBJECT-IDENTITY
    STATUS  current
    DESCRIPTION
        "appAccelerationAgentCapability provides a root object identifier
        from which AGENT-CAPABILITIES values may be assigned."
    ::= { appAcceleration 2 }

appAccelerationModules OBJECT-IDENTITY
    STATUS  current
    DESCRIPTION
        "appAccelerationModules provides a root object identifier from
        which MODULE-ENTITY values may be assigned."
    ::= { appAcceleration 3 }

appAccelerationMgmt OBJECT-IDENTITY
    STATUS  current
    DESCRIPTION
        "appAccelerationMgmt is the main subtree for management mibs."
    ::= { appAcceleration 4 }

appAccelerationNotifications OBJECT-IDENTITY
    STATUS  current
    DESCRIPTION
        "appAccelerationNotifications is the main subtree for agent notifications."
    ::= { appAcceleration 5 }

END
