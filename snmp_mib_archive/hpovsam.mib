--------------------------------------------------------------
--
-- The information in this MIB is subject to change without
-- notice and should not be construed as a commitment by 
-- Hewlett Packard.  Hewlett Packard assumes no responsibility
-- for the use or reliability of this software.
--
--------------------------------------------------------------
--
-- HP OpenView Storarge Areas Manager
-- Management Information Base description
-- SMI format
--
--------------------------------------------------------------
--
-- Author
-- Evan H. Burns
-- Modified by Paulene M. Purdy
-- Modified by Greg Stephens & Dave Kasberg
-- Modified by Eddie Houston
--------------------------------------------------------------
--
-- 01-13-98 Created Original Module
-- 08/11/2000 Modified  
-- 08/15/2000 Modified modification :)
-- 09/24/2002 Added NNM event config fields
-- 06/11/2003 Converted to SMIv1
--------------------------------------------------------------

    HPOvSam-MIB-V1 DEFINITIONS ::= BEGIN

        IMPORTS
            OBJECT-TYPE
                FROM RFC-1212
            TRAP-TYPE
                FROM RFC-1215
            enterprises
                FROM RFC1155-SMI
            DisplayString
                FROM RFC1213-MIB;


--
-- Node definitions
    
        -- 1.3.6.1.4.1.11
        hp OBJECT IDENTIFIER ::= { enterprises 11 }

        -- 1.3.6.1.4.1.11.2
        nm OBJECT IDENTIFIER ::= { hp 2 }

        -- 1.3.6.1.4.1.11.2.27
        hpStorageAssistant OBJECT IDENTIFIER ::= { nm 27 }

        -- 1.3.6.1.4.1.11.2.27.3
        hpSanManager OBJECT IDENTIFIER ::= { hpStorageAssistant 3 }

        -- 1.3.6.1.4.1.11.2.27.3.0
        hpSanManagerTraps OBJECT IDENTIFIER ::= { hpSanManager 0 }

        -- 1.3.6.1.4.1.11.2.27.3.1
        hpSanManagerModules OBJECT IDENTIFIER ::= { hpSanManager 1 }

        -- 1.3.6.1.4.1.11.2.27.3.1.1
        hpSanManagerMibModule OBJECT IDENTIFIER ::= { hpSanManagerModules 1 }

        -- 1.3.6.1.4.1.11.2.27.3.1.1.1
        mibModuleEventVars OBJECT IDENTIFIER ::= { hpSanManagerMibModule 1 }

-- Trap-only variable
        -- 1.3.6.1.4.1.11.2.27.3.1.1.1.1
        severityLevel OBJECT-TYPE
            SYNTAX INTEGER
                {
                informational(1),
                warning(2),
                minor(3),
                major(4),
                critical(5)
                }
            ACCESS read-only
            STATUS mandatory
            DESCRIPTION
                "Severity level of the event being reported"
            ::= { mibModuleEventVars 1 }


-- Trap-only variable
        -- 1.3.6.1.4.1.11.2.27.3.1.1.1.2
        category OBJECT-TYPE
            SYNTAX DisplayString
            ACCESS read-only
            STATUS mandatory
            DESCRIPTION
                "Category of the event being reported"
            ::= { mibModuleEventVars 2 }


-- Trap-only variable
        -- 1.3.6.1.4.1.11.2.27.3.1.1.1.3
        id OBJECT-TYPE
            SYNTAX INTEGER 
            ACCESS read-only
            STATUS mandatory
            DESCRIPTION
                "ID number of the event within the given category"
            ::= { mibModuleEventVars 3 }

-- Trap-only variable
        -- 1.3.6.1.4.1.11.2.27.3.1.1.1.4
        msgString OBJECT-TYPE
            SYNTAX DisplayString
            ACCESS read-only
            STATUS mandatory
            DESCRIPTION
                "Message string associated with the event being reported."
            ::= { mibModuleEventVars 4 }


-- Trap-only variable
        -- 1.3.6.1.4.1.11.2.27.3.1.1.1.5
        contactName OBJECT-TYPE
            SYNTAX DisplayString
            ACCESS read-only
            STATUS mandatory
            DESCRIPTION
                "Name of the person to be notified of the
                 occurence of the event being reported."
            ::= { mibModuleEventVars 5 }

-- Trap-only variable
        -- 1.3.6.1.4.1.11.2.27.3.1.1.1.6
        contactEmail	OBJECT-TYPE
            SYNTAX DisplayString
            ACCESS read-only
            STATUS mandatory
            DESCRIPTION
                "Email address of the individual referenced by 
                 an instance of the contactName variable."
            ::= { mibModuleEventVars 6 }

-- Trap-only variable
        -- 1.3.6.1.4.1.11.2.27.3.1.1.1.7
        contactHomePhone OBJECT-TYPE
            SYNTAX DisplayString
            ACCESS read-only
            STATUS mandatory
            DESCRIPTION
                "Home telephone number of the individual
                 referenced by an instance of the contactName
                 variable."
            ::= { mibModuleEventVars 7 }

-- Trap-only variable
        -- 1.3.6.1.4.1.11.2.27.3.1.1.1.8
        contactWorkPhone OBJECT-TYPE
            SYNTAX DisplayString
            ACCESS read-only
            STATUS mandatory
            DESCRIPTION
                "Work telephone number of the individual
                 referenced by an instance of the contactName
                 variable."
            ::= { mibModuleEventVars 8 }

-- Trap-only variable
        -- 1.3.6.1.4.1.11.2.27.3.1.1.1.9
        contactPager OBJECT-TYPE
            SYNTAX DisplayString
            ACCESS read-only
            STATUS mandatory
            DESCRIPTION
                "Pager telephone number of the individual
                 referenced by an instance of the contactName
                 variable."
            ::= { mibModuleEventVars 9 }

-- Trap-only variable
        -- 1.3.6.1.4.1.11.2.27.3.1.1.1.10
        contactFax OBJECT-TYPE
            SYNTAX DisplayString
            ACCESS read-only
            STATUS mandatory
            DESCRIPTION
                "Fax telephone number of the individual
                 referenced by an instance of the contactName
                 variable."
            ::= { mibModuleEventVars 10 }

-- Trap-only variable
        -- 1.3.6.1.4.1.11.2.27.3.1.1.1.11
        sourceName OBJECT-TYPE
            SYNTAX DisplayString
            ACCESS read-only
            STATUS mandatory
            DESCRIPTION
                "Event source 'friendly' name"
            ::= { mibModuleEventVars 11 }

-- Trap-only variable
        -- 1.3.6.1.4.1.11.2.27.3.1.1.1.12
        uniqueId OBJECT-TYPE
            SYNTAX DisplayString
            ACCESS read-only
            STATUS mandatory
            DESCRIPTION
                "Unique identifier of device that is source of event"
            ::= { mibModuleEventVars 12 }

-- Trap-only variable
        -- 1.3.6.1.4.1.11.2.27.3.1.1.1.12
        vendorId OBJECT-TYPE
            SYNTAX DisplayString
            ACCESS read-only
            STATUS mandatory
            DESCRIPTION
                "Vendor identifier of device that is source of event"
            ::= { mibModuleEventVars 13 }

-- Trap-only variable
        -- 1.3.6.1.4.1.11.2.27.3.1.1.1.14
        prodId OBJECT-TYPE
            SYNTAX DisplayString
            ACCESS read-only
            STATUS mandatory
            DESCRIPTION
                "Product identifier of device that is source of event"
            ::= { mibModuleEventVars 14 }

-- Trap-only variable
        -- 1.3.6.1.4.1.11.2.27.3.1.1.1.15
        prodRev OBJECT-TYPE
            SYNTAX DisplayString
            ACCESS read-only
            STATUS mandatory
            DESCRIPTION
                "Product revision of device that is source of event"
            ::= { mibModuleEventVars 15 }

-- Trap-only variable
        -- 1.3.6.1.4.1.11.2.27.3.1.1.1.16
        serialNo OBJECT-TYPE
            SYNTAX DisplayString
            ACCESS read-only
            STATUS mandatory
            DESCRIPTION
                "Serial number of device that is source of event"
            ::= { mibModuleEventVars 16 }

-- Trap-only variable
        -- 1.3.6.1.4.1.11.2.27.3.1.1.1.17
        storageDmn OBJECT-TYPE
            SYNTAX DisplayString
            ACCESS read-only
            STATUS mandatory
            DESCRIPTION
                "Storage domain in which the device is located."
            ::= { mibModuleEventVars 17 }

    genericSanEvent TRAP-TYPE
        ENTERPRISE hpSanManager
        VARIABLES  { severityLevel, category, id,
                     msgString, contactName, contactEmail,
                     contactWorkPhone, contactHomePhone, 
                     contactPager, contactFax }
        DESCRIPTION
                        "A generic SAN event has occurred.  The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName"
     -- The following are attributes used by xnmloadmib for improved formatting
     --#TYPE "OV SAM SAN Event"
     --#SUMMARY "OV SAM SAN Event, Category/Id: %d/%d, Msg: %d  Severity: %d  Contact: %d"
     --#ARGUMENTS {1,2,3,0,4}
     --#SEVERITY CRITICAL
     --#GENERIC 6
     --#CATEGORY "Application Alert Events"
     --#SOURCE_ID "T"
        ::= 1

    sanDeviceEvent TRAP-TYPE
        ENTERPRISE hpSanManager
        VARIABLES  { severityLevel, category, id,
                     msgString, contactName, contactEmail,
                     contactWorkPhone, contactHomePhone,
                     contactPager, contactFax, sourceName, 
                     uniqueId, vendorId, prodId, prodRev, 
                     serialNo, storageDmn}
        DESCRIPTION
                        "A SAN Device Event has occurred.  The variables are:
                            severityLevel - the event severity level;
                            category - Category of the event being reported;
                            code - ID of the event in the given category;
                            msgString - the message string describing
                                the event;
                            contactName - the name of the individual
                                to be notified of the event;
                            contactEmail - the e-mail address of the
                                individual referred to in contactName;
                            contactWorkPhone - the work phone number
                                of the individual referred to in 
                                contactName;
                            contactHomePhone - the home phone number
                                of the individual referred to in 
                                contactName;
                            contactPager - the pager number of the 
                                individual referred to in contactName;
                            contactFax - the FAX number of the individual
                                 referred to in contactName;
                            sourceName - Event source 'friendly' name;
                            uniqueId - Unique identifier of device that 
                                is source of event;
                            vendorId - Vendor identifier of device that 
                                is source of event;
                            prodId - Product identifier of device that 
                                is source of event;
                            prodRev - Product revision of device that is 
                                source of event;
                            serialNo - Serial number of device that is
                                source of event
                            storageDom - Storage domain in which the device
                                is located"
     -- The following are attributes used by xnmloadmib for improved formatting
     --#TYPE "OV SAM Device Event"
     --#SUMMARY "OV SAM Device Event, Id: %d, Msg: %d  Severity: %d  Source: %d, %d, %d, %d  StorageDomain: %d Contact: %d"
     --#ARGUMENTS {2,3,0,10,11,12,13,16,4}
     --#SEVERITY CRITICAL
     --#GENERIC 6
     --#CATEGORY "Application Alert Events"
     --#SOURCE_ID "T"
        ::= 2

END
