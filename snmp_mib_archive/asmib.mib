ARCserve-Alarm-MIB DEFINITIONS ::= BEGIN

	IMPORTS
		enterprises    FROM RFC1155-SMI
		OBJECT-TYPE    FROM RFC-1212
		TRAP-TYPE      FROM RFC-1215;
		
		cheyenne            OBJECT IDENTIFIER ::= { enterprises 46 }
		arcServe            OBJECT IDENTIFIER ::= { cheyenne 877 }
                arcServeNLMRev      OBJECT IDENTIFIER ::= { arcServe 1 }

-- *************************************************************************
-- ARCserve (1.3.6.1.4.1.46.877)
-- **************************************************************************
arcServeNLMRevMajor OBJECT-TYPE
	SYNTAX INTEGER (0..65535)
	ACCESS read-only
	STATUS mandatory
	DESCRIPTION
		"The major revision level of the NLM (left of the decimal).
		Used for presence checking."
	::= { arcServeNLMRev 1 }

arcServeNLMRevMinor OBJECT-TYPE
	SYNTAX INTEGER (0..65535)
	ACCESS read-only
	STATUS mandatory
	DESCRIPTION
		"The minor revision level of the NLM (right of the decimal)."
	::= { arcServeNLMRev 2 }

arcServeParmsTrapEnable OBJECT-TYPE
	SYNTAX INTEGER (0..1)
	ACCESS read-write
	STATUS mandatory
	DESCRIPTION
		"Indicates whether agent should or should not send traps."
	::= { arcServe 2 }

arcServeParmsPollTime OBJECT-TYPE
	SYNTAX INTEGER (60..2592000)
	ACCESS read-write
	STATUS mandatory
	DESCRIPTION
		"Seconds between checking for traps."
	::= { arcServe 3 }

arcServeServerName OBJECT-TYPE
                SYNTAX OCTET STRING
                ACCESS read-only
                STATUS mandatory
                DESCRIPTION
                        "NetWare Server Which Generated Error."
                ::= { arcServe 4 }        
        
arcServetrapdesc   OBJECT-TYPE
                SYNTAX OCTET STRING
                ACCESS read-only
                STATUS optional
                DESCRIPTION
                        "A description of a specific Cheyenne trap."
                ::= { arcServe 5 }        
        
-- *************************************************************************
-- traps
-- **************************************************************************
arcServetrapHigh                TRAP-TYPE       
	        		ENTERPRISE	arcServe
                                VARIABLES       {
                                                arcServeServerName,
                                                arcServetrapdesc
                                                }
        			DESCRIPTION
                                        "ARCServe Critical Trap.
                                        
                                        A Critical trap has been generated by ARCServe.
                                        Refer to the trap summary information for a detailed
                                        description of this trap.  A critical trap normally
                                        indicates a serious error has occurred."
                                --#TYPE "ARCserve Critical Trap"
                                --#SUMMARY "%s   %s "
                                --#ARGUMENTS {0,1}
                                --#SEVERITY CRITICAL
                                --#STATE   DEGRADED     
	        	        ::= 1
arcServetrapMed                 TRAP-TYPE       
	        		ENTERPRISE	arcServe
                                VARIABLES       {
                                                arcServeServerName,
                                                arcServetrapdesc
                                                }
        			DESCRIPTION
                                        "ARCServe Minor Trap.
                                        
                                        A minor trap has been generated by ARCServe.  Minor
                                        traps are used by ARCServe to warn the user of unusual,
                                        but not fatal incidents.  Review the message summary to
                                        determine if this trap should concern you."
                                --#TYPE "ARCServe Minor Trap"
                                --#SUMMARY "%s   %s "
                                --#ARGUMENTS {0,1}
                                --#SEVERITY MINOR
                                --#TIMEINDEX 1
                                --#STATE   OPERATIONAL     
	        	        ::= 2
arcServetrapLow                 TRAP-TYPE       
	        		ENTERPRISE	arcServe
                                VARIABLES       {
                                                arcServeServerName,
                                                arcServetrapdesc
                                                }
        			DESCRIPTION
                                        "ARCServe Informational Trap.
                                        
                                        An ARCServe informational trap has been generated by
                                        ARCServe."
                                --#TYPE "ARCServe Informational Trap"
                                --#SUMMARY "%s   %s "
                                --#ARGUMENTS {0,1}
                                --#SEVERITY INFORMATIONAL
                                --#STATE   OPERATIONAL     
	        	        ::= 3
arcServetrap4                   TRAP-TYPE       
	        		ENTERPRISE	arcServe
                                VARIABLES       {
                                                arcServeServerName,
                                                arcServetrapdesc
                                                }
        			DESCRIPTION
                                        "Failed to attach to queue.
                                        
                                        This trap signifies that ARCServe was unable to locate
                                        it's queue.   This could be caused by Bindery or Directory
                                        Services corruption.  This problem can also occur if the
                                        ARCServe queue has been deleted.  Please verify that the
                                        ARCServe queue exists before attempting to continue."
                                --#TYPE "Failed to attach to queue (ARCServe)."
                                --#SUMMARY "%s  %s"
                                --#ARGUMENTS {0,1}
                                --#SEVERITY CRITICAL
                                --#TIMEINDEX 1
                                --#STATE   OPERATIONAL     
	        	        ::= 4
arcServetrap5                   TRAP-TYPE       
	        		ENTERPRISE	arcServe
                                VARIABLES       {
                                                arcServeServerName,
                                                arcServetrapdesc
                                                }
        			DESCRIPTION
                                        "Failed to service the job in queue.
                                        
                                        This trap signifies that ARCServe cannot remove jobs
                                        from it's queue.  This is normally due to a Bindery or
                                        Directory Services corruption.  Please verify that ARCserve
                                        was completely installed and that your Bindery/Directory is
                                        not corrupted."
                                --#TYPE "Failed to service the job in queue (ARCServe)."
                                --#SUMMARY "%s  %s"
                                --#ARGUMENTS {0,1}
                                --#SEVERITY CRITICAL
                                --#TIMEINDEX 1
                                --#STATE   OPERATIONAL     
	        	        ::= 5
arcServetrap6                   TRAP-TYPE       
	        		ENTERPRISE	arcServe
                                VARIABLES       {
                                                arcServeServerName,
                                                arcServetrapdesc
                                                }
        			DESCRIPTION
                                        "Failed to allocate memory.
                                        
                                        This trap signifies that ARCServe was unable to allocate
                                        memory.  More server memory may be required if this message
                                        occurs on a regular basis.  This message is not normally
                                        fatal, unless repeated attempts for memory fail."
                                --#TYPE "Failed to allocate memory (ARCServe)."
                                --#SUMMARY "%s  %s"
                                --#ARGUMENTS {0,1}
                                --#SEVERITY CRITICAL
                                --#TIMEINDEX 1
                                --#STATE   OPERATIONAL     
        	                ::= 6
arcServetrap7                   TRAP-TYPE       
	        		ENTERPRISE	arcServe
                                VARIABLES       {
                                                arcServeServerName,
                                                arcServetrapdesc
                                                }
        			DESCRIPTION
                                        "Server is low on memory, cannot start jobs.
	        	                                            
                                        This trap signifies that server is so low on memory
                                        that jobs cannot be processed.   Unload any unnecessary
                                        modules to obtain additional memory so jobs can be
                                        processed.  Jobs will be processed when memory has
                                        been restored on the server."

                                --#TYPE "Server low on memory, cannot start jobs (ARCServe)."
                                --#SUMMARY "%s  %s"
                                --#ARGUMENTS {0,1}
                                --#SEVERITY MINOR
                                --#TIMEINDEX 1
                                --#STATE   OPERATIONAL     
        	                ::= 7	       	    
arcServetrap8                   TRAP-TYPE       
	        		ENTERPRISE	arcServe
                                VARIABLES       {
                                                arcServeServerName,
                                                arcServetrapdesc
                                                }
        			DESCRIPTION
                                        "Same license found on another server.
                                        
                                        This trap signifies that another server has the same
                                        license as the server which generated the server.  You
                                        must install different licenses on each ARCServe server."
                                --#TYPE "Same license found on another server (ARCServe)."
                                --#SUMMARY "%s  %s"
                                --#ARGUMENTS {0,1}
                                --#SEVERITY MINOR
                                --#TIMEINDEX 1
                                --#STATE   OPERATIONAL     
        	                ::= 8	
arcServetrap9                   TRAP-TYPE       
	        		ENTERPRISE	arcServe
                                VARIABLES       {
                                                arcServeServerName,
                                                arcServetrapdesc
                                                }
        			DESCRIPTION
                                        "Failed to format tape.
                                        
                                        This trap signifies that ARCServe was unable to format
                                        a tape.  This could be caused by hardware or media failure.
                                        Verify tape drive has been cleaned and all cable connections.
                                        This message can also occur when an invalid board driver has
                                        been loaded."
                                --#TYPE "Failed to format tape (ARCServe)."
                                --#SUMMARY "%s  %s"
                                --#ARGUMENTS {0,1}
                                --#SEVERITY CRITICAL
                                --#TIMEINDEX 1
                                --#STATE   OPERATIONAL     
        	                ::= 9
arcServetrap10                  TRAP-TYPE       
	        		ENTERPRISE	arcServe
                                VARIABLES       {
                                                arcServeServerName,
                                                arcServetrapdesc
                                                }
        			DESCRIPTION
                                        "Failed to read tape header.
                                        
                                        This trap signifies a hardware or device failure when trying
                                        to read the tape header.  Verify that the tape is an ARCserve
                                        formatted tape.  Also verify that the tape drive has been
                                        cleaned and all cables are properly connected.  This message
                                        can also be displayed when an invalid board driver has been
                                        loaded."
                                --#TYPE "Failed to read tape header  (ARCServe)."
                                --#SUMMARY "%s  %s"
                                --#ARGUMENTS {0,1}
                                --#SEVERITY CRITICAL
                                --#TIMEINDEX 1
                                --#STATE   OPERATIONAL     
        	                ::= 10
arcServetrap11                  TRAP-TYPE       
	        		ENTERPRISE	arcServe
                                VARIABLES       {
                                                arcServeServerName,
                                                arcServetrapdesc
                                                }
        			DESCRIPTION
                                        "Failed to position tape.
                                        
                                        This trap signifies that ARCServe was unable to position
                                        the tape.  Also verify that the tape drive has been
                                        cleaned and all cables are properly connected.  This message
                                        can also be displayed when an invalid board driver has been
                                        loaded."
                                --#TYPE "Failed to position tape  (ARCServe)."
                                --#SUMMARY "%s  %s"
                                --#ARGUMENTS {0,1}
                                --#SEVERITY CRITICAL
                                --#TIMEINDEX 1
                                --#STATE   OPERATIONAL     
        	                ::= 11
arcServetrap12                  TRAP-TYPE       
	        		ENTERPRISE	arcServe
                                VARIABLES       {
                                                arcServeServerName,
                                                arcServetrapdesc
                                                }
        			DESCRIPTION
                                        "Backup Operation Cancelled. 
                                        
                                        This trap signifies that an operator has cancelled an
                                        ARCServe job."
                                --#TYPE "Backup Operation Cancelled (ARCServe)."
                                --#SUMMARY "%s  %s"
                                --#ARGUMENTS {0,1}
                                --#SEVERITY CRITICAL
                                --#TIMEINDEX 1
                                --#STATE   OPERATIONAL     
        	                ::= 12      				      				  				      			     				      			      			     											
arcServetrap13                  TRAP-TYPE       
	        		ENTERPRISE	arcServe
                                VARIABLES       {
                                                arcServeServerName,
                                                arcServetrapdesc
                                                }
        			DESCRIPTION
                                        "Backup Operation Successful.
                                        
                                        This trap signifies that the backup operation completed
                                        successfully."
                                --#TYPE "Backup Operation Successful (ARCServe)."
                                --#SUMMARY "%s  %s"
                                --#ARGUMENTS {0,1}
                                --#SEVERITY INFORMATIONAL
                                --#TIMEINDEX 1
                                --#STATE   OPERATIONAL     
        	                ::= 13
arcServetrap14                  TRAP-TYPE       
	        		ENTERPRISE	arcServe
                                VARIABLES       {
                                                arcServeServerName,
                                                arcServetrapdesc
                                                }
        			DESCRIPTION
                                        "Backup Operation Incomplete.
                                        
                                        This trap signifies that the backup operation completed with
                                        warnings.  Refer to the activity log to determine if important
                                        nodes selected for backup have been missed."
                                --#TYPE "Backup Operation Incomplete (ARCServe)."
                                --#SUMMARY "%s  %s"
                                --#ARGUMENTS {0,1}
                                --#SEVERITY MINOR
                                --#TIMEINDEX 1
                                --#STATE   OPERATIONAL 
        	                ::= 14
arcServetrap15                  TRAP-TYPE       
	        		ENTERPRISE	arcServe
                                VARIABLES       {
                                                arcServeServerName,
                                                arcServetrapdesc
                                                }
        			DESCRIPTION
                                        "Backup Operation Failed.
                                        
                                        This trap signifies that the backup operation failed.  This message
                                        indicates that the backup encountered processing errors.  Refer to
                                        the activity log for a description of the problems encountered
                                        when the backup failed."
                                --#TYPE "Backup Operation Failed (ARCServe)."
                                --#SUMMARY "%s  %s"
                                --#ARGUMENTS {0,1}
                                --#SEVERITY CRITICAL
                                --#TIMEINDEX 1
                                --#STATE   DEGRADED     
        	                ::= 15
END
