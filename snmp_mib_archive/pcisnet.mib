--
-- Name:
--
--  Tandem ServerNet PCI Adapter MIB
--
-- Abstract:
--
--  This file defines the message information block for SNMP for the ServerNet
--  PCI Adapter board from Tandem.
--
--  Notes:
--
--      * Multiple adapters are possible. Currently only 1 is supported.
--      * The MIB is specific to the servernet group (4) under the Tandem
--        enterprise (169).
--      * The MIB is targeted for only Tandem development and Compaq's needs
--        at this time.
--      * The ServerNet subtree is:
--          tandem      1.3.6.1.4.1.169
--           servernet      1.3.6.1.4.1.169.8
--            pcisnet           1.3.6.1.4.1.169.8.1
--             snetMibRev           1.3.6.1.4.1.169.8.1.1
--              snetMibRevMajor        		1.3.6.1.4.1.169.8.1.1.1
--              snetMibRevMinor        		1.3.6.1.4.1.169.8.1.1.2
--              snetMibCondition       		1.3.6.1.4.1.169.8.1.1.3
--              snetMibPollInterval     	1.3.6.1.4.1.169.8.1.1.4
--             snetAdaptr                1.3.6.1.4.1.169.8.1.2
--              snetAdaptrNumber    		1.3.6.1.4.1.169.8.1.2.1
--              snetAdaptrTable     		1.3.6.1.4.1.169.8.1.2.2
--               snetAdaptrEntry    		1.3.6.1.4.1.169.8.1.2.2.1
--		snetAdaptrNeighborTable		1.3.6.1.4.1.169.8.1.2.3
--               snetAdaptrNeighborEntry        1.3.6.1.4.1.169.8.1.2.3.1 
--		 snetAdaptrNodeIDTable          1.3.6.1.4.1.169.8.1.2.4
--               snetAdaptrNodeIDEntry		1.3.6.1.4.1.169.8.1.2.4.1
--             snetAdaptrOsCommonGroup   1.3.6.1.4.1.169.8.1.3
--
--      * snetMibRev    Contains Mib revision and condition information.
--      * snetAdaptr    Contains configuration and statistical information
--                      of the ServerNet Adapter.
--      * snetAdapterTable  The actual table containing the Adapter entries.
--      * snetAdaptrNeighborTable The table containing the neighbor entries.
--      * snetAdaptrNodeIDTable  The table containing the adapter card Id(s).
--
-- Author:
--
--  JL  6/6/96
--
-- History:
--
--  CS   6/13/96  changed serverNet to proper OID
--
--  KM  10/2/96 - Added a new MIB variable to hold subagent
--                       polling interval.
--                       Also, made minor syntax and comment
--                       corrections.
--
--  KM   11/15/96 - Added a new TrapEnable MIB variables.
--
--  CC   4/8/97  Added new Trap for TimeoutError and 
--                         corresponding enable.  Changed Path to Port
--  CC   4/21/97 Changed ServerNet from 1.3.6.1.4.1.169.4 to
--                           1.3.6.1.4.1.169.8 due to conflict with S4000. 
--  CC   7/8/97  Changes for second release.  Counters changed
--                           to 2 32 bit fields to represent 1 64 bit counter,
--                            Timeout and Nak errors split into
--                           X and Y port counters, OsCommon group added.
--  FC   1/20/98 Added "LxSymbol" link exception symbol and intrinsic error counters:
--				CauseExceptQueueError, CauseWriteReqOverflow,
--				CauseAccessError, CauseReadReqOverflow, CauseQueueFull,
--				IntrPktDropped and BteDoneInterrupts.
--				Each counter has two 32 bits fields that
--			        represents one 64 bit counter.
--				Halt, LxSecondExceptions, LxCrcErrors, LxIllegalCommands,
--				LxFifoOverruns, LxKeepAliveErrors, and LxEFifoOverflow
--				are further split into X and Y counters.
--  FC   3/2/98 Added two ServerNet adapter Neighboring data entries: 
--                              snetAdaptrNeighborTable  1.3.6.1.4.1.169.8.1.2.3
--                              snetAdaptrNeighborEntry  1.3.6.1.4.1.169.8.1.2.3.1
--                               
--  FC   3/10/98 Added two ServerNet Adapter Node ID entries:
--                              snetAdaptrNodeIDTable          1.3.6.1.4.1.169.8.1.2.4
--                              snetAdaptrNodeIDEntry	       1.3.6.1.4.1.169.8.1.2.4.1  
--                              The snetAdaptrNodeIDEntry contains two entries: 
--                              snetAdaptrNodeIDIndex and snetAdapterNodeID
--
-- CC    5/7/98 Changed the enumerations to be inline instead of predefined.
--
-- FC    6/1/98 Changed description for calculated 32 bit low and high counters.
--		Added Smart and Dumb IO in Neighbor Node Type.
--
-- FC    6/3/98 Added snetAdaptrNodeMfgId, snetAdaptrNodePartNumber and snetAdaptrNodeSerialNumber
--              to AdapterEntry
--
-- CC    5/26/99 Changes to support dual ServerNet IDs per PCI adapter
--              obsolete unsupported LinkEX counters for SPAD2
--              obsolete snetAdaptrTimeoutErrorsChange and snetMibTimeoutErrorTrapEnable
--              since the timeout trap is not needed and not used
-- CC    9/08/99 Obsoleted snetMibPollInterval 
-- CC    10/5/99 Obsoleted snetAdaptrIntrPktDroppedLow and snetAdaptrIntrPktDroppedHi
-- CC    2/23/00 Added snetAdaptrRevMajor and snetAdaptrRevMinor to store the
--               software driver versions.  This data was incorrectly being put into
--               the snetMibRevMajor and snetMibRevMinor.  
          
ServerNetPCI-MIB DEFINITIONS ::= BEGIN

   IMPORTS
      enterprises,Counter,Gauge  FROM RFC1155-SMI
      OBJECT-TYPE                  FROM RFC-1212
      DisplayString                      FROM RFC1213-MIB 
      TRAP-TYPE                      FROM RFC-1215; 

   tandem                    OBJECT IDENTIFIER ::= { enterprises 169 }
   serverNet                 OBJECT IDENTIFIER ::= { tandem 8 }
   pcisnet                   OBJECT IDENTIFIER ::= { serverNet 1 }
   snetMibRev                OBJECT IDENTIFIER ::= { pcisnet 1 }
   snetAdaptr                OBJECT IDENTIFIER ::= { pcisnet 2 }
   snetAdaptrOsCommonGroup   OBJECT IDENTIFIER ::= { pcisnet 3 }


--
-- ServerNet Mib Revision Group
--

   snetMibRevMajor OBJECT-TYPE
      SYNTAX  INTEGER (1..65535)
      ACCESS  read-only
      STATUS  mandatory
      DESCRIPTION
         "The Major Revision level of the MIB.

         A change in the major revision level represents a major change
         in the architecture of the MIB.  A change in the major revision
         level may indicate a significant change in the information
         supported and/or the meaning of the supported information.
         Correct interpretation of data may require a MIB document with
         the same major revision level."
      ::= { snetMibRev 1 }

   snetMibRevMinor OBJECT-TYPE
      SYNTAX  INTEGER (0..65535)
      ACCESS  read-only
      STATUS  mandatory
      DESCRIPTION
         "The Minor Revision level of the MIB.

         A change in the minor revision level may represent some minor
         additional support, no changes to any pre-existing information
         has occurred."
      ::= { snetMibRev 2 }

   snetMibCondition OBJECT-TYPE
      SYNTAX  INTEGER{
          other(1),
          ok(2),
          degraded(3),
          failed(4)
          }
      ACCESS  read-only
      STATUS  mandatory
      DESCRIPTION
         "ServerNet adapter(s) overall MIB condition.

         This represents the overall condition of all ServerNet adapters
         installed in the system.  The overall condition states are:

            other(1)
                All ServerNet adapters are OK except for at least 1 is Other.

            ok(2)
                All ServerNet adapters are OK.

            degraded(3)
                One or more ServerNet adapters are Degraded.

            failed(4)
                One or more ServerNet adapters are Failed."
      ::= { snetMibRev 3 }

   snetMibPollInterval OBJECT-TYPE
      SYNTAX  INTEGER
      ACCESS  read-write
      STATUS  mandatory
      DESCRIPTION
         "**NOTE: this object is obsolete."
      ::= { snetMibRev 4 }

   snetMibStatusTrapEnable OBJECT-TYPE
      SYNTAX  INTEGER (0..1)
      ACCESS  read-write
      STATUS  mandatory
      DESCRIPTION
         "The snetAdaptrStatusChange Trap Enable/Disable switch.

         This defaults to on."

      ::= { snetMibRev 5 }

   snetMibXPortTrapEnable OBJECT-TYPE
      SYNTAX  INTEGER (0..1)
      ACCESS  read-write
      STATUS  mandatory
      DESCRIPTION
         "The snetAdaptrXPortStatusChange Trap Enable/Disable switch.

         This defaults to on."

      ::= { snetMibRev 6 }

   snetMibYPortTrapEnable OBJECT-TYPE
      SYNTAX  INTEGER (0..1)
      ACCESS  read-write
      STATUS  mandatory
      DESCRIPTION
         "The snetAdaptrYPortStatusChange Trap Enable/Disable switch.

         This defaults to on."

      ::= { snetMibRev 7 }

   snetMibTimeoutErrorTrapEnable OBJECT-TYPE
      SYNTAX  INTEGER (0..1)
      ACCESS  read-write
      STATUS  obsolete
      DESCRIPTION
         "**NOTE: this object is obsolete."

      ::= { snetMibRev 8}

--
-- ServerNet Adapter Group
--

   snetAdaptrNumber OBJECT-TYPE
      SYNTAX  INTEGER
      ACCESS  read-only
      STATUS  mandatory
      DESCRIPTION
         "The number of ServerNet adapters (regardless of state)
          present on the system."
      ::= { snetAdaptr 1 }

   snetAdaptrTable OBJECT-TYPE
      SYNTAX  SEQUENCE OF SnetAdaptrEntry
      ACCESS  not-accessible
      STATUS  mandatory
      DESCRIPTION
         "ServerNet adapter table."
      ::= { snetAdaptr 2 }

   snetAdaptrEntry OBJECT-TYPE
      SYNTAX  SnetAdaptrEntry
      ACCESS  not-accessible
      STATUS  mandatory
      DESCRIPTION
         "An entry containing ServerNet adapter objects."
      INDEX   { snetAdaptrIndex }
      ::= { snetAdaptrTable 1 }

   SnetAdaptrEntry ::= SEQUENCE
   {
     	snetAdaptrIndex             		INTEGER,
    	snetAdaptrProductModel      		DisplayString,
     	snetAdaptrProductVersion    		DisplayString,
     	snetAdaptrProductVendor     		DisplayString,
     	snetAdaptrBusSlot           		INTEGER,
     	snetAdaptrSnetID            		DisplayString,
     	snetAdaptrMtu               		INTEGER,
     	snetAdaptrStatus            		INTEGER,
     	snetAdaptrAdminStatus       		INTEGER,
     	snetAdaptrBTEAvail          		INTEGER,
     	snetAdaptrBTEGauge          		Gauge,
     	snetAdaptrAVTAvail          		INTEGER,
     	snetAdaptrAVTGauge          		Gauge,
     	snetAdaptrXPortStatus       		INTEGER,
     	snetAdaptrYPortStatus       		INTEGER,
     	snetAdaptrPushRequestsLow   		Counter,
     	snetAdaptrPushOctetsLow     		Counter,
     	snetAdaptrPullRequestsLow   		Counter,
     	snetAdaptrPullOctetsLow     		Counter,
     	snetAdaptrNakErrorsLow      		Counter,
     	snetAdaptrTimeoutErrorsLow  		Counter,
     	snetAdaptrParamErrorsLow    		Counter,
     	snetAdaptrRemoteErrorsLow   		Counter,
     	snetAdaptrPushRequestsHi    		Counter,
     	snetAdaptrPushOctetsHi      		Counter,
     	snetAdaptrPullRequestsHi    		Counter,
     	snetAdaptrPullOctetsHi      		Counter,
     	snetAdaptrNakErrorsHi       		Counter,
     	snetAdaptrTimeoutErrorsHi   		Counter,
     	snetAdaptrParamErrorsHi     		Counter,
     	snetAdaptrRemoteErrorsHi   		Counter,
     	snetAdaptrXNakErrorsLow     		Counter,
     	snetAdaptrXNakErrorsHi      		Counter,
     	snetAdaptrYNakErrorsLow     		Counter,
     	snetAdaptrYNakErrorsHi      		Counter,
     	snetAdaptrXTimeoutErrorsLow 		Counter,
     	snetAdaptrXTimeoutErrorsHi  		Counter,
     	snetAdaptrYTimeoutErrorsLow 		Counter,
     	snetAdaptrYTimeoutErrorsHi  		Counter,
	snetAdaptrCauseExceptQueueErrorLow	Counter,
	snetAdaptrCauseExceptQueueErrorHi	Counter,
	snetAdaptrCauseWriteReqOverflowLow	Counter,
	snetAdaptrCauseWriteReqOverflowHi	Counter,
	snetAdaptrCauseAccessErrorLow		Counter,
	snetAdaptrCauseAccessErrorHi		Counter,
	snetAdaptrCauseReadReqOverflowLow	Counter,
	snetAdaptrCauseReadReqOverflowHi	Counter,  
	snetAdaptrCauseQueueFullLow		Counter,
	snetAdaptrCauseQueueFullHi		Counter,
	snetAdaptrXHaltLow			Counter,
	snetAdaptrXHaltHi		  		Counter,
	snetAdaptrYHaltLow			Counter,
	snetAdaptrYHaltHi				Counter,
	snetAdaptrHaltLow				Counter,
	snetAdaptrHaltHi				Counter,
	snetAdaptrXLxSecondExceptionsLow	Counter,		
	snetAdaptrXLxSecondExceptionsHi	Counter,
	snetAdaptrYLxSecondExceptionsLow	Counter,
	snetAdaptrYLxSecondExceptionsHi	Counter, 
	snetAdaptrLxSecondExceptionsLow	Counter,
	snetAdaptrLxSecondExceptionsHi	Counter,       
	snetAdaptrXLxCrcErrorsLow		Counter,
	snetAdaptrXLxCrcErrorsHi		Counter,
	snetAdaptrYLxCrcErrorsLow		Counter,
	snetAdaptrYLxCrcErrorsHi		Counter,
	snetAdaptrLxCrcErrorsLow		Counter,
	snetAdaptrLxCrcErrorsHi			Counter,
	snetAdaptrXLxIllegalCommandsLow	Counter,
	snetAdaptrXLxIllegalCommandsHi	Counter,
	snetAdaptrYLxIllegalCommandsLow	Counter,
	snetAdaptrYLxIllegalCommandsHi	Counter,
	snetAdaptrLxIllegalCommandsLow	Counter,
	snetAdaptrLxIllegalCommandsHi		Counter,
	snetAdaptrXLxFifoOverrunLow		Counter,
	snetAdaptrXLxFifoOverrunHi		Counter,	        
	snetAdaptrYLxFifoOverrunLow		Counter,
	snetAdaptrYLxFifoOverrunHi		Counter,
	snetAdaptrLxFifoOverrunLow		Counter,
	snetAdaptrLxFifoOverrunHi		Counter,
	snetAdaptrXLxKeepAliveErrorsLow	Counter,
	snetAdaptrXLxKeepAliveErrorsHi	Counter,
	snetAdaptrYLxKeepAliveErrorsLow	Counter,
	snetAdaptrYLxKeepAliveErrorsHi	Counter,
	snetAdaptrLxKeepAliveErrorsLow	Counter,
	snetAdaptrLxKeepAliveErrorsHi		Counter,
	snetAdaptrXLxEFifoOverflowLow		Counter,	        
	snetAdaptrXLxEFifoOverflowHi		Counter,
	snetAdaptrYLxEFifoOverflowLow		Counter,
	snetAdaptrYLxEFifoOverflowHi		Counter,  
	snetAdaptrLxEFifoOverflowLow		Counter,
	snetAdaptrLxEFifoOverflowHi		Counter,      
	snetAdaptrXRecentLxSymbol		INTEGER,
	snetAdaptrXPreviousLxSymbol		INTEGER,
	snetAdaptrYRecentLxSymbol		INTEGER,
	snetAdaptrYPreviousLxSymbol		INTEGER,
	snetAdaptrIntrPktDroppedLow 		Counter,
	snetAdaptrIntrPktDroppedHi		Counter,
	snetAdaptrBteDoneInterrupts1Low	Counter,
	snetAdaptrBteDoneInterrupts1Hi	Counter,
	snetAdaptrBteDoneInterrupts2Low	Counter,
	snetAdaptrBteDoneInterrupts2Hi	Counter,
	snetAdaptrNodeMfgId			INTEGER,
	snetAdaptrNodePartNumber		INTEGER,
	snetAdaptrNodeSerialNumber		DisplayString,
      snetAdaptrSnetID1            		DisplayString,
      snetAdaptrRevMajor                  INTEGER,
      snetAdaptrRevMinor 	            INTEGER
   }

   snetAdaptrIndex OBJECT-TYPE
      SYNTAX  INTEGER (0..225)
      ACCESS  read-only
      STATUS  mandatory
      DESCRIPTION
         "ServerNet adapter index.

         The adapter index indicates to which ServerNet adapter instance
         this table entry belongs."
     ::= { snetAdaptrEntry 1 }

   snetAdaptrProductModel OBJECT-TYPE
      SYNTAX  DisplayString (SIZE(0..255))
      ACCESS  read-only
      STATUS  mandatory
      DESCRIPTION
         "A textual string containing the product model name of the
         interface."
      ::= { snetAdaptrEntry 2 }

   snetAdaptrProductVersion OBJECT-TYPE
      SYNTAX  DisplayString (SIZE(0..255))
      ACCESS  read-only
      STATUS  mandatory
      DESCRIPTION
         "A textual string containing the product version of the
         interface."
      ::= { snetAdaptrEntry 3 }

   snetAdaptrProductVendor OBJECT-TYPE
      SYNTAX  DisplayString (SIZE(0..255))
      ACCESS  read-only
      STATUS  mandatory
      DESCRIPTION
         "A textual string containing the vendor of the product
         interface."
      ::= { snetAdaptrEntry 4 }

   snetAdaptrBusSlot OBJECT-TYPE
      SYNTAX  INTEGER
      ACCESS  read-only
      STATUS  mandatory
      DESCRIPTION
         "The PCI bus logical slot number of the ServerNet adapter."
      ::= { snetAdaptrEntry 5 }

   snetAdaptrSnetID OBJECT-TYPE
      SYNTAX  DisplayString (SIZE(0..16))
      ACCESS  read-only
      STATUS  mandatory
      DESCRIPTION
         "The ServerNet ID of the node containing the ServerNet
          adapter Port 0. It is displayed as hexadecimal value"
      ::= { snetAdaptrEntry 6 }

    snetAdaptrSnetID1 OBJECT-TYPE
      SYNTAX  DisplayString (SIZE(0..16))
      ACCESS  read-only
      STATUS  mandatory
      DESCRIPTION
         "The ServerNet ID of the node containing the ServerNet
          adapter Port 1. It is displayed as hexadecimal value"
      ::= { snetAdaptrEntry 105 }


   snetAdaptrMtu OBJECT-TYPE
      SYNTAX  INTEGER
      ACCESS  read-only
      STATUS  mandatory
      DESCRIPTION
         "The size of the largest transfer which can be
         pushed or pulled on the interface, specified in octets."
      ::= { snetAdaptrEntry 7 }

   snetAdaptrStatus OBJECT-TYPE
      SYNTAX  INTEGER{
          other(1),
          ok(2),
          degraded(3),
          failed(4)
          }
      ACCESS  read-only
      STATUS  mandatory
      DESCRIPTION
         "ServerNet adapter status.

         The ServerNet board can be in one of the following states:

         other(1)
            The controller is in a state other than one of those listed
            below.

         ok(2)
            Indicates normal operating mode.  No user action is necessary.

         degraded(3)
            Indicates either the X-Port or Y-Port has failed but not both.

         failed(4)
            Indicates that the controller has failed because both ports have
            failed or a detectable hardware failure occurred.  You should bring
            down the server and run Diagnostics to help identify the
            problem.  The ServerNet adapter may need to be replaced."
      ::= { snetAdaptrEntry 8 }

   snetAdaptrAdminStatus OBJECT-TYPE
      SYNTAX  INTEGER      {
          other(1),
          up(2),
          down(3),
          testing(4)
          }
      ACCESS  read-write
      STATUS  mandatory
      DESCRIPTION
         "Reserved for future use."
      ::= { snetAdaptrEntry 9 }

   snetAdaptrBTEAvail OBJECT-TYPE
      SYNTAX  INTEGER
      ACCESS  read-only
      STATUS  mandatory
      DESCRIPTION
         "The total number of BTE descriptors available."
      ::= { snetAdaptrEntry 10 }

   snetAdaptrBTEGauge OBJECT-TYPE
      SYNTAX  Gauge
      ACCESS  read-write
      STATUS  mandatory
      DESCRIPTION
         "The high watermark of BTE descriptors used.  An SNMP set can reset the
          high water mark to zero, all other values are not allowed."
      ::= { snetAdaptrEntry 11 }

   snetAdaptrAVTAvail OBJECT-TYPE
      SYNTAX  INTEGER
      ACCESS  read-only
      STATUS  mandatory
      DESCRIPTION
         "The total number of AVT entries available."
      ::= { snetAdaptrEntry 12 }

   snetAdaptrAVTGauge OBJECT-TYPE
      SYNTAX  Gauge
      ACCESS  read-write
      STATUS  mandatory
      DESCRIPTION
         "The high watermark of AVT entries used.  An SNMP set can reset the
          high water mark to zero, all other values are not allowed."
      ::= { snetAdaptrEntry 13 }

   snetAdaptrXPortStatus OBJECT-TYPE
      SYNTAX  INTEGER{
          other(1),
          ok(2),
          degraded(3),
          failed(4)
	    }
      ACCESS  read-only
      STATUS  mandatory
      DESCRIPTION
         "The current state of the X-Port.

         other(1)
            The state of the X-Port could not be determined.

         ok(2)
            Indicates normal operating mode.  No user action is necessary.

         degraded(3)
            Indicates the X-Port is running in a degraded mode.

         failed(4)
            The X-Port has failed."
      ::= { snetAdaptrEntry 14 }

   snetAdaptrYPortStatus OBJECT-TYPE
      SYNTAX INTEGER{
          other(1),
          ok(2),
          degraded(3),
          failed(4)
	    }
      ACCESS  read-only
      STATUS  mandatory
      DESCRIPTION
         "The current state of the Y-Port.

         other(1)
            The state of the Y-Port could not be determined.

         ok(2)
           Indicates normal operating mode.  No user action is necessary.

         degraded(3)
            Indicates the Y-Port is running in a degraded mode.

         failed(4)
            The Y-Port has failed."
      ::= { snetAdaptrEntry 15 }

   snetAdaptrPushRequestsLow OBJECT-TYPE
      SYNTAX  Counter
      ACCESS  read-only
      STATUS  mandatory
      DESCRIPTION
         "The number of requests pushed. Low order 32 bits."
      ::= { snetAdaptrEntry 16 }


   snetAdaptrPushOctetsLow OBJECT-TYPE
      SYNTAX  Counter
      ACCESS  read-only
      STATUS  mandatory
      DESCRIPTION
         "The number of octets pushed that originate from the local node.
          Low order 32 bits."
      ::= { snetAdaptrEntry 17 }


    snetAdaptrPullRequestsLow OBJECT-TYPE
      SYNTAX  Counter
      ACCESS  read-only
      STATUS  mandatory
      DESCRIPTION
         "The number of calls made to the SPA driver from the client.
          Low order 32 bits."
      ::= { snetAdaptrEntry 18 }

    snetAdaptrPullOctetsLow OBJECT-TYPE
      SYNTAX  Counter
      ACCESS  read-only
      STATUS  mandatory
      DESCRIPTION
         "The number of octets pulled. Low order 32 bits."
      ::= { snetAdaptrEntry 19 }

   snetAdaptrNakErrorsLow OBJECT-TYPE
      SYNTAX  Counter
      ACCESS  read-only
      STATUS  mandatory
      DESCRIPTION
         "The number of push/pull requests that were received by 
          the destination but rejected and cannot be completed. Low order 32
          bits. This value is combined with snetAdaptrNakErrorsHi to create
          a 64 bit value.
          The MIB variable snetAdaptrNakErrorsLow is a calculated value. It  
          is the low order 32 bits of the sum of snetAdaptrXNakErrors, 
          and snetAdaptrYNakErrors."
      ::= { snetAdaptrEntry 20 }

  snetAdaptrTimeoutErrorsLow OBJECT-TYPE
      SYNTAX  Counter
      ACCESS  read-only
      STATUS  mandatory
      DESCRIPTION
         "The number of push/pull requests that were never
          acknowledged and cannot be completed.  Low order 32
          bits. This value is combined with snetAdaptrTimeoutErrorsHi to create
          a 64 bit value.
          The MIB variable snetAdaptrTimeoutErrorsLow is a calculated value. It
          is the low order 32 bits of the sum of snetAdaptrXTimeoutErrors and
          snetAdaptrYTimeoutErrors." 
      ::= { snetAdaptrEntry 21 }
 
   snetAdaptrParamErrorsLow  OBJECT-TYPE
      SYNTAX  Counter
      ACCESS  read-only
      STATUS  mandatory
      DESCRIPTION
         "The number of push/pull requests that were never
         sent to the destination because of a parameter
         programming error and cannot be completed.
         Low order 32 bits." 
      ::= { snetAdaptrEntry 22 }

     snetAdaptrRemoteErrorsLow OBJECT-TYPE
        SYNTAX  Counter
        ACCESS  read-only
        STATUS  mandatory
        DESCRIPTION
         "The number of errors that occurred due to remote 
         push/pull requests."
      ::= { snetAdaptrEntry 23 }   
 

   snetAdaptrPushRequestsHi   OBJECT-TYPE 
      SYNTAX  Counter
      ACCESS  read-only
      STATUS  mandatory
      DESCRIPTION
         "The number of requests pushed. High order 32 bits."
      ::= { snetAdaptrEntry 24 }

  snetAdaptrPushOctetsHi   OBJECT-TYPE
      SYNTAX  Counter
      ACCESS  read-only
      STATUS  mandatory
      DESCRIPTION
         "The number of octets pushed that originate from the local node.
          High order 32 bits."
      ::= { snetAdaptrEntry 25 }

    snetAdaptrPullRequestsHi OBJECT-TYPE
      SYNTAX  Counter
      ACCESS  read-only
      STATUS  mandatory
      DESCRIPTION
         "The number of calls made to the SPA driver from the client.
          High order 32 bits."
      ::= {snetAdaptrEntry 26 }

   snetAdaptrPullOctetsHi OBJECT-TYPE
      SYNTAX  Counter
      ACCESS  read-only
      STATUS  mandatory
      DESCRIPTION
         "The number of octets pulled. High order 32 bits."
      ::= { snetAdaptrEntry 27 }

   snetAdaptrNakErrorsHi OBJECT-TYPE
      SYNTAX  Counter
      ACCESS  read-only
      STATUS  mandatory
      DESCRIPTION
         "The number of push/pull requests that were
         received by the destination but rejected and
         cannot be completed. High order 32 bits. 
         This value is combined with snetAdaptrNakErrorsLow to create
         a 64 bit value.

         The MIB variable snetAdaptrNakErrorsHi is a calculated value. It  
         is the high order 32 bits of the sum of snetAdaptrXNakErrors and
         snetAdaptrYNakErrors."
      ::= { snetAdaptrEntry 28}

    snetAdaptrTimeoutErrorsHi OBJECT-TYPE
      SYNTAX  Counter
      ACCESS  read-only
      STATUS  mandatory
      DESCRIPTION
         "The number of push/pull requests that were never
         acknowledged and cannot be completed. High order
         32 bits. This value is combined with snetAdaptrTimeoutErrosHi
         to create a 64 bit value.

         The MIB variable snetAdaptrTimeoutErrorsHi is a calculated value. It
         is the high order 32 bits of the sum of snetAdaptrXTimeoutErrors and
         snetAdaptrYTimeoutErrors."
      ::= {  snetAdaptrEntry 29}

     snetAdaptrParamErrorsHi  OBJECT-TYPE
      SYNTAX  Counter
      ACCESS  read-only
      STATUS  mandatory
      DESCRIPTION
         "The number of push/pull requests that were never
         sent to the destination because of a parameter
         programming error and cannot be completed.
         High order 32 bits."
      ::= {  snetAdaptrEntry 30}

    snetAdaptrRemoteErrorsHi OBJECT-TYPE
       SYNTAX  Counter
       ACCESS  read-only
       STATUS  mandatory
       DESCRIPTION
         "The number of errors that occurred due to remote push/pull
          requests. High order 32 bits."
      ::= {  snetAdaptrEntry 31 }


    snetAdaptrXNakErrorsLow OBJECT-TYPE
      SYNTAX  Counter
      ACCESS  read-only
      STATUS  mandatory
      DESCRIPTION
         "The number of push/pull requests that were
         received by the destination but rejected and
         cannot be completed on the X port. Low order 
         32 bits."
      ::= { snetAdaptrEntry 32 }
 
   snetAdaptrXNakErrorsHi OBJECT-TYPE
      SYNTAX  Counter
      ACCESS  read-only
      STATUS  mandatory
      DESCRIPTION
         "The number of push/pull requests that were
         received by the destination but rejected and
         cannot be completed on the X port. High order 
         32 bits."
      ::= { snetAdaptrEntry 33}

    snetAdaptrYNakErrorsLow OBJECT-TYPE
      SYNTAX  Counter
      ACCESS  read-only
      STATUS  mandatory
      DESCRIPTION
         "The number of push/pull requests that were
         received by the destination but rejected and
         cannot be completed on the Y port. Low order 
         32 bits."
      ::= { snetAdaptrEntry 34 }
 
   snetAdaptrYNakErrorsHi OBJECT-TYPE
      SYNTAX  Counter
      ACCESS  read-only
      STATUS  mandatory
      DESCRIPTION
         "The number of push/pull requests that were
         received by the destination but rejected and
         cannot be completed on the Y port. High order 
         32 bits."
      ::= { snetAdaptrEntry 35 }

   snetAdaptrXTimeoutErrorsLow OBJECT-TYPE
      SYNTAX  Counter
      ACCESS  read-only
      STATUS  mandatory
      DESCRIPTION
         "The number of push/pull requests that were never
         acknowledged and cannot be completed on the X port.
         Low order 32 bits."
      ::= {  snetAdaptrEntry 36 }

   snetAdaptrXTimeoutErrorsHi OBJECT-TYPE
      SYNTAX  Counter
      ACCESS  read-only
      STATUS  mandatory
      DESCRIPTION
         "The number of push/pull requests that were never
         acknowledged and cannot be completed on the X port.
         High order 32 bits."
      ::= {  snetAdaptrEntry 37}

   snetAdaptrYTimeoutErrorsLow OBJECT-TYPE
      SYNTAX  Counter
      ACCESS  read-only
      STATUS  mandatory
      DESCRIPTION
         "The number of push/pull requests that were never
         acknowledged and cannot be completed on the Y port.
         Low order 32 bits."
      ::= {  snetAdaptrEntry 38 }

   snetAdaptrYTimeoutErrorsHi OBJECT-TYPE
      SYNTAX  Counter
      ACCESS  read-only
      STATUS  mandatory
      DESCRIPTION
         "The number of push/pull requests that were never
         acknowledged and cannot be completed on the Y port.
         High order 32 bits."
      ::= {  snetAdaptrEntry 39 }

--
-- Intrinsic error counters
--

   snetAdaptrCauseExceptQueueErrorLow OBJECT-TYPE
      SYNTAX  Counter
      ACCESS  read-only
      STATUS  mandatory
      DESCRIPTION
         "The total number of push exception queue overflows.
          Low order 32 bits." 
      ::= {  snetAdaptrEntry 40 }
  
   snetAdaptrCauseExceptQueueErrorHi OBJECT-TYPE
      SYNTAX  Counter
      ACCESS  read-only
      STATUS  mandatory
      DESCRIPTION
         "The total number of push exception queue overflows.
	  High order 32 bits."
      ::= {  snetAdaptrEntry 41 }
  
    snetAdaptrCauseWriteReqOverflowLow OBJECT-TYPE
      SYNTAX  Counter
      ACCESS  read-only
      STATUS  mandatory
      DESCRIPTION
         "The total number of Write Request Overflows.
	  Low order 32 bits."
      ::= {  snetAdaptrEntry 42 }
  
    snetAdaptrCauseWriteReqOverflowHi OBJECT-TYPE
      SYNTAX  Counter
      ACCESS  read-only
      STATUS  mandatory
      DESCRIPTION
         "The total number of Write Request overflows.
          High order 32 bits."
      ::= {  snetAdaptrEntry 43 }
  
    snetAdaptrCauseAccessErrorLow OBJECT-TYPE
      SYNTAX  Counter
      ACCESS  read-only
      STATUS  mandatory
      DESCRIPTION
         "The total number of Access errors.
	  Low order 32 bits."
      ::= {  snetAdaptrEntry 44 }
  
    snetAdaptrCauseAccessErrorHi OBJECT-TYPE
      SYNTAX  Counter
      ACCESS  read-only
      STATUS  mandatory
      DESCRIPTION
         "The total number of Access errors.
	  High order 32 bits."
      ::= {  snetAdaptrEntry 45 }
  
    snetAdaptrCauseReadReqOverflowLow OBJECT-TYPE
      SYNTAX  Counter
      ACCESS  read-only
      STATUS  mandatory
      DESCRIPTION
         "The total number of Read Request Overflows.
	  Low order 32 bits." 
      ::= {  snetAdaptrEntry 46 }
    
    snetAdaptrCauseReadReqOverflowHi OBJECT-TYPE
      SYNTAX  Counter
      ACCESS  read-only
      STATUS  mandatory
      DESCRIPTION
         "The total number of Read Request Overflows.
	  High order 32 bits."
      ::= {  snetAdaptrEntry 47 }
    
    snetAdaptrCauseQueueFullLow OBJECT-TYPE
      SYNTAX  Counter
      ACCESS  read-only
      STATUS  mandatory
      DESCRIPTION
         "The total number of Interrupt Queue Full Errors.
	  Low order 32 bits."
      ::= {  snetAdaptrEntry 48 }
    
    snetAdaptrCauseQueueFullHi OBJECT-TYPE
      SYNTAX  Counter
      ACCESS  read-only
      STATUS  mandatory
      DESCRIPTION
         "The total number of Interrupt Queue Full Errors.
	  High order 32 bits."
      ::= {  snetAdaptrEntry 49 }

    snetAdaptrXHaltLow OBJECT-TYPE
      SYNTAX  Counter
      ACCESS  read-only
      STATUS  obsolete
      DESCRIPTION
         "**NOTE: this object is obsolete."
      ::= {  snetAdaptrEntry 50 }
    
    snetAdaptrXHaltHi OBJECT-TYPE
      SYNTAX  Counter
      ACCESS  read-only
      STATUS  obsolete
      DESCRIPTION
         "**NOTE: this object is obsolete."
      ::= {  snetAdaptrEntry 51 }
    
    snetAdaptrYHaltLow OBJECT-TYPE
      SYNTAX  Counter
      ACCESS  read-only
      STATUS  obsolete
      DESCRIPTION
         "**NOTE: this object is obsolete."
      ::= {  snetAdaptrEntry 52 }
    
    snetAdaptrYHaltHi OBJECT-TYPE
      SYNTAX  Counter
      ACCESS  read-only
      STATUS  obsolete
      DESCRIPTION
         "**NOTE: this object is obsolete."
     ::= {  snetAdaptrEntry 53 }

    snetAdaptrHaltLow OBJECT-TYPE
      SYNTAX  Counter
      ACCESS  read-only
      STATUS  obsolete
      DESCRIPTION
         "**NOTE: this object is obsolete."
      ::= {  snetAdaptrEntry 54 }
    
    snetAdaptrHaltHi OBJECT-TYPE
      SYNTAX  Counter
      ACCESS  read-only
      STATUS  obsolete
      DESCRIPTION
         "**NOTE: this object is obsolete."
      ::= {  snetAdaptrEntry 55 }    

    snetAdaptrXLxSecondExceptionsLow OBJECT-TYPE
      SYNTAX  Counter
      ACCESS  read-only
      STATUS  obsolete
      DESCRIPTION
         "**NOTE: this object is obsolete."
      ::= {  snetAdaptrEntry 56 }

    snetAdaptrXLxSecondExceptionsHi OBJECT-TYPE
      SYNTAX  Counter
      ACCESS  read-only
      STATUS  obsolete
      DESCRIPTION
          "**NOTE: this object is obsolete."
      ::= {  snetAdaptrEntry 57 }

    snetAdaptrYLxSecondExceptionsLow OBJECT-TYPE
      SYNTAX  Counter
      ACCESS  read-only
      STATUS  obsolete
      DESCRIPTION
         "**NOTE: this object is obsolete."
      ::= {  snetAdaptrEntry 58 }
 
    snetAdaptrYLxSecondExceptionsHi OBJECT-TYPE
      SYNTAX  Counter
      ACCESS  read-only
      STATUS  obsolete
      DESCRIPTION
         "**NOTE: this object is obsolete."
      ::= {  snetAdaptrEntry 59 }
 
    snetAdaptrLxSecondExceptionsLow OBJECT-TYPE
      SYNTAX  Counter
      ACCESS  read-only
      STATUS  obsolete
      DESCRIPTION
         "**NOTE: this object is obsolete."
      ::= {  snetAdaptrEntry 60 }
 
    snetAdaptrLxSecondExceptionsHi OBJECT-TYPE
      SYNTAX  Counter
      ACCESS  read-only
      STATUS  obsolete
      DESCRIPTION
         "**NOTE: this object is obsolete."
      ::= {  snetAdaptrEntry 61 }
 
    snetAdaptrXLxCrcErrorsLow OBJECT-TYPE
      SYNTAX  Counter
      ACCESS  read-only
      STATUS  obsolete
      DESCRIPTION
         "**NOTE: this object is obsolete."
      ::= {  snetAdaptrEntry 62 }
 
    snetAdaptrXLxCrcErrorsHi OBJECT-TYPE
      SYNTAX  Counter
      ACCESS  read-only
      STATUS  obsolete
      DESCRIPTION
         "**NOTE: this object is obsolete."
      ::= {  snetAdaptrEntry 63 }
 
    snetAdaptrYLxCrcErrorsLow OBJECT-TYPE
      SYNTAX  Counter
      ACCESS  read-only
      STATUS  obsolete
      DESCRIPTION
         "**NOTE: this object is obsolete."
      ::= {  snetAdaptrEntry 64 }
 
    snetAdaptrYLxCrcErrorsHi OBJECT-TYPE
      SYNTAX  Counter
      ACCESS  read-only
      STATUS  obsolete
      DESCRIPTION
         "**NOTE: this object is obsolete."
      ::= {  snetAdaptrEntry 65 }
 
    snetAdaptrLxCrcErrorsLow OBJECT-TYPE
      SYNTAX  Counter
      ACCESS  read-only
      STATUS  obsolete
      DESCRIPTION
         "**NOTE: this object is obsolete."
      ::= {  snetAdaptrEntry 66 }
 
    snetAdaptrLxCrcErrorsHi OBJECT-TYPE
      SYNTAX  Counter
      ACCESS  read-only
      STATUS  obsolete
      DESCRIPTION
         "**NOTE: this object is obsolete."
      ::= {  snetAdaptrEntry 67 }
 
    snetAdaptrXLxIllegalCommandsLow OBJECT-TYPE
      SYNTAX  Counter
      ACCESS  read-only
      STATUS  obsolete
      DESCRIPTION
         "**NOTE: this object is obsolete."
      ::= {  snetAdaptrEntry 68 }
 
    snetAdaptrXLxIllegalCommandsHi OBJECT-TYPE
      SYNTAX  Counter
      ACCESS  read-only
      STATUS  obsolete
      DESCRIPTION
         "**NOTE: this object is obsolete."
      ::= {  snetAdaptrEntry 69 }
 
    snetAdaptrYLxIllegalCommandsLow OBJECT-TYPE
      SYNTAX  Counter
      ACCESS  read-only
      STATUS  obsolete
      DESCRIPTION
         "**NOTE: this object is obsolete."
      ::= {  snetAdaptrEntry 70 }

    snetAdaptrYLxIllegalCommandsHi OBJECT-TYPE
      SYNTAX  Counter
      ACCESS  read-only
      STATUS  obsolete
      DESCRIPTION
         "**NOTE: this object is obsolete."
      ::= {  snetAdaptrEntry 71 }

    snetAdaptrLxIllegalCommandsLow OBJECT-TYPE
      SYNTAX  Counter
      ACCESS  read-only
      STATUS  obsolete
      DESCRIPTION
         "**NOTE: this object is obsolete."
      ::= {  snetAdaptrEntry 72 }

    snetAdaptrLxIllegalCommandsHi OBJECT-TYPE
      SYNTAX  Counter
      ACCESS  read-only
      STATUS  obsolete
      DESCRIPTION
         "**NOTE: this object is obsolete."
      ::= {  snetAdaptrEntry 73 }

    snetAdaptrXLxFifoOverrunLow OBJECT-TYPE
      SYNTAX  Counter
      ACCESS  read-only
      STATUS  obsolete
      DESCRIPTION
         "**NOTE: this object is obsolete."
      ::= {  snetAdaptrEntry 74 }
 
    snetAdaptrXLxFifoOverrunHi OBJECT-TYPE
      SYNTAX  Counter
      ACCESS  read-only
      STATUS  obsolete
      DESCRIPTION
         "**NOTE: this object is obsolete."
      ::= {  snetAdaptrEntry 75 }
 
    snetAdaptrYLxFifoOverrunLow OBJECT-TYPE
      SYNTAX  Counter
      ACCESS  read-only
      STATUS  obsolete
      DESCRIPTION
         "**NOTE: this object is obsolete."
      ::= {  snetAdaptrEntry 76 }
 
    snetAdaptrYLxFifoOverrunHi OBJECT-TYPE
      SYNTAX  Counter
      ACCESS  read-only
      STATUS  obsolete
      DESCRIPTION
         "**NOTE: this object is obsolete."
      ::= {  snetAdaptrEntry 77 }

    snetAdaptrLxFifoOverrunLow OBJECT-TYPE
      SYNTAX  Counter
      ACCESS  read-only
      STATUS  obsolete
      DESCRIPTION
         "**NOTE: this object is obsolete."
      ::= {  snetAdaptrEntry 78 }
 
    snetAdaptrLxFifoOverrunHi OBJECT-TYPE
      SYNTAX  Counter
      ACCESS  read-only
      STATUS  obsolete
      DESCRIPTION
         "**NOTE: this object is obsolete."
      ::= {  snetAdaptrEntry 79 }
  
    snetAdaptrXLxKeepAliveErrorsLow OBJECT-TYPE
      SYNTAX  Counter
      ACCESS  read-only
      STATUS  obsolete
      DESCRIPTION
         "**NOTE: this object is obsolete."
      ::= {  snetAdaptrEntry 80 }
 
    snetAdaptrXLxKeepAliveErrorsHi OBJECT-TYPE
      SYNTAX  Counter
      ACCESS  read-only
      STATUS  obsolete
      DESCRIPTION
         "**NOTE: this object is obsolete."
      ::= {  snetAdaptrEntry 81 }
 
    snetAdaptrYLxKeepAliveErrorsLow OBJECT-TYPE
      SYNTAX  Counter
      ACCESS  read-only
      STATUS  obsolete
      DESCRIPTION
         "**NOTE: this object is obsolete."
      ::= {  snetAdaptrEntry 82 }
 
    snetAdaptrYLxKeepAliveErrorsHi OBJECT-TYPE
      SYNTAX  Counter
      ACCESS  read-only
      STATUS  obsolete
      DESCRIPTION
         "**NOTE: this object is obsolete."
      ::= {  snetAdaptrEntry 83 }

    snetAdaptrLxKeepAliveErrorsLow OBJECT-TYPE
      SYNTAX  Counter
      ACCESS  read-only
      STATUS  obsolete
      DESCRIPTION
         "**NOTE: this object is obsolete."
      ::= {  snetAdaptrEntry 84 }
 
    snetAdaptrLxKeepAliveErrorsHi OBJECT-TYPE
      SYNTAX  Counter
      ACCESS  read-only
      STATUS  obsolete
      DESCRIPTION
         "**NOTE: this object is obsolete."
      ::= {  snetAdaptrEntry 85 }
  
    snetAdaptrXLxEFifoOverflowLow OBJECT-TYPE
      SYNTAX  Counter
      ACCESS  read-only
      STATUS  obsolete
      DESCRIPTION
         "**NOTE: this object is obsolete."
      ::= {  snetAdaptrEntry 86 }
 
    snetAdaptrXLxEFifoOverflowHi OBJECT-TYPE
      SYNTAX  Counter
      ACCESS  read-only
      STATUS  obsolete
      DESCRIPTION
         "**NOTE: this object is obsolete."
      ::= {  snetAdaptrEntry 87 }
 
    snetAdaptrYLxEFifoOverflowLow OBJECT-TYPE
      SYNTAX  Counter
      ACCESS  read-only
      STATUS  obsolete
      DESCRIPTION
         "**NOTE: this object is obsolete."
      ::= {  snetAdaptrEntry 88 }
 
    snetAdaptrYLxEFifoOverflowHi OBJECT-TYPE
      SYNTAX  Counter
      ACCESS  read-only
      STATUS  obsolete
      DESCRIPTION
         "**NOTE: this object is obsolete."
      ::= {  snetAdaptrEntry 89 }

    snetAdaptrLxEFifoOverflowLow OBJECT-TYPE
      SYNTAX  Counter
      ACCESS  read-only
      STATUS  obsolete
      DESCRIPTION
         "**NOTE: this object is obsolete."
      ::= {  snetAdaptrEntry 90 }
 
    snetAdaptrLxEFifoOverflowHi OBJECT-TYPE
      SYNTAX  Counter
      ACCESS  read-only
      STATUS  obsolete
      DESCRIPTION
         "**NOTE: this object is obsolete."
      ::= {  snetAdaptrEntry 91 }
  
    snetAdaptrXRecentLxSymbol OBJECT-TYPE
      SYNTAX  INTEGER
      ACCESS  read-only
      STATUS  obsolete
      DESCRIPTION
         "**NOTE: this object is obsolete."
      ::= {  snetAdaptrEntry 92 }
 
    snetAdaptrXPreviousLxSymbol OBJECT-TYPE
      SYNTAX  INTEGER
      ACCESS  read-only
      STATUS  obsolete
      DESCRIPTION
         "**NOTE: this object is obsolete."
      ::= {  snetAdaptrEntry 93 }
 
    snetAdaptrYRecentLxSymbol OBJECT-TYPE
      SYNTAX  INTEGER
      ACCESS  read-only
      STATUS  obsolete
      DESCRIPTION
         "**NOTE: this object is obsolete."
      ::= {  snetAdaptrEntry 94 }

    snetAdaptrYPreviousLxSymbol OBJECT-TYPE
      SYNTAX  INTEGER
      ACCESS  read-only
      STATUS  obsolete
      DESCRIPTION
         "**NOTE: this object is obsolete."
      ::= {  snetAdaptrEntry 95 }

    snetAdaptrIntrPktDroppedLow OBJECT-TYPE
      SYNTAX  Counter
      ACCESS  read-only
      STATUS  obsolete
      DESCRIPTION
         "**NOTE: this object is obsolete."
      ::= {  snetAdaptrEntry 96 }
 
    snetAdaptrIntrPktDroppedHi OBJECT-TYPE
      SYNTAX  Counter
      ACCESS  read-only
      STATUS  obsolete
      DESCRIPTION
         "**NOTE: this object is obsolete."
      ::= {  snetAdaptrEntry 97 }

    snetAdaptrBteDoneInterrupts1Low OBJECT-TYPE
      SYNTAX  Counter
      ACCESS  read-only
      STATUS  mandatory
      DESCRIPTION
         "The count of bte done interrupts for each BTEqueue.
	  Low 32 bits."
      ::= {  snetAdaptrEntry 98 }
 
    snetAdaptrBteDoneInterrupts1Hi OBJECT-TYPE
      SYNTAX  Counter
      ACCESS  read-only
      STATUS  mandatory
      DESCRIPTION
         "The count of bte done interrupts for each BTEqueue.
	  High 32 bits."
      ::= {  snetAdaptrEntry 99 }

    snetAdaptrBteDoneInterrupts2Low OBJECT-TYPE
      SYNTAX  Counter
      ACCESS  read-only
      STATUS  mandatory
      DESCRIPTION
         "The count of bte done interrupts for each BTEqueue.
	  Low 32 bits.."
      ::= {  snetAdaptrEntry 100 }
 
    snetAdaptrBteDoneInterrupts2Hi OBJECT-TYPE
      SYNTAX  Counter
      ACCESS  read-only
      STATUS  mandatory
      DESCRIPTION
         "The count of bte done interrupts for each BTEqueue.
	  High 32 bits."
      ::= {  snetAdaptrEntry 101 }

    snetAdaptrNodeMfgId OBJECT-TYPE
      SYNTAX  INTEGER
      ACCESS  read-only
      STATUS  mandatory
      DESCRIPTION
         "Node Manufacturing ID"
      ::= {  snetAdaptrEntry 102 }

    snetAdaptrNodePartNumber OBJECT-TYPE
      SYNTAX  INTEGER
      ACCESS  read-only
      STATUS  mandatory
      DESCRIPTION
         "Node Part Number"
      ::= {  snetAdaptrEntry 103 }

    snetAdaptrNodeSerialNumber OBJECT-TYPE
      SYNTAX  DisplayString
      ACCESS  read-only
      STATUS  mandatory
      DESCRIPTION
         "Node Serial Number"
      ::= {  snetAdaptrEntry 104 }

   snetAdaptrRevMajor  OBJECT-TYPE
      SYNTAX  INTEGER
      ACCESS  read-only
      STATUS  mandatory
      DESCRIPTION
         "Adapter driver major revision level"
      ::= {  snetAdaptrEntry 106}

   snetAdaptrRevMinor  OBJECT-TYPE
      SYNTAX  INTEGER
      ACCESS  read-only
      STATUS  mandatory
      DESCRIPTION
         "Adapter driver minor revision level"
      ::= {  snetAdaptrEntry 107}
 
  snetAdaptrNeighborTable OBJECT-TYPE
      SYNTAX  SEQUENCE OF SnetAdaptrNeighborEntry
      ACCESS  not-accessible
      STATUS  mandatory
      DESCRIPTION
         "ServerNet adapter neighboring data."
      ::= { snetAdaptr 3 }

   snetAdaptrNeighborEntry OBJECT-TYPE
      SYNTAX  SnetAdaptrNeighborEntry
      ACCESS  not-accessible
      STATUS  mandatory
      DESCRIPTION
         "An entry containing ServerNet adapter neighbor data."
      INDEX   { snetAdaptrIndex, snetAdaptrNeighborIndex }
      ::= { snetAdaptrNeighborTable 1 }

   SnetAdaptrNeighborEntry ::= SEQUENCE
   {
	snetAdaptrNeighborIndex		  INTEGER,
	snetAdaptrNeighborNodeType	  INTEGER,
	snetAdaptrNeighborflState         INTEGER,
	snetAdaptrNeighborflAttrib	  INTEGER,
	snetAdaptrNeighborNodeId	  DisplayString,
	snetAdaptrNeighborName 	  	  DisplayString,
	snetAdaptrNeighborDomain	  DisplayString,
	snetAdaptrNeighborMfgId  	  INTEGER,
	snetAdaptrNeighborPartNumber 	  INTEGER,
	snetAdaptrNeighborSerialNumber    DisplayString,
	snetAdaptrNeighborFabric          INTEGER 
   }

   snetAdaptrNeighborIndex OBJECT-TYPE
      SYNTAX  INTEGER (0..225)
      ACCESS  read-only
      STATUS  mandatory
      DESCRIPTION
         "ServerNet adapter neighbor data index.
         Indicates the port the neighbor is
         connected to."
     ::= { snetAdaptrNeighborEntry 1 }

   snetAdaptrNeighborNodeType  OBJECT-TYPE
       SYNTAX  INTEGER{
           unknown(1),
           endNode(2),
           autoConfiguredIO(3),
	   manualConfiguredIO(4),
           switch(5)
           }
       ACCESS  read-only
       STATUS  mandatory
       DESCRIPTION
         "ServerNet adapter's neighbor Node type.
	  Valid values are
            Unknown(1),
	    End Node(2),
            Auto-Configured IO(3),
	    Manual-Configutred IO(4),
            Switch(5)"
     ::= {snetAdaptrNeighborEntry 2 }
 
   snetAdaptrNeighborflState OBJECT-TYPE
      SYNTAX  INTEGER{
          unConfigured(1),
          configured(2)
          }
      ACCESS  read-only
      STATUS  mandatory
      DESCRIPTION
         "ServerNet adapter's neighbor node state.
          Valid values are
             unConfigured(1),
      	     configured(2)"
     ::= { snetAdaptrNeighborEntry 3 }
     
   snetAdaptrNeighborflAttrib OBJECT-TYPE
      SYNTAX  INTEGER (0..225)
      ACCESS  read-only
      STATUS  mandatory
      DESCRIPTION
         "ServerNet adapter's neighbor node attributes.(Not supported)"
     ::= { snetAdaptrNeighborEntry 4 }

   snetAdaptrNeighborNodeId OBJECT-TYPE
      SYNTAX  DisplayString (SIZE(0..16))
      ACCESS  read-only
      STATUS  mandatory
      DESCRIPTION
         "ServerNet adapter's neighbor node High level Id."
     ::= { snetAdaptrNeighborEntry 5 } 

   snetAdaptrNeighborName  OBJECT-TYPE
       SYNTAX  DisplayString (SIZE(0..19))
       ACCESS  read-only
       STATUS  mandatory
       DESCRIPTION
         "ServerNet adapter's neighbor node name."
     ::= {snetAdaptrNeighborEntry 6 }

   snetAdaptrNeighborDomain  OBJECT-TYPE
       SYNTAX  DisplayString (SIZE(0..19))
       ACCESS  read-only
       STATUS  mandatory
       DESCRIPTION
         "ServerNet adapter's neighbor node Domain.(Not supported.)"
     ::= {snetAdaptrNeighborEntry 7 }

   snetAdaptrNeighborMfgId OBJECT-TYPE
      SYNTAX  INTEGER 
      ACCESS  read-only
      STATUS  mandatory
      DESCRIPTION
         "ServerNet adapter's neighbor node manufacturing ID."
     ::= { snetAdaptrNeighborEntry 8 }
 
   snetAdaptrNeighborPartNumber OBJECT-TYPE
      SYNTAX  INTEGER  
      ACCESS  read-only
      STATUS  mandatory
      DESCRIPTION
         "ServerNet adapter's neighbor node part number."
     ::= { snetAdaptrNeighborEntry 9 }

   snetAdaptrNeighborSerialNumber  OBJECT-TYPE
       SYNTAX  DisplayString 
       ACCESS  read-only
       STATUS  mandatory
       DESCRIPTION
         "ServerNet adapter's neighbor node serial number."
     ::= {snetAdaptrNeighborEntry 10 }

   snetAdaptrNeighborFabric OBJECT-TYPE
      SYNTAX  INTEGER{
            xFabric (1),
            yFabric (2),
            bothFabrics (3),
            notDefined(4)
          } 
      ACCESS  read-only
      STATUS  mandatory
      DESCRIPTION
         "ServerNet adapter's neighbor node fabric.
          Valid values are
            1 = X Fabric
            2 = Y Fabric
            3 = both Fabrics
            4 = Not Defined"
     ::= { snetAdaptrNeighborEntry 11 }
               
  snetAdaptrNodeIDTable OBJECT-TYPE
      SYNTAX  SEQUENCE OF SnetAdaptrNodeIDEntry
      ACCESS  not-accessible
      STATUS  mandatory
      DESCRIPTION
         "ServerNet adapter node ID table."
      ::= { snetAdaptr 4 }

   snetAdaptrNodeIDEntry OBJECT-TYPE
      SYNTAX  SnetAdaptrNodeIDEntry
      ACCESS  not-accessible
      STATUS  mandatory
      DESCRIPTION
         "An entry containing ServerNet adapter node ID data."
      INDEX   { snetAdaptrNodeIDIndex }
      ::= { snetAdaptrNodeIDTable 1 }

   SnetAdaptrNodeIDEntry ::= SEQUENCE
   {
	snetAdaptrNodeIDIndex		INTEGER,
	snetAdapterNodeID	        DisplayString 
	
   }

   snetAdaptrNodeIDIndex OBJECT-TYPE
      SYNTAX  INTEGER 
      ACCESS  read-only
      STATUS  mandatory
      DESCRIPTION
         "ServerNet node data index.
         The adapter index indicates which ServerNet adapter data instance
         this table entry belongs."
     ::= { snetAdaptrNodeIDEntry 1 }

   snetAdapterNodeID  OBJECT-TYPE
       SYNTAX  DisplayString 
       ACCESS  read-only
       STATUS  mandatory
       DESCRIPTION
         "ServerNet Node ID."
     ::= {snetAdaptrNodeIDEntry 2 }
 
    snetAdaptrOsCommonModuleTable OBJECT-TYPE
       SYNTAX SEQUENCE OF SnetAdaptrOsCommonModuleEntry
       ACCESS  not-accessible
       STATUS  mandatory
       DESCRIPTION
        "A table of software modules that provide an interface to the 
         ServerNet adapter."
     ::= {snetAdaptrOsCommonGroup 1}

     snetAdaptrOsCommonModuleEntry OBJECT-TYPE
       SYNTAX  SnetAdaptrOsCommonModuleEntry
       ACCESS  not-accessible
       STATUS  mandatory
       DESCRIPTION
        "A description of software modules that provide an interface  
         to the ServerNet adapter."
       INDEX {snetAdaptrOsCommonModuleIndex} 
     ::= {snetAdaptrOsCommonModuleTable 1}

     SnetAdaptrOsCommonModuleEntry ::= SEQUENCE {
        snetAdaptrOsCommonModuleIndex     INTEGER,
        snetAdaptrOsCommonModuleName      DisplayString,
        snetAdaptrOsCommonModuleVersion   DisplayString,
        snetAdaptrOsCommonModuleDate      OCTET STRING,
        snetAdaptrOsCommonModulePurpose   DisplayString
     }

     snetAdaptrOsCommonModuleIndex  OBJECT-TYPE
       SYNTAX  INTEGER  (0..255)
       ACCESS  read-only
       STATUS  mandatory
       DESCRIPTION
         "A unique index for the module description."
     ::= {snetAdaptrOsCommonModuleEntry 1 }

     snetAdaptrOsCommonModuleName  OBJECT-TYPE
       SYNTAX  DisplayString (SIZE(0..255))
       ACCESS  read-only
       STATUS  mandatory
       DESCRIPTION
         "The module name."
     ::= {snetAdaptrOsCommonModuleEntry 2 }

     snetAdaptrOsCommonModuleVersion  OBJECT-TYPE
       SYNTAX  DisplayString (SIZE(0..19))
       ACCESS  read-only
       STATUS  mandatory
       DESCRIPTION
         "The module version in XX.YY format.
          XX is the major version and YY is the minor version number.
          This field will be a null (size 0) string if the agent cannot
          provide the module version."
     ::= {snetAdaptrOsCommonModuleEntry 3 }
       
     snetAdaptrOsCommonModuleDate  OBJECT-TYPE
       SYNTAX  OCTET STRING (SIZE (7))
       ACCESS  read-only
       STATUS  mandatory
       DESCRIPTION
         "The module date.

          field   octets   contents          range
          =====   ======   ========          =====
            1      1-2     year              0..65536  
            2       3      month             1..12
            3       4      day               1..31
            4       5      hour              0..23
            5       6      minute            0..59
            6       7      second            0..60
                           (use 60 for leap second)

          This field will be set to year = 0 if the agent cannot provide
          the module date.  The hour, minute, and second field will be set
          to zero (0) if they are not relevant.  The year field is set 
          with the most significant octet first."
      ::= {snetAdaptrOsCommonModuleEntry 4 }

     snetAdaptrOsCommonModulePurpose  OBJECT-TYPE
       SYNTAX  DisplayString (SIZE(0..255))
       ACCESS  read-only
       STATUS  mandatory
       DESCRIPTION
         "The purpose of the module described in this entry."
     ::= {snetAdaptrOsCommonModuleEntry 5 }


--
--  ServerNet Trap Definitions
--

   snetAdaptrStatusChange TRAP-TYPE
      ENTERPRISE serverNet
      VARIABLES  { snetAdaptrStatus, snetAdaptrSnetID }
      DESCRIPTION
         "ServerNet Controller Status Change.

         The agent has detected a change in the controller
         status of a ServerNet Controller.  The variable
         snetAdaptrStatus indicates the current controller status."

         --#TYPE "ServerNet Controller Status Change"
         --#SUMMARY "Status is now %d."
         --#ARGUMENTS {2}
         --#SEVERITY CRITICAL
         --#TIMEINDEX 99
      ::= 1

   snetAdaptrXPortStatusChange TRAP-TYPE
      ENTERPRISE serverNet
      VARIABLES  { snetAdaptrXPortStatus, snetAdaptrSnetID }
      DESCRIPTION
         "ServerNet Controller X-Port Status Change.

         The agent has detected a change in the controller
         status of a the X-Port of the ServerNet Controller.  The
         variable snetAdaptrXPortStatus indicates the current
         X-Port controller status."

         --#TYPE "ServerNet X-Port Status Change"
         --#SUMMARY "Status is now %d."
         --#ARGUMENTS {0}
         --#SEVERITY CRITICAL
         --#TIMEINDEX 99
      ::= 2

   snetAdaptrYPortStatusChange TRAP-TYPE
      ENTERPRISE serverNet
      VARIABLES  { snetAdaptrYPortStatus, snetAdaptrSnetID1 }
      DESCRIPTION
         "ServerNet Controller Y-Port Status Change.

         The agent has detected a change in the controller
         status of a the Y-Port of the ServerNet Controller.  The
         variable snetAdaptrYPortStatus indicates the current
         Y-Port controller status."

         --#TYPE "ServerNet Y-Port Status Change"
         --#SUMMARY "Status is now %d."
         --#ARGUMENTS {0}
         --#SEVERITY CRITICAL
         --#TIMEINDEX 99
      ::= 3
 
 snetAdaptrTimeoutErrorsChange TRAP-TYPE
      ENTERPRISE serverNet
      VARIABLES  { snetAdaptrTimeoutErrorsLow, snetAdaptrTimeoutErrorsHi,snetAdaptrSnetID }
      DESCRIPTION
         "This trap is obsolete.  It is no longer generated.
          The trap number is reserved for compatibility."

         --#TYPE "ServerNet Timeout Error Change"
         --#SUMMARY "Status is now %d."
         --#ARGUMENTS {0}
         --#SEVERITY CRITICAL
         --#TIMEINDEX 99
      ::= 4

END
