--
-- WS-INFRA-SMI-MIB.my
-- MIB generated by MG-SOFT Visual MIB Builder Version 6.0  Build 88
-- Thursday, May 01, 2008 at 16:49:42
--

	WS-INFRA-SMI-MIB DEFINITIONS ::= BEGIN
 
		IMPORTS
			MODULE-IDENTITY			
				FROM SNMPv2-SMI			
			wsInfra			
				FROM WS-SMI;
	
	
		-- 1.3.6.1.4.1.388.14.1.1
		wslInfraMIB MODULE-IDENTITY 
			LAST-UPDATED "200805011900Z"		-- May 01, 2008 at 19:00 GMT
			ORGANIZATION 
				"Symbol Technology"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"infrastructure MIB"
			REVISION "200805011327Z"		-- May 01, 2008 at 13:27 GMT
			DESCRIPTION 
				"02a02
				Added wsInfraSmtpNotify"
			REVISION "200701121154Z"		-- January 12, 2007 at 11:54 GMT
			DESCRIPTION 
				"02a01"
			REVISION "200605241442Z"		-- May 24, 2006 at 14:42 GMT
			DESCRIPTION 
				"01a09"
			REVISION "200512191035Z"		-- December 19, 2005 at 10:35 GMT
			DESCRIPTION 
				"01a08"
			REVISION "200507281900Z"		-- July 28, 2005 at 19:00 GMT
			DESCRIPTION 
				"01a07"
			REVISION "200506241100Z"		-- June 24, 2005 at 11:00 GMT
			DESCRIPTION 
				"01a06"
			REVISION "200506221136Z"		-- June 22, 2005 at 11:36 GMT
			DESCRIPTION 
				"01a05"
			REVISION "200505231736Z"		-- May 23, 2005 at 17:36 GMT
			DESCRIPTION 
				"01a04"
			REVISION "200505041609Z"		-- May 04, 2005 at 16:09 GMT
			DESCRIPTION 
				"01a03"
			REVISION "200505041558Z"		-- May 04, 2005 at 15:58 GMT
			DESCRIPTION 
				"01a02"
			REVISION "200505041032Z"		-- May 04, 2005 at 10:32 GMT
			DESCRIPTION 
				"01a01"
			::= { wsInfra 1 }

		
	
	
--
-- Node definitions
--
	
		-- 1.3.6.1.4.1.388.14.1.2
		wsInfraFileMgmt OBJECT IDENTIFIER ::= { wsInfra 2 }

		
		-- 1.3.6.1.4.1.388.14.1.3
		wsInfraSysMsg OBJECT IDENTIFIER ::= { wsInfra 3 }

		
		-- 1.3.6.1.4.1.388.14.1.5
		wsInfraPM OBJECT IDENTIFIER ::= { wsInfra 5 }

		
		-- 1.3.6.1.4.1.388.14.1.6
		wsInfraDiag OBJECT IDENTIFIER ::= { wsInfra 6 }

		
		-- 1.3.6.1.4.1.388.14.1.8
		wsInfraCluster OBJECT IDENTIFIER ::= { wsInfra 8 }

		
		-- 1.3.6.1.4.1.388.14.1.9
		wsInfraLic OBJECT IDENTIFIER ::= { wsInfra 9 }

		
		-- 1.3.6.1.4.1.388.14.1.10
		wsInfraNTP OBJECT IDENTIFIER ::= { wsInfra 10 }

		
		-- 1.3.6.1.4.1.388.14.1.11
		wsInfraAutoUpdate OBJECT IDENTIFIER ::= { wsInfra 11 }

		
		-- 1.3.6.1.4.1.388.14.1.12
		wsInfraSmtpNotify OBJECT IDENTIFIER ::= { wsInfra 12 }

		
	
	END

--
-- WS-INFRA-SMI-MIB.my
--
