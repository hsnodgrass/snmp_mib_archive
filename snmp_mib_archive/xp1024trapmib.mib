--
-- Hitachi RAID450 SNMP Agent MIB definition.
-- 04/16/03

RAID450MIB DEFINITIONS ::= BEGIN

IMPORTS
	OBJECT-TYPE		FROM RFC-1212
	TRAP-TYPE		FROM RFC-1215
	DisplayString	FROM RFC1213-MIB
	enterprises		FROM RFC1155-SMI;

--
-- Hitachi and RAID sub-tree
--

	hitachi		OBJECT IDENTIFIER ::= { enterprises 116 }
	system		OBJECT IDENTIFIER ::= { hitachi 3 }
	storage		OBJECT IDENTIFIER ::= { system 11 }
	raid		OBJECT IDENTIFIER ::= { storage 4 }
	raidDummy	OBJECT IDENTIFIER ::= { raid 1 }
	raidRoot		OBJECT IDENTIFIER ::= { raidDummy 1 }


-- Trap definition
--
	raideventUseracute	TRAP-TYPE
		ENTERPRISE	raidRoot
		VARIABLES	{
			eventTrapSerialNumber,
			eventTrapNickname,
			eventTrapREFCODE,
			eventTrapPartsID
		}
		DESCRIPTION	
			"The impact of this event on the subsystem is acute."
		::= 1

	raideventUserserious	TRAP-TYPE
		ENTERPRISE	raidRoot
		VARIABLES	{
			eventTrapSerialNumber,
			eventTrapNickname,
			eventTrapREFCODE,
			eventTrapPartsID
		}
		DESCRIPTION	
			"The impact of this event on the subsystem is serious."
		::= 2

	raideventUsermoderate	TRAP-TYPE
		ENTERPRISE	raidRoot
		VARIABLES	{
			eventTrapSerialNumber,
			eventTrapNickname,
			eventTrapREFCODE,
			eventTrapPartsID
		}
		DESCRIPTION	
			"The impact of this event on the subsystem is moderate."
		::= 3

	raideventUserservice	TRAP-TYPE
		ENTERPRISE	raidRoot
		VARIABLES	{
			eventTrapSerialNumber,
			eventTrapNickname,
			eventTrapREFCODE,
			eventTrapPartsID
		}
		DESCRIPTION	
			"The impact of this event on the subsystem is low."
		::= 4

	raidCommandFinished	TRAP-TYPE
		ENTERPRISE	raidRoot
		VARIABLES	{
			commandSerialNumber,
			commandManagerName,
			commandKind,
			commandStatus
		}
		DESCRIPTION
			"Required command was finished."
		::= 100

END
