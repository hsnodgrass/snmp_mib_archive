RC-ERROR-MIB DEFINITIONS ::= BEGIN

IMPORTS
    MODULE-IDENTITY, OBJECT-TYPE, Integer32
        FROM SNMPv2-SMI
    DisplayString, TruthValue
        FROM SNMPv2-TC
    rcError
        FROM RAPID-CITY;

rcErrorMib MODULE-IDENTITY
       LAST-UPDATED     "200512080000Z"
       ORGANIZATION     "Bay Networks, Rapid-City Group"
       CONTACT-INFO     "Yu-Ten Lee
                     	 Postal: 	    Nortel Networks, Inc. 
                           	    4655 Great America Parkway 
                     		    Santa Clara, CA 95052-8185 

                   	 Tel: 	408-495-2560
                   	 Fax: 	408-495-6680
                	 E-mail:	ylee@nortelnetworks.com"

       DESCRIPTION 	"Enterprise MIB for the Accelar product family."

       REVISION "200512080000Z" -- 08 Dec 2005
       DESCRIPTION "Version 65: Added error codes 6971-6973, 8554"

       REVISION "200511220000Z" -- 22 Nov 2005
       DESCRIPTION "Version 64: Added more ipv6 error codes; up to 7486"

       REVISION "200511090000Z" -- 09 Nov 2005
       DESCRIPTION "Version 63: Added 5708"

       REVISION "200511020000Z" -- 02 Nov 2005
       DESCRIPTION "Version 62: Added 8552 - 8553"

       REVISION "200510250000Z" -- 25 Oct 2005
       DESCRIPTION "Version 61: Added 8549 - 8551"

       REVISION "200510180000Z" -- 18 Oct 2005
       DESCRIPTION "Version 60: Added 8546 - 8548 and modified 8513 and 8525"

       REVISION "200510130000Z" -- 13 Oct 2005
       DESCRIPTION "Version 59: Added 8534 - 8545"

       REVISION "200510070000Z" -- 07 Oct 2005
       DESCRIPTION "Version 58: Added 6709"

       REVISION "200510050000Z" -- 05 Oct 2005
       DESCRIPTION "Version 57: Added 6706-6708"

       REVISION "200509300000Z" -- 30 Sep 2005
       DESCRIPTION "Version 56: Removed 631-635, Added 1148-1149, 1530-1531, 6705, 7467-7476, 9380-9381, 9107, 9417"

       REVISION "200509280000Z" -- 28 Sep 2005
       DESCRIPTION "Version 55: Add error code 635."

       REVISION "200509260000Z" -- 26 Sep 2005
       DESCRIPTION "Version 54: Added error codes 633-634 for ECMP 8-path"

       REVISION "200509230000Z" -- 23 Sep 2005
       DESCRIPTION "Version 53: Modify error codes 1147, 6967, and 6969.  Add new error code 6970."

       REVISION "200509210000Z" -- 21 Sep 2005
       DESCRIPTION "Version 52: Added error code 6969"

       REVISION "200509080000Z" -- 08 Sep 2005
       DESCRIPTION "Version 51: Added error codes for IPv6 & SLPP & NSNA"

       REVISION "200509071200Z" -- 07 Sep 2005
       DESCRIPTION "Version 50: Added error codes 6961-6968, 8529-8533"

       REVISION "200508311200Z" -- 31 Aug 2005
       DESCRIPTION "Version 49: Added error codes 9605, 8526-8528, and initial error codes for VRF 8601-8603"

       REVISION "200508261200Z" -- 26 Aug 2005
       DESCRIPTION "Version 48: Added initial error codes for IPv6 - 74xx"

       REVISION "200508260000Z" -- 26 August 2005
       DESCRIPTION "Version 47: Added new error codes 1146-1147 and 8501-8525."

       REVISION "200508250000Z" -- 25 Aug 2005
       DESCRIPTION "Version 46: Added error codes 8424, 8425"

       REVISION "200508100000Z" -- 10 Aug 2005
       DESCRIPTION "Version 45: Added error codes 2539, 4110"

       REVISION "200508030000Z" -- 03 Aug 2005
       DESCRIPTION "Version 44: Added error codes 1145, 6513"

       REVISION "200507250000Z" -- 25 July 2005
       DESCRIPTION "Version 43: Added error codes 3618-3620, 8422-8423, 9379"

       REVISION "200507140000Z" -- 14 July 2005
       DESCRIPTION "Version 42: Added error codes 1141-1144."

       REVISION "200507060000Z" -- 06 July 2005
       DESCRIPTION "Version 41: Added NSNA error codes 8401-8421.  Also, added 1140."

       REVISION "200506011200Z" -- 01 June 2005
       DESCRIPTION "Version 40: Added new error code 1529."

       REVISION "200505241200Z" -- 24 May 2005
       DESCRIPTION "Version 39: Added new error codes for NSNA.  Reorganized existing error codes so that they appear in ascending order."

       REVISION "200505240000Z" -- 24 May 2005
       DESCRIPTION "Version 38: Added new error codes 8332 and 8333."

       REVISION "200505230000Z" -- 23 May 2005
       DESCRIPTION "Version 37: Added new error code 8205."

       REVISION "200505170000Z" -- 17 May 2005
       DESCRIPTION "Version 36: Added new error code 2604."

       REVISION "200505160000Z" -- 16 May 2005
       DESCRIPTION "Version 35: Renamed error codes 8311-8312 and 8325-8329."

       REVISION "200505131200Z" -- 13 May 2005
       DESCRIPTION "Version 34: Added error code 8331"

       REVISION "200505130000Z" -- 13 May 2005
       DESCRIPTION "Version 33: Added error code 9604"

       REVISION "200505060000Z" -- 06 May 2005
       DESCRIPTION "Version 32: Added error code 8004.  Updated 8002."

       REVISION "200504221200Z" -- 22 April 2005
       DESCRIPTION "Version 31: Added new error code 8330.
			Also sync up the error codes with the Master Copy:
			- Add 2533 - 2537
			- Add 7064 - 7077
			- Add 7127-7128
			- 8108-8119 incorrectly numbered - should be 8107-8118"

       REVISION "200504131200Z" -- 13 April 2005
       DESCRIPTION "Version 30: Added error codes 8319-8329"

       REVISION "200503241200Z" -- 24 March 2005
       DESCRIPTION "Version 29: Added error code 8003 - eapInvalidMaxNonEapValue"

       REVISION "200502231200Z" -- 23 February 2005
       DESCRIPTION "Version 28: Added error codes 9375-9378"

       REVISION "200502180000Z" -- 18 February 2005
       DESCRIPTION "Version 27: Sync-up with Master Copy and introduced ISIS @ 83xx"

       REVISION "200502110000Z" -- 11 February 2005
       DESCRIPTION "Version 26: Added error codes for 4109 & 5507.  Introduced Tacacs @ 82xx"

       REVISION "200502100000Z" -- 10 February 2005
       DESCRIPTION "Version 25: Added intial error codes for IPFIX @ 81xx"

       REVISION "200502011800Z" -- 01 February 2005
       DESCRIPTION "Version 24: Added error code 2419"

       REVISION "200501241200Z" -- 24 January 2005
       DESCRIPTION "Version 23: Added error codes 6511-6512, 8002"

       REVISION "200501201200Z" -- 20 January 2005
       DESCRIPTION "Version 22: Added error codes 1134-1135"       

       REVISION "200501171200Z" -- 17 January 2005
       DESCRIPTION "Version 21: Updated 7613"

       REVISION "200501141800Z" -- 14 January 2005
       DESCRIPTION "Version 20: Added message 9373"

       REVISION "200412200000Z" -- 20 December 2004
       DESCRIPTION "Version 19: Updated messages (7059,6958)
				Added new messages (6956,6957,7057,7058) "
       
       REVISION "200412171800Z" -- 17 December 2004
       DESCRIPTION "Version 18: Added new messages (6958,7059, 7648-7653,7505,7506)."
       
       REVISION "200412071400Z" -- 12 December 2004
       DESCRIPTION "Version 17: Added new messages (1132-1133)."

       REVISION "200411301700Z" -- 30 November 2004
       DESCRIPTION "Version 16: Added new messages for Launch Pad(1129-1131)."

       REVISION "200411110000Z" -- 11 November 2004
       DESCRIPTION "Version 15: Cleaned up REVISIONs and fixed typos."

       REVISION "200411040000Z" -- 04 November 2004
       DESCRIPTION "Version 14: Modify PowerRanger related Error
                                messages(9363,64,65,69,71,72, 7501-04,
                                7601-47,7701-17)"

       REVISION "200410271700Z" -- 27 October 2004
       DESCRIPTION "Version 13: Add error message
                                communityListModificationNotAllowed(5288)"

       REVISION "200410200000Z" -- 20 October 2004
       DESCRIPTION "Version 12: Add error message 6948-6955 and 7052-7054,
                                7056, 7904-7905"

       REVISION "200410110000Z" -- 11 October 2004
       DESCRIPTION "Version 11: Add error message 1127, 1128 And Correct
                                the 7042,7045."

       REVISION "200410080000Z" -- 08 October 2004
       DESCRIPTION "Version 10: Add error message (1126)."

       REVISION "200410050000Z" -- 05 October 2004
       DESCRIPTION "Version 9: Add missing error message (2532, 7035-7051)."

       REVISION "200409300000Z" -- 30 September 2004
       DESCRIPTION "Version 8: Add missing error message (9338-9344)."

       REVISION "200409290000Z" -- 29 September 2004
       DESCRIPTION "Version 7: Add error message eapGuestAndMultiMac ."

       REVISION "200409280000Z" -- 28 September 2004
       DESCRIPTION "Version 6: Fixing typo and remove duplicate entry."

       REVISION "200409230000Z" -- 23 September 2004
       DESCRIPTION "Version 5: Added back unsubmitted error message."

       REVISION "200409130000Z" -- 13 September 2004
       DESCRIPTION "Version 4: Added radiusInvalidCliCommandCount(4107)"  

       REVISION "200407200000Z" -- 20 July 2004
       DESCRIPTION "Version 3: Added version info"  

       ::= { rcError 0 }
 
rcErrorLevel OBJECT-TYPE
        SYNTAX        Integer32
        MAX-ACCESS    read-only
        STATUS        current
        DESCRIPTION   "Error level indicator for the last error
                      reported in the system.  The meaning of
		      this value are :

			0 = Informative Information
			1 = Warning Condition
			2 = Error Condition
			3 = Manufacturing Information
			4 = Fatal Condition
		      "
        ::= { rcError 1 } 
 
rcErrorCode OBJECT-TYPE
        SYNTAX        Integer32
        MAX-ACCESS    read-only
        STATUS        current
        DESCRIPTION   "Error code indicator for the last error
                      reported in the system.  This is an encoded
		      value that identifies the software module
		      that generated the error message as well as
                      a specific error condition within that module.
		      This value is transparent to the user.  This
		      value is intended to help Accelar support and
		      development staff to isolate system problems."
        ::= { rcError 2 }

rcErrorText OBJECT-TYPE
        SYNTAX        DisplayString
        MAX-ACCESS    read-only
        STATUS        current
        DESCRIPTION   "Error string of the last error reported 
                      in the system."
        ::= { rcError 3 }

-- 
-- *** THIS SECTION IS GENERATED FROM ../mib_tools/error.mib ***

-- This is generated by str2c.py -mib
-- Do not edit this file
-- Instead, edit $(TOPDIR)/mib/mib_tools/error_input.txt

rcErrorReturnCode OBJECT-TYPE
    SYNTAX INTEGER {
		none(100),
		resourceNotAvailable(101),
		operationNotAllowed(102),
		operationInProgress(103),
		invalidPortNumber(104),
		invalidSubnetAddress(105),
		invalidSubnetMask(106),
		invalidVlanId(107),
		invalidVlanName(108),
		invalidVlanType(109),
		invalidStgId(110),
		invalidProtocolId(111),
		invalidPortMembers(112),
		invalidStaticMembers(113),
		invalidNotAllowedMembers(114),
		destinationNotReachable(115),
		tableIsFull(116),
		nondualConnectorGigPort(117),
		testIdNotPresent(118),
		invalidTestId(119),
		invalidStatusChange(120),
		invalidCpuCard(121),
		invalidSrcPortChoice(122),
		dstPortUnspecified(123),
		srcPortOneUnspecified(124),
		srcPortTwoUnspecified(125),
		notSupported(126),
		userNameIsNonUnique(127),
		invalidName(128),
		unknownErrorCode1(129),
		cannotModifyThisField(130),
		invalidUserPasswordLength(131),
		thisUsernameExists(132),
		invalidIpAddress(133),
		invalidMacAddress(134),
		nosuchEntry(135),
		anotherLoopBackTestAlreadyRunning(136),
		protocolIdNotRoutable(137),
 		autoNegotiateIsOn(138),
		noActionSpecified(139),
		invalidActionSpecified(140),
		cannotModifyAutoNegotiateIsOn(141),
		cannotModifyAutoPortIsFiber(142),
		autoNegotiationNotSupported(143),
		cannotSetAdminSpeed(144),
		cannotSetAdminDuplex(145),
		ospfRtrDeadIntIsnotMultOfHelloInt(146),
		ospfRtrDeadIntLessThan4TimesHelloInt(147),
		notUsed1(148),
		ospfBadAuthValue(149),
		ospfEnabled(150),
		ospfAreaNotFound(151),
		ospfBackboneArea(152),
		notInTestMode(153),
		ospfInvalidAreaRangeMask(154),
		ospfDuplicateEntry(155),
		ospfRangeNotAllocated(156),
		ospfAreaRangeNotFound(157),
		testRunning(158),
		nvramLimitExceeded(159),
		flowAlreadyExist(160),
		flowNotFound(161),
		invalidOspfAreaRangeNet(162),
		duplicateIpAddress(163),
		conflictingIpAddress(164),
		invalidRouteCost(165),
		invalidNextHop(166),
		duplicateRoute(167),
		cannotFindRoute(168),
		cannotDeleteLocalRoute(169),
		badDhcpMinSec(170),
		badDhcpMaxHop(171),
		badDhcpMode(172),
		badAgentAddress(173),
		dhcpNotEnabled(174),
		dhcpForwardNotFound(175),
		dhcpDuplicateForward(176),
		dhcpMaxForward(177),
		dhcpBadEnable(178),
		invalidDeviceFileNumber(179),
		notExecutableDeviceFile(180),
		deletedDeviceFile(181),
		pcmciaNotPresent(182),
		pcmciaWriteProtected(183),
		discontiguousSubnetMask(184),
		invalidOspfMetric(185),
		ospfHostRouteNotFound(186),
		invalidMltId(187),
		invalidMltName(188),
		onlyOnePortInMlt(189),
		moreThan4PortsInMlt(190),
		portsInDifferentQuid(191),
		portAlreadyInAnotherMlt(192),
		invalidVlan(193),
		nonExistIpMcastAddriess(194),
		invalidIpMulticastAddress(195),
		portIsLocked(196),
		accessRestriction(197),
		invalidDeviceFileLength(198),
		duplicateAccessPolicyId(199),
		noDesiredAccessPolicyItem(200),
		ipfFilterNonExist(201),
		ipfInvalidVlanPriority(202),
		ipfInvalidDestinationAddress(203),
		ipfInvalidSourceAddress(204),
		ipfFilterDuplicate(205),
		ipfGlobalListDuplicate(206),
		ipfGlobalListNonExist(207),
		ipfBaseListDuplicate(208),
		ipfBaseListNonExist(209),
		ipfPortDuplicate(210),
		ipfPortNonExist(211),
		ipfListNonExist(212),
		snmpSnoopDisabled(213),
		invalidHostIpAddress(214),
		snoopStaticGroupExist(215),
		ripAnnouncePolicyNotFound(216),
		duplicateRipAnnouncePolicy(217),
		ospfAnnouncePolicyNotFound(218),
		duplicateOspfAnnouncePolicy(219),
		policyMatchNetEntryNotFound(220),
		duplicatePolicyNetEntry(221),
		policyAddrListEntryNotFound(222),
		duplicatePolicyAddrListEntry(223),
		policyAddrListIdNotFound(224),
		policyExactNetListNotFound(225),
		policyRangeNetListNotFound(226),
		policyRipGatewayListNotFound(227),
		policyRipInterfaceListNotFound(228),
		policyOspfRtrIdListNotFound(229),
		policyAnnounceInterfaceListNotFound(230),
		policyAdvertiseNetListNotFound(231),
		policyInjectNetListNotFound(232),
		invalidPolicyListIdListSize(233),
		policyAddrEntryNotFound(234),
		duplicatePolicyAddrEntry(235),
		disableThisPortFirst(236),
		mutinettingNotSupported(237),
		addingGlobalFilterToNonGlobalList(238),
		addingNonGlobalFilterToGlobalList(239),
		setFilteredPortMode(240),
		setFilteredPortEnableValue(241),
		invalidModeType(242),
		duplicateRipAcceptPolicy(243),
		ripAccepPolicyNotFound(244),
		duplicateOspfAcceptPolicy(245),
		ospfAccepPolicyNotFound(246),
		invalidAccessPolicyName(247),
		invalidAccessPolicyPolicyEnable(248),
		invalidAccessPolicyMode(249),
		invalidAccessPolicyService(250),
		invalidAccessPolicyPrecedence(251),
		invalidAccessPolicyNetAddress(252),
		invalidAccessPolicyTrustedHostAddress(253),
		invalidAccessPolicyTrustedHostUserName(254),
		invalidAccessPolicyAccessLevel(255),
		invalidAccessPolicyLogSetting(256),
		invalidAccessPolicyPolicyId(257),
		invalidAreaOptions(258),
		cannotDeleteAreaIfCountIsNotZero(259),
		ospfInterfaceNotFound(260),
		ospfIfAreaIdConflictsWithConfiguredAreaRange(261),
		applyingDuplicateGlobalFilterToPort(262),
		differentMltPortTypes(263),
		addPortToMltFailed(264),
		removePortFromMltFailed(265),
		mirrorPortInMlt(266),
		invalidDhcpAlwaysBroadcast(267),
		interfaceIsSetToTransmitRipV1(268),
		ripInterfaceDoesnotExist(269),
		interfaceIsNotRunningRip(270),
		cannotCreateVirtLinksThroughStubArea(271),
		invalidSyslogEnableSetting(272),
		invalidSyslogMaxHostsSettings(273),
		invalidSyslogHostIpAddr(274),
		invalidSyslogHostUdpPort(275),
		invalidSyslogHostFacility(276),
		invalidSyslogModuleId(277),
		invalidSyslogSeverity(278),
		invalidSyslogMapInfoSeverity(279),
		invalidSyslogMapWarningSeverity(280),
		invalidSyslogMapErrorSeverity(281),
		invalidSyslogMapMfgSeverity(282),
		invalidSyslogMapFatalSeverity(283),
		invalidSyslogMapTraceMsgSetting(284),
		invalidSyslogMapTrapMsgSetting(285),
		invalidSyslogLogTraceMsgSetting(286),
		invalidSyslogLogTrapMsgSetting(287),
		invalidSyslogEntryEnableSetting(288),
		invalidSyslogMaxHostSetting(289),
		invalidSyslogHostId(290),
		duplicateSyslogEntry(291),
		syslogHostTableIsFull(292),
		noDesiredSyslogHostEntryFound(293),
		invalidHoldDownTime(294),
		incompatibleAruHardware(295),
		invalidVrid(296),
		duplicateVrrpEntry(297),
		noVrrpIpAddressSpecified(298),
		invalidVrrpControlValue(299),
		invalidVrrpPriority(300),
		invalidVrrpAdvertisementInterval(301),
		maxNumOfVrrpsEntriesExceeded(302),
		policyNetListEntryNotFound(303),
		duplicatePolicyNetListEntry(304),
		policyNetListIdNotFound(305),
		filterOnAnEnabledPort(306),
		listOnAnEnabledPort(307),
		invalidIpFilterSrcOption(308),
		invalidIpFilterDstOption(309),
		invalidOspfAreaImportextOption(310),
		invalidOspfInterfaceMd5KeyIdLength(311),
		invalidOspfInterfaceMd5KeyLength(312),
		invalidIPXNetworkNumber(313),
		ipxCircuitAlreadyExists(314),
		ipxCircuitDoesNotExist(315),
		encapsulationIsNotAllowedOnSameSegment(316),
		encapsulationDoesNotMatchProtocolBasedVLAN(317),
		invalidDvmrpIfTblEnableValue(318),
		invalidDvmrpIfTblMetricValue(319),
		ipHostPartForSubnetAddrIsNonZero(320),
		globalMulticastNotEnabled(321),
		metricFieldIsCreatedButModified(322),
		invalidIpMRouteInterfaceTblTtlValue(323),
		invalidUdpPortNumber(324),
		invalidUdpProtocolNameLength(325),
		cannotModifyUdpProtocolName(326),
		udpProtocolEntryDoesnotexists(327),
		duplicateUdpProtocolEntry(328),
		cannotDelUdpProtocolEntryFwdEntriesExists(329),
		udpBroadcastIntfEntryDoesnotExists(330),
		duplicateUdpBroadcastIntfEntry(331),
		invalidUdpConfBroacastInterface(332),
		updConfIntfEntryNotEnabledForUdpBcastForwarding(333),
		udpPortFwdEntryDoesnotExists(334),
		duplicateUdpPortFwdEntryDoesnotExists(335),
		udpPortFwdEntryUdpPortInterfaceDoesnotExists(336),
		udpPortFwdListEntryDoesnotExists(337),
		duplicateUdpPortFwdListEntryDoesnotExists(338),
		udpPortFwdListEntryPortFwdIdDoesnotExists(339),
		udpPortFwdListEntryinvalidFwdIdListSize(340),
		cannotDeleteUdpPortFwdListEntryInterfaceUsingThisList(341),
		invalidIgmpSnoopDestAddress(342),
		invalidIgmpSnoopHostAddress(343),
		cannotDeleteDefaultUdpProtocolTblEntry(344),
		nextHopRouteIsStaticRoute(345),
		invalidUpdateIntervalValueInDVMRPGlobalTable(346),
		invalidTriggeredUpdateIntervalValueInDVMRPGlobalTable(347),
		invalidLeafTimeoutValueInDVMRPGlobalTable(348),
		invalidNbrTimeoutValueInDVMRPGlobalTable(349),
		invalidNbrProbeIntervalValueInDVMRPGlobalTable(350),
		invalidQueryIntervalValueInIgmpInterfaceTable(351),
		invalidVersionValueInIgmpInterfaceTable(352),
		invalidQueryMaxResponseTimeValueInIgmpInterfaceTable(353),
		invalidRobustnessValueInIgmpInterfaceTable(354),
		invalidLastMembQueryIntvlValueInIgmpInterfaceTable(355),
		invalidANDMaskInRcIpTosRuleGroup(356),
		invalidORRule1InRcIpTosRuleGroup(357),
		invalidORRule2InRcIpTosRuleGroup(358),
		invalidORRule3InRcIpTosRuleGroup(359),
		deleteStaticPortNotValid(360),
		maxEntriesForIgmpAccTbl(361),
		maxMaskNumberOfHostIgmpAccTbl(362),
		dvmrpIgmpExclusive(363),
		theSpecifiedAreaRangeMaskIsInvalid(364),
		invalidLengthOf2kBootConfigImageSource(365),
		invalidLengthOf2kBootConfigSource(366),
		preferenceOfStaticRouteIsInvalid(367),
		copyFileOutOfSpace(368),
		copyFileFileNotFound(369),
		copyFileInvalidDestination(370),
		copyFileInvalidSource(371),
		copyFileFail(372),
		invalidLinkFlapDetectAutoPortDown(373),
		invalidLinkFlapDetectFrequency(374),
		invalidLinkFlapDetectInterval(375),
		invalidLinkFlapDetectSendTrap(376),
		invalidQosLevel(377),
		invalidQosWeight(378),
		invalidQosThreshold(379),
		invalidTagToQosTableIeee1pValue(380),
		invalidTagToQosTableQosLevel(381),
		invalidDsFieldToQosTableDsField(382),
		invalidDsFieldToQosTableQosLevel(383),
		invalidQosToTagTableQosLevel(384),
		invalidQosToTagTableIeee1pValue(385),
		invalidQosLevelValue(386),
		invalidQosToDsFieldTableDsFieldValue(387),
		invalidQosToDsFieldTableQosLevel(388),
		invalidDiffServEnable(389),
		invalidDiffServType(390),
		invalidIeeeOverride(391),
		invalidVlanQosValue(392),
		invalidVlanTosValue(393),
		operationNotAllowedOnAccessPort(394),
		operationNotAllowedOnTaggingPort(395),
		invalidFileName(396),
		invalidDiaglogueDuplicateMirroredPort(397),
 		invalidDiaglogueEnableValue(398),
		invalidDiaglogueEnableSetting(399),
		invalidDiaglogueModeSetting(400),
		invalidDiaglogueEntryId(401),
		srcMacVlanIsNotYetEnabled(402),
		srcMacVlanIsNotYetDisabled(403),
		invalidDiaglogueOperation(404),
		invalidMacAddressSpecied(405),
		maxResponseTimeGreaterThanQueryInterval(406),
		noModifyDsFltrAllowedOnDiffSrvCorePort(407),
		mltMoreThan4PortsInMgMlt(408),
		protocolRulesForThePortHasExceeded16(409),
		routeDoesNotExistsInTheRroutingTable(410),
		diagMirrorByPortTableAccessError(411),
		diagMirrorByPortInvalidMirroringPortSetting(412),
		igmpAdminVersionConfiguredLessThanOperatingVersion(413),
		canOnlyConfigureViaMltTable(414),
		dvmrpInterfaceTableIsFull(415),
		invalidDscpField(416),
		invalidDscpReservedField(417),
		disablePortPriorToChangingDiffServPortType(418),
		ipFilterInvalidId(419),
		rateLimitingExceeded(420),
		diagEntryMaxExceeded(421),
		onlyOneMirroringPortAllow(422),
		radiusServerExist(423),
		radiusServerNotExist(424),
		radiusServerInUse(425),
		radiusMaxServerNumExceeded(426),
		radiusInvalidAttribute(427),
		canNotChangeLocking(428),
		activationDisabled(429),
		zeroMac(430),
		atmBadVpi(431),
		atmBadVci(432),
		atmBadFramingMode(433),
		atmDestroyPvcFailed(434),
		atmBadName(435),
		atmBadEnable(436),
		atmBadpvcEncapsulation(437),
		atmBadPvdServiceType(438),
		atmBadPeakCellRate(439),
		atmBadSustainedCellRate(440),
		atmBadMaxBurstSize(441),
		atmBadMaxMtuSize(442),
		atmBadElanId(443),
		atmUnknownOperation(444),
		atmDestroy1483ElanFailed(445),
		atmBadPerformTagging(446),
		atmIlleagalElanDefinition(447),
		atmCreate1483ElanFailed(448),
		atmBadSnmpMessage(449),
		atmBadScrambleEnable(450),
		atmBadSignalingEnable(451),
		atmBadClockSource(452),
		atmBadLoopback(453),
		badRowStatus(454),
		atmBadLaneConfigMode(455),
		atmLecCreationFailed(456),
		atmBad1438Inarp(457),
		atmF5StartFailed(458),
		atmBadPvcId(459),
		atmBadConnectType(460),
		atmBadIpxEncapMethod(461),
		atmBadUniVersion(462),
		atmCreatePvcFailed(463),
		invalidLoginPromptLength(464),
		invalidPasswordPromptLength(465),
		invalidCliBannerLength(466),
		invalidCliBannerSize(467),
		invalidCliMotdLength(468),
		invalidCliMotdSize(469),
		invalidPortNameLength(470),
		invalidPortName(471),
		invalidMaxAdvertiseInterval(472),
		invalidMinAdvertiseInterval(473),
		invalidMaxInitialAdvertiseInterval(474),
		invalidMaxInitalAdvertments(475),
		invalidNeigborDeadInterval(476),
		invalidUserSetTimeYearValue(477),
		invalidUserSetTimeMonthValue(478),
		invalidUserSetTimeDateValue(479),
		invalidUserSetTimeHourValue(480),
		invalidUserSetTimeMinuteValue(481),
		invalidUserSetTimeSecondValue(482),
		rtcIsNotPresent(483),
		rtcIsNotRunning(484),
		maxMacCount(485),
		maxAdvertiseIntLessThanMinAdvertiseInt(486),
		minAdvertiseIntGreaterThanMaxAdvertiseInt(487),
		dvmrpNotEnabledGlobally(488),
		vrrpCriticalIpAddrNotEnable(489),
		vrrpInvalidCriticalIpAddr(490),
		metricConfigNotAllowed(491),
		posActiveNonBcpEnabledPort(492),
		posVlanNoMorePorts(493),
		posPortCanBeAdded(494),
		posNonBcpCanNotBeEnabled(495),
		posImageFilenameTooLong(496),
		posNoIpcpEnableOnMltPorts(497),
		posNoIpcpEnableOnTagPort(498),
		posNoIpxcpEnableOnMltPort(499),
		posNoIpxcpEnableOnTagPort(500),
		posDisableTagBeforeBcpDisable(501),
		posAssignIpBeforeIpcpEnable(502),
		posAssignIpxBeforeIpxcpEnable(503),
		posAssignIpBeforeRemoteIp(504),
		posKeepRemoteIpInSameSubnet(505),
		staticRouteEnabled(506),
		cannotChangeAutoLearnState(507),
		invalidVirtualIpAddr(508),
		virtualAndPhysicalIpNotInSameSubnet(509),
		vidNotAvailable(510),
		mgidNotAvailable(511),
		posNoIpcpEnableOnPolicyVlanPort(512),
		posNoIpxcpEnableOnPolicyVlanPort(513),
		posVrrpNotAllowed(514),
		webInvalidHttpPort(515),
		cannotAddMulticastStaticMac(516),
		posNoStpEnableWithBCPClosed(517),
		posAtmNoRip1(518),
		ipfFilterNumOverFilterSetLimit(519),
		ipfQosTrafficAverageRateOverLimit(520),
		ipfQosTrafficProfileNotExist(521),
		atmNoIpIpxConfigOnVlan(522),
		atmPvcIsInUse(523),
		globalFilterNotDisabled(524),
		dhcpNotOnByIpSubnetVlan(525),
		cannotConfigureDefaultGateway(526),
		routeExists(527),
		gatewayNotOnMgmtInterfaceSubnet(528),
		mgmtRouteTableFull(529),
		routeNotExists(530),
		invalidMacOffsetRangeForBW(531),
		invalidMacOffsetRangeForMG(532),
		atmPvcBadPeakCellRate(533),
		atmPvcBadSustainedCellRate(534),
		qosReservedQosLevel(535),
		dvmrpGlobInvalidFwdCacheTimeOut(536),
		dvmrpGlobInvalidRouteExpireTimeOut(537),
		dvmrpGlobInvalidRouteDiscardTimeOut(538),
		dvmrpGlobInvalidRouteSwitchTimeOut(539),
		pimCondRPGroupExists(540),
		pimCandRPAddressInvalid(541),
		pimGroupAddressInvalid(542),
		pimNotEnabled(543),
		pimInvalidJPInterval(544),
		pimInvalidMode(545),
		pimInvalidHelloInt(546),
		pimInvalidCBSRPRef(547),
		pimInvalidEnable(548),
		pimAlreadyEnabled(549),
		ipDvmrpAlreadyEnabled(550),
		ospfIntfChangeNotAllowedWhenEnabled(551),
		ospfIntfChangeFromNBMANotAllowed(552),
		ospfPollIntIsnotMultOfHelloInt(553),
		ospfNeigNoCircuit(554),
		ospfNeigSameIp(555),
		ospfCircNotNBMA(556),
		ospfCircPriZero(557),
		ospfNBMANeigExist(558),
		ospfNBMANeigNotFound(559),
		ospfDynNeigExist(560),
		pgmInvalidSessionLifetime(561),
		pgmInvalidMaxRetxStates(562),
		pgmInvalidMaxSessions(563),
		pgmInvalidIfNakRetxInterval(564),
		pgmInvalidIfMaxNakRetxCnt(565),
		pgmInvalidIfNakRdataInt(566),
		pgmInvalidIfNakElimInt(567),
		maxOfMirroringPortAllowedExceed(568),
		duplicatedRoutePolicyEntry(569),
		specifiedRoutePolicyEntryNotFound(570),
		specifiedPrefixListNotFound(571),
		routePolicyListNotSpecify(572),
		routePolicyPrefixListOverLimit(573),
		ipPrefixListDuplicate(574),
		ipPrefixListDuplicateEntry(575),
		ipPrefixListEntryNotFound(576),
		ipPrefixListInvalidName(577),
		ipRedistributeDuplicateEntry(578),
		ipRedistributeEntryNotFound(579),
		ipOspfInFilterDuplicateEntry(580),
		ipOspfInFilterEntryNotFound(581),
		ipEcmpNotDisabled(582),
		ipEcmpMaxExceeded(583),
		ipfQosTrafficAvgRateZeroProfileEnable(584),
		ipmTimePruneEntryInvalidGroup(585),
		ipmTimePruneEntryDuplicate(586),
		ipmTimePruneEntryNotExist(587),
		ipmTimePruneEntryInvalidExpireTime(588),
		smltIstExist(589),
		smltSmltIdExist(590),
		smltIstNotExist(591),
		smltSmltIsEnabled(592),
		smltSmltLocalIpNotExist(593),
		smltInvalidPortTypeForIstMlt(594),
		ntpServerAlreadyExist(595),
		ntpServerDoesNotExist(596),
		ntpKeyAlreadyExists(597),
		ntpKeyDoesNotExist(598),
		ntpMaxKeyExceeded(599),
		ntpServerAlreadyEnabled(600),
		ntpServerAlreadyDisabled(601),
		ntpNoServerConfigured(602),
		ntpMaxServerNumExceeded(603),
		ntpInvalidIntervalValue(604),
		ecmpNotEnabled(605),
		ipfInvalidProtocolType(606),
		assignIpToPortInRouteVlan(607),
		assignIpToVlanWithRoutePortMember(608),
		ipfIstPort(609),
		smltMltIpfExist(610),
		smltMltPortIpfExist(611),
		smltL2fIstPort(612),
		smltMltL2fExist(613),
		smltMltPortL2fExist(614),
		portMirroringEgressNotSupportFullDuplexMode(615),
		pimGlobInvalidRegSupprTimeOut(616),
		smltNotAvailableIn8100(617),
		mltNoPort(618),
		mltInvalidPortType(619),
		inUsedByATM1483Elan(620),
		smltIstStpEnableNotAllowed(621),
		invalidHighestVrrpPrio(622),
		dynamicPortMemberIn8100IsNotAllowed(623),
		ipfGlobalNextHopModeNotSupported(624),
		smltPeerIpNotExist(625),
		smltMltNoThisVlan(626),
		smltNotANormalMlt(627),
		validStaticRtExist(628),
		validBlkHolRtExist(629),
		pimOrIgmpAlreadyEnabled(630),
		readWriteAccessReadOnly(900),
		readWriteAccessLevelOne(901),
		readWriteAccessLevelTwo(902),
		readWriteAccessLevelThree(903),
		readWriteAccessReadWrite(904),
		readWriteAccessReadWriteAll(905),
		readWriteAccessUnknownLevel(906),
		vlanWithIPXEnabledCannotAdd10GEPortOrMlt(1101),
		addRemDsapSsapNotAllowed(1102),
		maxDsapSsapExceeded(1103),
		vlanInvalidEncap(1104),
		cannotDeleteVlanWithTlsEndpointMember (1105),
		vlanCannotAddMoreThanOneServerPort (1106),
		vlanSupportsOneAssociatedPortOrOneMlt (1107),
		vlanCannotRemoveVpnPortWhileInService (1108),
		vlanEnforcementNotAllowed(1109),
		vlanNaapVlanPortMustBeTagged(1110),
		vlanRegPortNotAllowedInNaapVlan(1111),
		vlanFwPortNotAllowedInRegVlan(1112),
		invalidVlanIdSpecified(1113),
		exceedMaxNumPolicyVlan (1114),
		retrieve10GEInfoFailure(1115),
		minMacGreaterThanMaxMac(1116),
		maxMacLessThanMinMac(1117),
		duplicateProtocolVlan(1118),
		macAddressDoesNotExist(1119),
		vlanTooManyPids(1120),
		prPortNotForStackedVlan (1121),
		prPortNotForIPXVlan (1122),
		vlanAgingTimeNotAppToStaticVlan (1123),
		cannotDeleteVlanWithTlsUniCustIpVlanAssociation (1124),
		vlanNotExists (1125),
		naapInvalidVlanId(1126),
		cannotDeleteRingIbtVlan(1127),
		cannotRemoveRingPortOrIbtPortFromIbtVlan(1128),
		clusterIsdAlreadyUsed(1129),
		regularPortsNotAllowedInPeeringVlan(1130),
                		regularPortsNotAllowedInClusterSyncVlan(1131),
                		mltSdmPortNotAllowed(1132),
                		clusterIdNotAllowedForNormalVlan(1133),
                		clusterTypeNotSupported(1134),
                		clusterMgmtSyncVlanCannotBeSame(1135),
		vlanIsBeingUsedAsARepeaterVlan (1136),
		ageTimeIsOnlyApplicableToDynamicVlan (1137),
		nsnaPortNotConfigurable (1138),
		nsnaOperationNotAllowed (1139),
                                           vlanNotRoutable(1140),
		exceededMaxFdbFilterMacEntries (1141),
		exceededMaxFdbStaticMacEntries (1142),
		exceededMaxStaticMcastEntries (1143),
		exceededMaxArpEntries (1144),
		clusterTpsSizeExceeded(1145),
		cannotEnableUnknownDestMacDiscard(1146),
		cannotDeletePbtVlanInUseByTrunk(1147),
		clusterNotFwIsd(1148),
		clusterNotTpsIsd(1149),
		dynModMaxModule(1201),
		dynModUnknown(1202),
		dynModAlreadyLoaded(1203),
		dynModCantOpenFile(1204),
		dynModNotEnoughSpace(1205),
		circuitlestInvalidIpInterfaceId(1501),
		circuitlessMaxNumberIpInterfacesReached(1502),
		circuitDoesNotExist(1503),
		circuitAlreadyExists(1504),
		circuitlessIpInterfacesOperationNotAllowed(1505),
		priority255SpecialForPhyIpSameAsVrIp(1506),
		icmpRdiscInvalidPreferenceLevel(1507),
		icmpRdiscAdvAddrIsNotBroadcastOrMulticastAddr(1508),
		icmpRdiscInvalidMaxAdvInt(1509),
		icmpRdiscMinAdvIntvGreaterThanMaxAdvIntvOrLessThan3Secs(1510),
		icmpRdiscLifeTimeLessThanMaxAdvIntvOrGreaterThan9000Secs(1511),
		vrrpInvalidFasterAdvertInterval(1512),
		vrrpFasterAdvEnabled(1513),
		vrrpFasterAdvDisabled(1514),
		vrrpInvalidFastAdvEnableValue(1515),
		globalFiltersNotSupportFwdingNextHopMode(1516),
		vrrpPreemptActionNotAllowed(1517),
		rcPimModeIgmpVersionIncompatible(1518),
		invalidOrInconsistentBroadCastMaskValue(1519),
		invalidRipTimeoutInterval(1520),
		rsmltNoCirc(1521),
		rsmltInvalidHoldUpTimer(1522),
		rsmltNoBrouter(1523),
		rsmltNoIst(1524),
		staticRoutesMaxLimitExceeded(1525),
		vrrpSetWithRsmltEnable(1527),
		rsmltSetWithVrrpEnable(1528),
		rsmltMaxSmltCreated(1529),
		ipEcmpMaxPathExceeded(1530),
		ipEcmpPathListNotAllowedInRmode(1531),
		igmpOutOfSsmRange(2301),
		igmpDuplicateSsmTblEntry(2302),
		igmpSsmEntryDoesNotExist(2303),
		igmpSsmTblNotEmpty(2304),
		igmpRpSetExistsInSsmRange(2305),
		igmpCandidateRpExistsInSsmRange(2306),
		igmpIfInvalidQIntervalMrt(2307),
		igmpAlreadyEnabled(2308),
		igmpMaxStreamExceeded(2309),
		igmpStreamLimitAlreadyEnabled(2310),
		igmpStreamLimitNotEnabled(2311),
		igmpPimEnabledInSSMMode(2312),
		igmpDisableV3First(2313),
		igmpSSmConflictsWithSsgEntry(2314),
		igmpSsmCanNotDisableDynamicEntry(2315),
		invalidIpMulticastRange(2316),
		igmpStaticGroupCountExceeded(2317),
		igmpL2DenyTxInvalidHost(2318),
		igmpOverlappingStaticRangeNotAllowed(2319),
		igmpCannotEditStaticRecMcastDisabledGloballyOrOnVlan(2320),
		ipfStreamAlreadyExists(2401),
		ipfStreamDoesNotExists(2402),
 		ipfStreamInvalidStreamType(2403),
		ipfStreamInvalidPortOption(2404),
		ipfStreamNameTooLong(2405),
		ipfStreamInvalidProtocol(2406),
		ipfStreamInvalidDscp(2407),
		ipfDeviceAlreadyExists(2408),
		ipfDeviceUnknownPlatform(2409),
		ipfDeviceUnknownDevice(2410),
		ipfDeviceDoesNotExists(2411),
		ipfDeviceNameTooLong(2412),
		ipfOneZeroIpDestFilterIsAllowed(2413),
		ipfGlobalFilterMaxPerOctapid(2414),
		ipfDeviceMaxPerPort(2415),
		ipfDeviceMaxPerBox(2416),
		ipfDeviceMaxFilterList(2417),
		ipfInvalidRmodPort (2418),
		ipfSourceNextHopModeNotSupported(2419),
		actErrIpIllegal(2421),
		actErrIdInvalid(2422),
		actErrNotExist(2423),
		actErrInUse(2424),
		actErrExists(2425),
		actErrFieldTooMany(2426),
		actErrNameInvalid(2427),
		aclErrIdInvalid(2428),
		aclErrNameInvalid(2429),
		aclErrTypeInvalid(2430),
		aclErrNotExist(2431),
		aclErrInUse(2432),
		aclErrExists(2433),
		aclErrActIdInvalid(2434),
		aclErrInvalidCounterMode(2435),
		aceErrAclIdInvalid(2436),
		aceErrAclNotExist(2437),
		aceErrAceNotExist(2438),
		aceErrAceInUse(2439),
		aceErrAceDefault(2440),
		aceErrAceExists(2441),
		aceErrPrecedenceInvalid(2442),
		aceErrTrafficIllegal(2443),
		aceErrModeIllegal(2444),
		aceErrSupportUnavailable(2445),
		aceErrDscpIllegal(2446),
		aceErrDot1PIllegal(2447),
		aceErrUnreachIllegal(2448),
		aceErrPoliceIllegal(2449),
		aceErrInvalidCountMode(2450),
		aceErrFieldIllegal(2451),
		acgErrIdInvalid(2452),
		acgErrNotExist(2453),
		acgErrInUse(2454),
		acgErrExists(2455),
		acgErrAclNotExist(2456),
		acgErrNameInvalid(2457),
		aclIfIndexErrNotExist(2458),
		aclIfIndexErrExists(2459),
		aclIfIndexErrAcgNotExist(2460),
		acgErrActIllegal(2461),
		acgErrAclIdDuplicate(2462),
		acgErrAclTypeDuplicate(2463),
		actErrDefaultAct(2464),
		aceErrAceNameInvalid(2465),
		aceErrFragmentOptionInvalid(2466),
		aceErrSpecifyTaggedUntagged(2467),
		aceErrPolicyEntryInvalid(2469),
		acgErrEmptyAcg(2470),
		acgErrAclLimitMax(2471),
		aceErrNeedTrafficType(2472),
		aceErrTrustDscpEnabled(2473),
		aceErrMaxExceeded(2474),
		aceErrSpecifyL4Protocol(2475),
		actPartialFieldInvalid(2476),
		aceErrMatchingUserPriorityNotSupported(2477),
		aceErrMatchingL4NotSupportedForFragmentedPackets(2478),
		aceErrSelectTagAct(2479),
		aceErrIfindexHwActInsuf(2480),
		acgErrUplinkCannotBeModified (2481),
		cannotDeleteIntMltId(2501),
		mltNoThisVlan(2502),
		mltPortsDifferentFramingMode(2503),
		moreThan2PortsInMlt(2504),
		portCannotBeAddedToDefualtVLANWithIPXEnabled(2505),
		portMemberNotSupportSMLT(2506),
		tenGEMltPortOrMltCannotBeAddedToVlanWithSmltMember(2507),
		tenGEMltPortCannotRunTogetherWithSMLT(2508),
		portCannotBeAddedToDefualtVLANWithSMLT(2509),
		tenGEPortOrMltCannotBeAddedToVlanWithSmltMember(2510),
		tenGEPortOrMltCannotRunTogetherWithSMLT(2511),
		tenGEPortNotSupportMcastDistribution(2512),
		tenGEPortNotSupportMLT(2513),
		mltSmltIdAlreadyExists(2514),
		mltInvalidSmltId(2515),
		mltSmltNotConfigured(2516),
		mltSmltAlreadyConfigured(2517),
		mltPortIsMemberOfMlt(2518),
		mltPortIsMemberOfSmlt(2519),
		mltSmltIpAddrNotAllowedOnSltPort (2520),
		mltUsedForLacp(2521),
		mltPortUsedForLacp(2522),
		mltUsedForMlt(2523),
		commandOnlySupportedIn10GMlt (2524),
		mltWithLacp10gBackupEnableSupports10GPortMemebersOnly (2525),
		removeIpOnVplsPortToAddToMltGroup (2526),
		mltIdAlreadyExists(2527),
		mltPartOfMoreThanOneVlan(2528),
		operationNotAllowedOnMltPort(2529),
		mltInvalidMltIdForFastEther(2530),
		mltPartOfMoreThanOneStg(2531),
		mltDoesNotExist(2532),
		mltCannotBeAddedToMultpleVlansWhilePerformTagIsDisabled(2533),
		performTagCannotBeDisabledWhileMltBelongsToMultipleVlans(2534),
		mltPerformTaggingIsAlreadyEnabledOrDisabled(2535),
		smltPeerIpCannotBeSameAsLocalIp(2536),
		mltCannotDeletedBeforeDeletingSmltOrSetMltTypeToNormal(2537),
		mltNsnaUplinkMismatch(2538),
		mltIdInvalidInNonRmode(2539),
		asListOverLimit(2601),
		communityListOverLimit(2602),
		mltSmltLacpInvalidKey(2603),
		ipRedistributeNotEnabled(2604),
		mcastMltNotEnabled(2701),
		mcastMltInvalidSrcMask(2702),
		mcastMltInvalidGrpMask(2703),
		mcastMltRedistrNotEnabled(2704),
		mcastMltDiscontiguousSrcMaskValue(2705),
		mcastMltDiscontiguousGrpMaskValue(2706),
 		mcastMltNotEnabledOnMlt(2707),
		mcastMltPortOnNonEtkt(2708),
		mcastMltConfMaskDisableMcastMlt(2709),
		ipmcTimePruneConflictsWithSsmEntry(2710),
		invalidPortServiceType (2711),
		rcSnmpSyslogDisableSyslogFirst(2801),
		dvmrpMBRNotAllowed(2901),
		dvmrpInvalidIntfTypeChange(2902),
		dvmrpMbrNotAllowed (2903),
		dvmrpInvalidIntfTypeChangeWhenIntfIsEnabled (2904),
		ipxPolicyNetEntryNotFound(3101),
		ipxPolicyNetDuplicateEntry(3102),
		ipxPolicyNetListEntryNotFound(3103),
		ipxPolicyNetListDuplicateEntry(3104),
		ipxPolicyServEntryNotFound(3105),
		ipxPolicyServDuplicateEntry(3106),
		ipxPolicyServeListEntryNotFound(3107),
		ipxPolicyServListDuplicateEntry(3108),
		ipxPolicyPolicyEntryNotFound(3109),
		ipxPlicyPolicyDuplicateEntry(3110),
		ipxRoutePolicyNetListOverLimit(3111),
		ipxRoutePolicyServListOverLimit(3112),
		ipxPolicyRipOutFilterEntryNotFound(3113),
		ipxPolicySapOutFilterEntryNotFound(3114),
		ipxPolicyRipInFilterEntryNotFound(3115),
		ipxPolicySapInFilterEntryNotFound(3116),
		ipxPolicyIpxNetEntryInvalidName(3117),
		ipxPolicyIpxServEntryInvalidName(3118),
		ipxPolicyPolicyEntryInvalidName(3119),
		vlanHas10GEMemberWhichNotSupportIPX(3120),
		vlanContainUnSupportedPrPort (3121),
		qosNumTxQueueOutOfRange(3601),
		qosTxQueueSizeOutOfRange(3602),
		qosEntryExist(3603),
		qosEntryNotExist(3604),
		qosEntryInUse(3605),
		qosInvalidPort(3606),
		qosNotAllowToModify(3607),
		qosPirSmallerThanCir(3608),
		qosShapingRateOutOfRange(3609),
		qosEgressCntrExceed(3610),
		qosPolicyRmkUsrOrDpNoEffect(3611),
		qosEgressCntrVlanNotExist(3612),
		qosEgressCntrPortLinkDown(3613),
		qosEgressCntrVlanInUsed(3614),
		qosPortBasedVlan(3615),
		qosPolicyRmkDpNoEffect (3617),
		qosVbEgressCounterNoVlan(3618),
		qosVbTrustDscp(3619),
		qosVbTxConfigAppliedPortsCascadingGrp(3620),
		invalidModeForAtmMDAType(3901),
		atmInvalidPVCEncapTypeForElan(3902),
		atmInvalidPVCPCRRange(3903),
		unsupportedVPI(3904),
		radiusAuthAcctAttrSame(4101),
		radiusAuthAcctPortSame(4102),
		radiusAuthAcctNoServerConfig(4103),
		radiusReAuthTimerFailed(4104),
		radiusAbortSesionTimerFailed(4105),
		radiusInvalidSnmpUserLength(4106),
		radiusInvalidCliCommandCount(4107),
		radiusNotEnabled(4108),
		radiusTacacsEnabled(4109),
		radiusInvalidSecretKey(4110),
		pimGlobInvalidUniRouteChangeTimeOut(4801),
		pimGlobInvalidDiscDataTimeOut(4802),
		pimGlobInvalidCRPADVTimeOut(4803),
		pimGlobInvalidBootStrapPeriod(4804),
		pimStaticRpEnabled(4805),
		pimStaticRpNotEnabled(4806),
		pimStaticRpEntryExists(4807),
		pimStaticRpNoRoute(4808),
		pimAddressInSsmRange(4809),
		pimInvalidModeChange(4810),
		pimStaticRpNotAllowed(4811),
		pimMBRNotAllowed(4812),
		pimGlobInvalidActChkInterval(4813),
		pimGlobActChkIntervalNotAllowed(4814),
		pimMbrNotAllowed (4815),
		rpsMcastMaskLenToNotAllowed(4901),
		tcpConnectionNotFound(5101),
		tcpInvalidState(5102),
		bgpPeerNotFound(5201),
		bgpInvalidPeerEnable(5202),
		bgpInvalidPeerRemoteas(5203),
		bgpInvalidPeerGroupName(5204),
		bgpInvalidPeerDefaultOriginate(5205),
		bgpInvalidPeerEbgpMultiNop(5206),
		bgpInvalidPeerAdvertisementInterval(5207),
		bgpInvalidPeerPassword(5208),
		bgpInvalidPeerWeight(5209),
		bgpInvalidPeerNextHopSelf(5210),
		bgpInvalidPeerRoutePolicyIn(5211),
		bgpInvalidPeerRoutePolicyOut(5212),
		bgpInvalidPeerRouteReflectorClient(5213),
		bgpInvalidPeerSoftReconfigurationIn(5214),
		bgpInvalidPeerSoftReconfiguration(5215),
		bgpInvalidPeerRemovePrivateAs(5216),
		bgpInvalidPeerRowStatus(5217),
		bgpNetworkNotFound(5218),
		bgpPeerGroupNotFound(5219),
		bgpInvalidPeerGroupEnable(5220),
		bgpInvalidPeerGroupRemoteAs(5221),
		bgpInvalidPeerGroupDefaultOriginate(5222),
		bgpInvalidPeerGroupUpdateSource(5223),
		bgpInvalidPeerGroupEbgpMultiHop(5224),
		bgpInvalidPeerGroupAdvertisementInterval(5225),
		bgpInvalidPeerGroupPassword(5226),
		bgpInvalidPeerGroupWeight(5227),
		bgpInvalidPeerGroupNextHopSelf(5228),
		bgpInvalidPeerGroupRoutePolicyIn(5229),
		bgpInvalidPeerGroupRoutePolicyOut(5230),
		bgpInvalidPeerGroupRouteReflectorClient(5231),
		bgpInvalidPeerGroupSoftReconfigurationIn(5232),
		bgpInvalidPeerGroupSoftReconfiguration(5233),
		bgpInvalidPeerGroupRemovePrivateAs(5234),
		bgpInvalidPeerGroupHoldTime(5235),
		bgpInvalidPeerGroupKeepAlive(5236),
		bgpInvalidPeerGroupRowStatus(5237),
		bgpInvalidPeerGroupGroupName(5238),
		bgpAggregateNotFound(5239),
		bgpInvalidAggregateAsSetGenerate(5240),
		bgpInvalidAggregateSummaryOnly(5241),
		bgpInvalidAggregateSuppressPolicy(5242),
		bgpInvalidAggregateAdvertisePolicy(5243),
		bgpInvalidAggregateAttributePolicy(5244),
		bgpOperationNotAllowedWhenBgpIsEnabled(5245),
		bgpInvalidPeerHoldTime(5246),
		bgpInvalidPeerKeepAlive(5247),
		bgpInvalidPeerMaxPrefix(5248),
		bgpInvalidPeerGroupMaxPrefix(5249),
		bgpInvalidPeerMD5Authentication(5250),
		bgpInvalidPeerGroupMD5Authentication(5251),
		bgpInvalidPeerGroupIndex(5252),
		bgpInvalidConfederationIdentifier(5253),
		bgpInvalidConfederationPeerAsNumber(5254),
		bgpInvalidConfederationPeerNotFound(5255),
		bgpInvalidConfederationPeerAlreadyExist(5256),
		bgpOperationNotAllowedWhenSoftReconfigInIsDisabled(5257),
		bgpNotAllowedSoftRecfgInIsDisabledForTheGrpOrAnyPeerInGrp(5258),
		bgpCanNotEnablePeerWithoutCfgRemoteAsForThePeer(5259),
		bgpCanNotEnablePeerGrpWoCfgRemoteASPeerGrpOrAnyPeerInGrp(5260),
		bgpOperationNotAllowedWhenPeerIsBGPON(5261),
		bgpOperationNotAllowedWhenPeerGrpOrAnyPeerInGrpIsBGPON(5262),
		bgpOperationNotAllowedExternalPeer(5263),
		bgpOperationNotAllowedInternalPeer(5264),
		asListNotFound(5265),
		asListDuplicate(5266),
		asListAsPathEntryNotFound(5267),
		asListAsPathEntryDuplicate(5268),
		asListInvalidModeOfAsPathEntry(5269),
		asListInvalidAsRegularExpressionOfAsPathEntry(5270),
		asListInvalidRowStatusOfAsPathEntry(5271),
		communityListNotFound(5272),
		communityListDuplicate(5273),
 		communityListCommunityPathEntryNotFound(5274),
		communityListCommunityPathEntryDuplicate(5275),
		communityListInvalidModeOfCommunityPathEntry(5276),
		communityListInvalidValueOfCommunityEntry(5277),
		communityListInvalidRowStatusOfCommunityEntry(5278),
		bgpFeatureNotSupport(5279),
		bgpMd5EnabledWithoutPasswd(5280),
		bgpEnabledWithoutLocalAs(5281),
		bgpAggregateAdvertisePolicyWithoutAsSet(5282),
		bgpPeerHoldTimeLessThanKeepAliveTime(5283),
		bgpCommListCommunityStringUsed(5284),
		bgpNotFoundRowStatus (5285),
		bgpCannotConfigSystemLocalInterfaceAsPeer (5286),
		bgpDuplicateRowStatus (5287),
		communityListModificationNotAllowed(5288),
		sshEnableTrue(5501),
		rsaKeyNotExist(5502),
		dsaKeyNotExist(5503),
		rsaKeyGenMiss(5504),
		dsaKeyGenMiss(5505),
		sshShutDownInProcess(5506),
		sshInvalidPort(5507),
		invalidOperationOnWsmOrSamStg(5601),
		invalidOperationOnWsmOrSamVlan(5602),
		invalidOperationOnWsmOrSamPort(5603),
		invalidOperationOnSamPort(5604),
		opmImageFilenameTooLong (5701),
		serverSupportedOnOpmPortOnly (5702),
		commandValidOnlyIfMezzCardIsPresent (5703),
		serverPortAlreadyEnabled (5704),
		serverPortCannotBeDisabledWhileInService (5705),
		serverPortAlreadyDisabled (5706),
		serverPortSomeOtherServiceEnabled(5708),
		mplsInvalidRowStatus (6101),
		mplsNoIpInterface (6102),
		mplsInvalidSetWhenMplsIsEnabled (6103),
		mplsNotAnMplsInterface (6104),
		mplsInvalidSetWhenMplsInterfaceIsEnabled (6105),
		mplsInvalidSetWhenLdpIsEnabled (6106),
		mplsNotAnLdpInterface (6107),
		mplsInvalidGlobalAdminStatus (6108),
		mplsInvalidRouterId (6109),
		mplsInvalidTtl (6110),
		mplsInterfaceInvalidAdminStatus (6111),
		mplsInterfaceInvalidLabelDistMode (6112),
		mplsInterfaceInvalidLabelRetenMode (6113),
		mplsInterfaceInvalidLabelUseMode (6114),
		mplsInterfaceInvalidLabelReqMode (6115),
		mplsInterfaceInvalidLabelAdvMode (6116),
		mplsInterfaceInvalidMtu (6117),
		mplsInterfaceInvalidLabelProtocol (6118),
		mplsInterfaceInvalidIpAddr (6119),
		mplsInvalidLdpAdminStatus (6120),
		mplsInvalidLdpHoldTime (6121),
		mplsInvalidLdpHelloHoldTime (6122),
		mplsInvalidLdpHelloInterval (6123),
		mplsInvalidLdpMaxHops (6124),
		mplsInvalidLdpPathVectorLimit (6125),
		mplsInvalidLdpTargettedHelloHoldTime (6126),
		mplsLdpInterfaceInvalidTargetAddr (6127),
		mplsInvalidRsvpAdminStatus (6128),
		mplsInvalidRsvpPathUpdateTime (6129),
		mplsInvalidRsvpResvUpdateTime (6130),
		mplsInvalidRsvpHelloTime (6131),		
		mplsInvalidRsvpBlockStateAgingTime (6132),
		mplsInvalidRsvpMaxBundleMsgSize (6133),
		mplsInvalidRsvpMaxBundleMsgTime (6134),
		mplsInvalidRsvpMaxAckMsgTime (6135),
		mplsInvalidRsvpMaxAckMsgs (6136),
		mplsInvalidRsvpMaxMsgIdListSize (6137),
		mplsInvalidRsvpMaxMsgIdListTime (6138),
		mplsInvalidRsvpMaxPiggybackAckMsgs (6139),
		mplsInvalidRsvpPathAgingTimeMultiplier (6140),
		mplsInvalidRsvpResvAgingTimeMultiplier (6141),
		mplsInvalidRsvpHelloAgingTimeMultiplier (6142),
		mplsInvalidRsvpPathVectorLimit (6143),
		mplsInvalidRsvpMaxHops (6144),
		mplsInvalidRsvpRapidRetransmissionTime (6145),
		mplsInvalidRsvpRapidRetransmissionIncrement (6146),
		mplsInvalidRsvpRapidRetransmissionLimit (6147),
		mplsInvalidTunnelName (6148),
		mplsInvalidTunnelDescr (6149),
		mplsInvalidTunnelIsif (6150),
		mplsInvalidTunnelSignalProto (6151),
		mplsInvalidTunnelSetupPrio (6152),
		mplsInvalidTunnelHoldingPrio (6153),
		mplsInvalidTunnelSessionAttr (6154),
		mplsInvalidTunnelOwner (6155),
		mplsInvalidTunnelLocalProtectInuse (6156),
		mplsInvalidTunnelHopTblIndex (6157),
		mplsInvalidTunnelAdminStatus (6158),
		mplsInvalidTunnelRowStatus (6159),
		mplsInvalidTunnelStorageType (6160),
		mplsInvalidTunnelBandwidth (6161),
		mplsInvalidTunnelHopAddrType (6162),
		mplsInvalidTunnelHopIpv4Addr (6163),
		mplsInvalidTunnelHopIpv4PrefixLen (6164),
		mplsInvalidTunnelHopIpv6Addr (6165),
		mplsInvalidTunnelHopIpv6PrefixLen (6166),
		mplsInvalidTunnelHopASNum (6167),
		mplsInvalidTunnelHopLspid (6168),
		mplsInvalidTunnelHopType (6169),
		mplsInvalidTunnelIncludeExclude (6170),
		mplsInvalidTunnePathOptionName (6171),
		mplsInvalidTunnePathComp (6172),
		mplsInvalidTunnelHopRowStatus (6173),
		mplsInvalidTunnelHopStorageType (6174),
		mplsInvalidFtnRowStatus (6175),
		mplsInvalidFtnMask (6176),
		mplsInvalidFtnSourceIpAddr (6177),
		mplsInvalidFtnSourceIpMask (6178),
		mplsInvalidFtnDestIpAddr (6179),
		mplsInvalidFtnDestIpMask (6180),
		mplsIpCircuitNotUp (6181),
		mplsInvalidTunnelGrpId (6182),
		mplsTunnelGrpNoDestAddr (6183),
		mplsTunnelGrpExists (6184),
		mplsTunnelGrpNonExists (6185),
		mplsTunnelGrpInvalidRowStatus (6186),
		mplsTunnelGrpInvalidTunnelId (6187),
		mplsTunnelGrpTunnelNonExists (6188),
		mplsTunnelGrpInvalidPersistentFlag (6189),
		mplsTunnelGrpInvalidOperation (6190),
		mplsTunnelGrpOperationNotEntered (6191),
		mplsTunnelGrpMemberExist (6192),
		mplsTunnelGrpBackupTunnelExists (6193),
		mplsTunnelGrpNoPrimaryTunnel (6194),
		mplsTunnelMemberOfAnothergroup (6195),
		mplsInvalidTunnelListFormat (6196),
		mplsInvalidTunnelPriority (6197),
		mplsTunnelHopCreateNotEnoughParameters (6198),
		mplsTunnelGroupInvalidTunnelOperation (6199),
		vpnPortModeNotConfigurable (6201),
		vpnIncompatiblePortServiceTypeAndMode (6202),
		vpnPortInvalidMember (6203),
		vpnPortInvalidQtag (6204),
		vpnPortServiceTypeModificationNotAllowed (6205),
		vpnLocalSwitchingNotEnabled (6206),
		vpnDuplicateEntry (6207),
		vpnEntryNotFound (6208),
		vpnCannotCreateBrouterIncompatiblePortServiceType (6209),
		vpnAddVpnMemberNotAllowed (6210),
		vpnCannotEnableVpnNoMemberExists (6211),
		vpnCannotEnableVpnSwitchModeNoQtag (6212),
		vpnCannotEnableVpnNoTunnelGrpExists (6213),
		vpnCannotEnableVpnNoRemotePeerExits (6214),
		vpnTunnelExpPolicyIdDoesNotExists (6215),
		vpnIncompatibleTunnelExpPolicyTypeAndTunnelExpPolicyId (6216),
		vpnInvalidTunnelExpPolicyType (6217),
		vpnInvalidTunnelExpPolicyId (6218),
		vpnTunnelGroupIdDoesnotExists (6219),
		vpnVcGrpIdEntryDoesnotExists (6220),
		vpnTransparentPortCannotHaveQtagSpecified (6221),
		vpnPortAlreadyConfiguredForASpecificService (6222),
		vpnPortTransAlreadyBeAVpnMember (6223),
		vpnPortCannotChangePeerIdWhileEnabled (6224),
		vpnInvalidRcGrpId (6225),
		vpnLowerBwCannotBeGreaterThanUpperBw (6226),
		vpnUpperBwCannotBeLessThanLowerBw (6227),
		vpnLocalSwitchingNotSupported (6228),
		vpnTunnelGrpIdCannotChangeWhenVPNOperational (6229),
		vpnPortIsNotVpnMember (6230),
		vpnServiceCtypeLowerBwCannotBeConfigured (6231),
		vpnLowerBwCannotBeZeroForServiceAB (6232),
		vpnInvlidQtagNumOrRange (6233),
		vpnEntryNoMemActionSet (6234),
		vpnNotL2uniPort (6235),
		vpnAddQtagNotAllowed (6236),
		vpnEntryInvalidMemActionSet (6237),
		vpnCannotAddMoreThan128Qtags (6238),
		vpnQtagExistInOtherVpn (6239),
		vlanNotCreatedOrNotAssocitaedWithServerPort (6240),
		vlanPortNotServerPort (6241),
		invalidPortOrMltId (6242),
		tunnelGroupIdInTlsVpn (6243),
		tunnelGroupIdInP2pVpn (6244),
		oeAdmInvalidValue (6301),
		oeAdmInvalidKpalvIntVal (6302),
		oeAdmInvalidUDPPort (6303),
		vpnTlsRemotePeerDoesNotExist (6304),
		vpnTlsRemotePeerEntryExists (6305),
		vpnTlsTdidoesNotExist (6306),
		tlsVpnTunnelGrpShouldBeSpecified (6307),
		tlsVpnRemotePeerEntryNotFound (6308),
		tlsVpnDoesNotExists (6309),
		tlsVpnTdiCannotBeUnset (6310),
		tlsVpnTdiHasBeenUsed (6311),
		tlsVpnInvalidRemotePeerId (6312),
		vpnAddRemoveMemberNotAllowedWhileEnabled (6313),
		portServiceTypeNotconfiured (6314),
		vplsIncompatiblePortServiceType (6315),
		tlsVpnSetValidOnlyOnAddRemotePeer (6316),
		tlsVpnTunnelGrpOrLdpFecShouldBeSpecified (6317),
		tlsvpnBothTunnelGrpAndLdpFecCannotBeSpecified (6318),
		tlsVpnTunnelIdCannotBespecified (6319),		
		portIsAssociatedWithOtherTranparentUni (6401),
		portCanBeOnlyAssignedToSwitchedServiceTypeUni (6402),
		portCanBeOnlyAssignedToIpmcUniServiceTypeUni (6403),
		portCanBeOnlyAssignedToIpmcBiServiceTypeUni (6404),
		cannotSetIpMcastServiceTypeForEndPointUni (6405),
		portCanBeOnlyAssignedToQnq1ServiceTypeUni (6406),
		portCanBeOnlyAssignedToQnq2ServiceTypeUni (6407),
		portInOtherUniWithDifferentServiceType (6408),
		incompleteStandaloneRbsUni (6409),
		tlsUniCannotSetPortForRbs (6410),
		tlsUniCannotChangeParam (6411),
		tlsUniCannotChangeUniServiceType (6412),
		tlsUniCannotAddNonOpmPort (6413),
		tlsMappedVlanDoesNotExist (6414),
		tlsUniCanNotEnableWithoutPort (6415),
		tlsQtagAlreadyInUse (6416),
		tlsUniAlreadyExist (6417),
		tlsUniDoesNotExist (6418),
		tlsUniNotFound (6419),
		tlsTdiAlreadyExist (6420),
		tlsTdiDoesNotExist (6421),
		tlsTdiNotFound (6422),
		tlsTdiEndpointAlreadyExist (6423),
		tlsTdiEndpointDoesNotExist (6424),
		tlsTdiEndpointNotFound (6425),
		tlsTdiUserMacAlreadyExist (6426),
		tlsTdiUserMacDoesNotExist (6427),
		tlsTdiUserMacNotFound (6428),
		tlsRemoteUniAlreadyExist (6429),
		tlsRemoteUniDoesNotExist (6430),
		tlsRemoteUniNotFound (6431),
		tlsUniCannotStandaloneforrbs (6432),
		tlsTdiEndpointExist (6433),
		tlsTdiCannotChangeParam (6434),
		tlsTdiAdmAlreadyEnable (6345),
		tlsTdiAdmAlreadyDisable (6346),
		tlsTdiEndpointCannotChangeParam (6437),
		tlsTdiEndpointCosProfileNotFound (6438),
		tlsTdiEndpointSpokeOrP2p (6439),
		tlsUniOtherUniEnabled (6440),
		portIsInTlsService (6441),
		portPerformTaggingIsDisabled (6442),
		tlsUniPortdoesnotexist (6443),
		tlsSwitchEndpointCannotInEnableStateWithoutQtag (6444),
		tlsQnqEndpointCannotInEnableStateWithoutOuterQtag (6445),
		portHasDiffEtherTypeWithOtherEnabledUni (6446),
		tlsEnableQnqForUniToAddOuterQtag (6447),
		tlsTransparentEndpointCannotSetQtag (6448),
		tlsTransparentUniCannotAddedToManyToOneTdi (6449),
		tlsOneToOneEndPointCannotSetMultiQtag (6450),
		tlsTdiCannotSetManyToOneWithTransparentUni (6451),
		tlsCannotAddSameTransparentEndpointToTwoDifferentTdis (6452),
		tlsMappedNniVlanCannotHaveIpAddress (6453),
		tlsVlanWithIpAddressCannotBeUsedAsMappedNniVlan (6454),
		tlsMappedNniVlanMustBePortBased (6455),
		tlsMacTableWaterMarkIsIngoredWhenThereIsNoMacTableSize (6456),
		tlsTdiCanOnlyHaveOneTypeOfEndPoints (6457),
		tlsTdiCannotHaveMoreThanTwoP2PEndPoints (6458),
		tlsTdiCannotHaveMoreThanOneHubEndPoints (6459),
		tlsExpedTrafCanOnlyTrueForTransEpOrSwEpWithQtag4096 (6460),
		tlsExpediteTrafficNotApplyToEndpointOnQinqPort (6461),
		tlsTdiEndpointRemoteUni (6462),
		tlsQnq1EptCannotHaveInnerQtag (6463),
		tlsQnqOnlyApplyToLocalTlsPOrt (6464),
		tlsUniCannotAssignRbsRingAndStandAlone (6465),
		tlsSwitchedEndPointQtagInvalid (6466),
		tlsQnqEndPointQtagInvalid (6467),
		tlsSwitchedEptOnSamePortNeedDiffInnerQtag (6468),
		tlsQnq1EptOnSamePortNeedDiffInnerQtag (6469),
		tlsQnq2EptOnSamePortNeedDiffQtag (6470),
		tlsUniInvalidNonOpmPortType (6471),
		tlsUniCannotEnableWithoutServerPort (6472),
		tlsUniOpmServerCannotBeAccess (6473),
		tlsUniCannotSetServerPortWithoutUniPort (6474),
		tlsUniCannotAssignNonServerPort (6475),
		tlsUniAnotherServerportAlreadyAssigned (6476),
		tlsEptSetPortForUniBeforeConfigEpt (6477),
		tlsEptMacTableSizeExceedLimit (6478),
		tlsMacTableSizeExceedLimitForPort (6479),
		tlsOverridePbitNotSupportedForQnq1 (6480),
		tlsPriorityOverrideNotSupportedForOpmPort (6481),
		tlsPriorityOverrideCannotBeEnabledOnMultiVlansPort (6482),
		tlsTdiCannotChangeMuxModeWithActiveEpt (6483),
		tlsDestUniIsNotInGlobalUniMacTable (6484),
		tlsCannotSetMulticastMacAddrToRemoteUni (6485),
		tlsManyToOneEptDoesNotSupportQtag4096 (6486),
		tlsRemoteUniNotSupportedForA2AEpt (6487),
		tlsUniCannotBeAssignedPortAndRbsRing (6488),
		tlsUniPortIsNotStandaloneRbsPort (6489),
		cannotAssignRbsRingOrStandaloneRbsToQnqServiceUni (6490),
		tlsUniFailsToRemoveRbsRing (6491),
		tlsUniFailsToRemoveServerPort (6492),
		tlsUniFailsToRemoveRbsStandalone (6493),
		ringIdAndRbsIdAndPortAllMustBeZero (6494),
		standaloneRbsIdAndPortAllMustBeZero (6495),
		tlsTdiOnlySpokesOnSameServerPort (6496),
		tlsGsmPortHasOverLimitNubmerOfSwitchedUni (6497),
		tlsGsmPortHasOverLimitNubmerOfQnq2OuterTag (6498),
		tlsRsmPortHasOverLimitNubmerOfQnq2OuterTag (6499),
		lacpInvalidAggrsysPrio(6501),
		lacpInvalidAggrActorAdminKey(6502),
		lacpInvalidAggrColMaxDelay(6503),
		lacpInconsistentKey(6504),
		lacpInvalidVal(6505),
		lacpOutOfRangeKey(6506),
		lacpPortNotAggregatable(6507),
		lacpKeyModificationNotAllowedOnSltPort(6508),
		lacpOtherPortsWithSameKey(6510),
		vlacpOneofPortorMLTIdIsRequired(6511),
		vlacpDuplicatePeerMacAddress(6512),
		vlacpOutOfRangeMac(6513),
		poeInvalidAdminState(6601),
		poeInvalidDetecCtrlState(6602),
		poeInvalidPriorityState(6603),
		poeInvalidType(6604),
		poeInvalidPwrPairState(6605),
		poeInvalidUsageThreshold(6606),
		poeInvalidBackupDCPower(6607),
		poeInvalidNotificationControl(6608),
		diagVctPortNotCapable(6701),
		diagVctPortNotEnabled(6702),
		diagVctPortNotFound(6703),
		diagVctUnknownSet(6704),
		esmPortMirrorParameter(6705),
		modeNotCorrectForGranularity(6706),
		filterNotSupportedOnThisHardware(6707),
		esmPortNotSuppAsMirroringPort(6708),
		mirroredPortNotSuppAsServerPort (6709),
		targetAddressMissing(6801),
		testAlreadyRunning(6802),
		invalidTargetAddress(6803),
		invalidSourceAddress(6804),
		controlEntryAlreadyExists(6805),
		invalidIpAddressFormat(6806),
		invalidDataRange(6807),
		invalidIndex(6808),
		entryDoesNotExist(6809),
		controlEntryMaxLimitReached(6810),
		maxRowOutOfRange(6811),
		oeAdmPEEdgeOutgoingInterfaceNotConfigured (6901),
		oeAdmPEEdgeNotAllowedWhenAdmEnabled (6902),
		tlsServerPortForUniOnLegacyPortBeforeConfigEpt (6903),
		tlsEndptInvalidPriorityMapping (6904),
		tlsVlanBasedUniEndPtInvalidQtag (6905),
		tlsUniUnsupportedServiceType (6906),
		portIsNotEsmServerPort (6907),
		cannotSetOneToOneWithMultipleQtagsEndpoint (6908),
		tdiMgmtAlreadyEnabled (6909),
		tdiMgmtAlreadyDisabled (6910),
		mappedNniVlanDoesNotHaveIp (6911),
		cannotDeleteVlanWithTlsTdiAssociation (6912),
		cannotCreateIpWhileVlanTdiEnabled (6913),
		cannotDeleteIpWhileVlanTdiEnabled (6914),
		tlsTdiMappedVlanCannotHaveIp (6915),
		netMgmtTdiMappedVlanDoesNotHaveIp (6916),
		tlsUniInvalidNonOpmPortVlanType (6917),
		tlsAtmEndptsShareSameServerPort (6918),
		oeAdmPEEdgeSecOutgoingInterfaceNotConfigured (6919),
		oeAdmPEEdgeDhPriPortNotConfigured (6920),
		oeAdmPEEdgeDhSecPortNotConfigured (6921),
		oeAdmPEEdgePortIsUsedAsDhPriPort (6922),
		oeAdmPEEdgePortIsUsedAsDhSecPort (6923),
		oeAdmPEEdgeDhPortCanNotBeOpmPort (6924),
		oeAdmPEEdgeIpAddIsUsedAsPriInterface (6925),
		oeAdmPEEdgeIpAddIsUsedAsSecInterface (6926),
		tlsUniIsNotCreatedYet (6927),
		tlsUniCustIpVlanAlreadyCreated (6928),
		tlsUniCustIpVlanIsNotCreatedYet (6929),
		custIpVlanCannotBeDeletedWhileIsEnabled (6930),
		tlsUniSPIpVlanCannotBeEmptyForCreation (6931),
		custIpVlanIsMappedToDifferentLocalIpVlan (6932),
		serviceProvideVlanIsMappedToADifferentLocalIpVlan (6933),
		oeAdmPEEdgeDhPriMltNotConfigured (6934),
		oeAdmPEEdgeDhSecMltNotConfigured (6935),
		oeAdmPEEdgePortIsUsedAsDhPriMlt (6936),
		oeAdmPEEdgePortIsUsedAsDhSecMlt (6937),
		custIpVlanCannotModifyParamWhileInEnableState (6938),
		custIpVlanIpTblWaterMarkIsIngoredWhenZeroIpTblSize (6939),
		tlsSetPortForUniBeforeConfigCustIpVlan (6940),
		uniIpTableSizeExceedLimitForPort (6941),
		transparentUniNotSupportCustIpVlan (6942),
		serviceProviderIpVlanNotExist (6943),
		qnqUniSupportsCustIpVlanOnlyIfIs8100EtherType (6944),
		uniEtherTypeOnlyCanBe8100IfWithCustIpVlan (6945),
		custIpVlanUniServiceTypeCannotBeQnqIfNot8100Type (6946),
		tdiCannotUseAccessPortDefaultVlanAsMappedVlan (6947),
		custIpVlanIpTblArpTimerIsLessThanGlobalArpTimer (6948),
		cannotSetArpTimerIfCustIpVlanUniOperUp (6949), 
		cannotSetPriMappedVlanIfAdmNotInDualHomingMode (6950),
		cannotSetSecMappedVlanIfAdmNotInDualHomingMode (6951),
		oeAdmPEEdgeDhPriAndSecMappedVlansCannotBeTheSame (6952),
		tdiCannotHaveSameValueForPriAndSecMappedVlan (6953),
		tdiSecMappedVlanCannotBeConfiguredWhenAdmIsNotDualHomed (6954),
		ipAddressBeingUsedAsAdmPriOrSecInterface (6955),
		tlsUniCustIpVlanInvalidPriorityMapping (6956),
		tlsUniCustIpVlanCosProfileNotFound (6957),
		cannotEnableAdmInDhModeWithoutSecOutgoingInterface(6958),
		cannotDeleteIpWhileVlanTdiMgmtEnabled (6959),
		standaloneUniCannotBeEnabledWithNonStandalonePort (6960),
		custIpVlanParamValueRemainsSame(6961),
		uniWithAtmPortSupportsTlsSwitchServiceOnly(6962),
		atmPortOnlyCanBeAssignedToTlsSwitchedServiceUni(6963),
		portIsAssociatedWithOtherServiceTypeUni(6964),
		etherTypeOnlyCanBe8100IfItsUniAssociatedWithCustIpVlan(6965),
		cannotModifyEtherTypeWhileItsEndptOperationUp(6966),
		tdiCannotSupportPbtAndMappedVlan(6967),
		tdiCannotSupportMimAndMappedVlan(6968),
		tdiMappedVlanIsAlreadyUsedForPbt(6969),
		pbtHasToBeEnabledForTdiMimEncap(6970),
		commandIsSupportedOnEsmPortOnly(6971),
		canNotEnableTdiWithMimEncapWhenMimEtherTypeIsNotSet(6972),
		canNotEnablePbtTdiWhenMezzCardIsNotPresent(6973),
		onlyOpmPortCanBeAssignedToRbsRing (7001),
		portIsAlreadyConfiguredInTheRbsRing (7002),
		portIsBeingUsedAsSecondaryPortInThisRbsRing (7003),
		portIsBeingUsedAsPrimaryPortInThisRbsRing (7004),
		portIsBeingUsedInOtherRbsRing (7005),
		portCannotBeUsedAsPrimaryAndSecondaryInRbsRing (7006),
		standaloneRbsPortCanBeAssignedToOnlyOneUni (7007),
		standaloneRbsPortAlreadyCreated (7008),
		portCannotBeModfiedWhenRingEnable (7009),
		portCannotBeModifiedWhileTheRbdRingUniIsEnabled (7010),
		rbsRingAlreadyExist (7011),
		rbsRingDoesNotExist (7012),
		rbsRingNotFound (7013),
		rbsRingCanNotEnableWithoutPort (7014),
		standaloneRbsPortDoesNotExist (7015),
		onlyOpmPortCanBeAssignedToStandalone (7016),
		rbsRingUniIsEnable (7017),
		rbsStandaloneUniIsEnable (7018),
		rbsRingCannotChangeParam (7019),
		rbsStandaloneCannotChangeParam (7020),
		rbsRingInvalidPortId (7021),
		rbsStandaloneInvalidPortId (7022),
		rbsRingTableSizeExceedLimit (7023),
		rbsPortCanOnlyAssignedOneUni (7024),
		rbsRingInvalidRbsId (7025),
		rbsRingHasOverLimitNubmerOfSwitchedUni (7026),
		vlanContainsRingPortAssociatedWithOtherIpmcEnabledVlan (7027),
		cannotAddSameRingPortToMoreThanOneIpmcEnabledVlan (7028),
		cannotEnableIpmcOnTlsIpmcDisabledRingVlan (7029),
		cannotDisableTlsIpmcOnIpmcEnabledRingVlan (7030),
		cannotAddRingPortToIpmcEnabledTlsIpmcDisabledVlan (7031),
		cannotAddRingToIpmcEnabledTlsIpmcDisabledVlan (7032),
		cannotAddSameRingToMoreThanOneIpmcEnabledVlan (7033),
		vlanContainsRingAssociatedWithOtherIpmcEnabledVlan (7034),
		esuDhRingCannotChangeParam (7035),               
		esuDhRingCannotBeDeletedUniIsEnable (7036),
		onlyOpmPortCanBeAssignedToDhRingPort(7037),
		portCannotBeModfiedWhenDhRingEnable (7038),
		paramCannotBeModifiedWhileTheDhRingUniIsEnabled (7039),
		opmPortCannotBeAssignedToIbtPort (7040),
		esuDhRingCanNotEnableWithoutPort (7041), 
		ibtPortNotPresent (7042),
		ringIdAlreadyUsedForOtherType (7043),
		esuDhRingIbtPortOrMltNotConfig (7044),
		ringPortNotPresent (7045),
		ringOnlyCanBeConfigEitherIbtPortOrIbtMlt (7046), 
		ibtVidCannotBeDefaultVlan (7047), 
		ringCannotBeEnabledWithoutIbtVid (7048),
		ringCannotBeEnableddWhileIbtMltHasNoPort (7049),
		mltPerformTaggingIsDisabled (7050),
		ringCannotBeEnabledWithoutPartnerPortMac (7051),
		ringOrIbtPortMustBePerformTaggingEnabled (7052),
		ringPortMustBePerformTaggingEnabled (7053),
		cannotDisableIbtPortPerformTagging (7054),
		cannotDeleteIbtMlt (7056), 
		uniMacCannotBeDeleteWhileIsInUse (7057),
		destUniIdIsRequiredForUserMacCreation (7058),
		standaloneCannotCreateUnisOnBothGigPorts (7059),
		removeVlanIdFromThisRingVlanListBeforeAssignItAsIbtVid (7060),
		vlanIsBeingUsedAsIbtVlanForThisRing (7061), 
		esuRingDoesNotHavePrimaryOrSecondaryPortsAssigned (7062), 
		esuDhRingDoesNotHavePrimaryOrSecondaryPortsAssigned (7063),
		primaryPortNotPresent(7064),
		secondaryPortNotPresent(7065),
		esuStandalonePortNotPresent(7066),
		cannotDirectlyAssignMltPortAsIbtPort(7067),
		vlanWithoutIpCannotBeAssignedToMgmtEnabledTdi(7068),
		uniCannotBeSetToTransparentWhilePortIsAssociatedWithOtherUni(7069),
		cannotSetPt2PtOrSpokeTypeWithoutRemoteUniWhileEndptIsEnabled(7070),
		remoteUniCannotBeResetInPt2PtOrSpokeEndptWhileItIsEnabled(7071),
		muxModeCannotBeManyToOneWhileTdiEndpointWithQtag4096(7072),
		custIpVlanCannotChangeParam(7073),
		custIpVlanIsBeingUsedAsEndptQtagInThisSubnet(7074),
		qtagIsBeingUsedAsCustIpVlanInThisSubnet(7075),
		ringCannotBeDeletedWhileItsUniAssociateWithEndpt(7076),
		cannotRemoveAllQtagsWhileEndptAdminStateEnabled(7077),
		cosProfileTableIndexAlreadyExist (7101),
		cosProfileTableIndexNotFound (7102),
		cosProfilePremiumUnitError (7103),
		cosProfilePremiumCirError (7104),
		cosProfileGoldUnitError (7105),
		cosProfileGoldCirError (7106),
		cosProfileSilverUnitError (7107),
		cosProfileSilverCirError (7108),
		cosProfileStandardUnitError (7109),
		cosProfileStandardPirError (7110),
		cosProfileTableNameAlreadyExist (7111),
		cosProfileDeleteTableNameIndexError (7112),
		cosProfileNameFieldCannotBeEmpty (7113),
		cosProfilePremiumCirRateOutOfRange (7114),
		cosProfileGoldCirRateOutOfRange (7115),
		cosProfileSilverCirRateOutOfRange (7116),
		cosProfileStandardPirRateOutOfRange (7117),
		changingPremCirUnitOrRateCauseTotalCirExceedStndPir (7118),
		changingGoldCirUnitOrRateCauseTotalCirExceedStndPir (7119),
		changingSilverCirUnitOrRateCauseTotalCirExceedStndPir (7120),
		changingStandardPirUnitOrRateCauseStndPirLessThanTotalCir (7121),
		premTbMaxKbCannotBeModifiedWhileItsCtlIsAutomatic (7122),
		goldTbMaxKbCannotBeModifiedWhileItsCtlIsAutomatic (7123),
		silverTbMaxKbCannotBeModifiedWhileItsCtlIsAutomatic (7124),
		stndTbMaxKbCannotBeModifiedWhileItsCtlisAutomatic (7125),
		cannotDeleteCosProfileWhileIsUsedInCustIpVlanOrTdiEndpt (7126),
		mcastRateCannotBeMoreThan15WhileMcastUnitIs64k(7127),
		cannotSetMcastUnitTo64kWhileMcastRateIsMoreThan15(7128),
		tdcontTestEntryAlreadyExists (7201), 
		tdcontTestEntryDoesNotExist (7202),
		testInProgress (7203),
		tdiHasBeenSet (7204),
		sourceUniDoesNotExist (7205),
		tdcTdiDoesNotExist (7206),
		tdiOrSrcUniDoesNotAssociateWithTheValidEndpoint (7207),
		tdiEndpointIsDisabled (7208),
		tdcOutofHistoryRange (7209),
		testNotInProgress (7210),
		srcUniHasBeenSet (7211),
		dstUniHasBeenSet (7212),
		nameExist (7213),
		tdcConfigNotDone (7214),
		mcastUcastBothZero (7215),
		uniIsNotOnPort (7216),
		noQtagForTdiInMappedUni (7217),
		priorityNeeded (7218),
		tdiIsDown (7219),
		testIsNotPeriodicRun (7220),
		periodicRateCannotBeZero (7221),
		dstUniHasNotBeenConfigured (7222),
		tdcTdiHasNotBeenConfigured (7223),
		unicastTestIsNotAllowedWithDestPortSet (7224),
		tdcTestDstPortOutOfRange (7225),
		dstPortCannotBeSetInUnicastTest (7226), 
		dstPortHasBeenSet (7227),
		mplsTunnelExists (7301),
		mplsInvalidTunnelGrpTunnelDestnNoMatch (7302),
		mplsInvalidLabelRecordFlagSet (7303),
		mplsInvalidSetWhenRsvpEnabled (7304),
		mplsTunnelGrpInvalidHelloInterval (7305),
		mplsTunnelHopToIpMapInvalidPrefixLen (7306),
		mplsTunnelHopToIpMapHopNameExists  (7307),
		mplsTunnelHopToIpMapInvalidHopName (7308),
		mplsTunnelHopToIpMapIpAddressExists (7309),
		ipv6VlanDoesnotExist (7401),
		ipv6InvalidInstance(7402),
		ipv6InvalidParameter(7403),
		ipv6AttrNotImplemented(7404),
		ipv6EntryDuplicate(7405),
		ipv6EntryNotExist(7406),
		ipv6InvalidIdentifierLength(7407),
		ipv6CircuitDoesNotExist(7408),
		ipv6PortNotPowerRanger(7409),
		ipv6InvalidInterfaceIdentifier(7410),
		ipv6CannotChangeWhenAdminEnable(7411),
		ipv6InvalidReasmMaxSize(7412),
		ipv6InvalidReachableTime(7413),
		ipv6InvalidPrefixLength(7414),
		ipv6InvalidSendAdverts(7415),
		ipv6InvalidMaxInterval(7416),
		ipv6InvalidMinInterval(7417),
		ipv6InvalidRetransmitTimer(7418),
		ipv6InvalidDefaultLifeTime(7419),
		ipv6InvalidCurHopLimit(7420),
		ipv6InvalidManagedFlag(7421),
		ipv6InvalidOtherConfigFlag(7422),
		ipv6InvalidDadNsNum(7423),
		ipv6InvalidPhysicalAddress(7424),
		ipv6InvalidNetToPhysicalType(7425),
		ipv6NeighborDuplicate(7426),
		ipv6NeighborDoesNotExist(7427),
		ipv6InvalidInvalidIpv6Addr(7428),
		ipv6PrefixDuplicate(7429),
		ipv6InvalidPrefix(7430),
		ipv6InvalidInterfaceType(7431),
		ipv6NexthopOrIndexReq(7432),
		ipv6NexthopIsLinklocBothIndexHopReq(7433),
		ipv6StaticRouteDistanceReq(7434),
		ipv6StaticRouteDuplicate(7435),
		ipv6StaticRouteInvalid(7436),
		ipv6OspfInvalidRouterId(7437),
		ipv6OspfNotSupported(7438),
		ipv6OspfAreaDoesNotExist(7439),
		ipv6OspfAlreadyExist(7440),
		ipv6OspfInterfaceInvalid(7441),
		ipv6OspfInterfaceExists(7442),
		ipv6OspfInterfaceNotExists(7443),
		ipv6OspfAreaAggregateEntryExists(7444),
		ipv6OspfAreaAggregateEntryDoesNotExist(7445),
		ipv6OspfInvalidAreaRangeMask(7446),
		ipv6OspfAreaCannotDeleteBackbone(7447),
		tcpConnectTblPermittedStateIsDelete(7448),
		ipv6InterfaceVlanNotFound(7449),
		ipv6TunnelInterfaceDoesnotExist(7450),
		ipv6TunnelNotImplemented(7451),
		ipv6TunnelInvalidOperation(7452),
		ipv6TunnelInvalidType(7453),
		ipv6TunnelInterfaceAlreadyExist(7454),
		ipv6TunnelRemAddrShldBeZero(7455),
		ipv6VlanDoesNotMatchPreviousVlanid(7456),
		ipv6UvifDoesNotExist(7457),
		ipv6MldNotEnabled(7458),
		ipv6MldInterfaceExists(7459),
		ipv6MldInterfaceDoesNotExist(7460),
		ipv6MldInvalidQueryInterval(7461),
		ipv6MldInvalidVersion(7462),
		ipv6MldInvalidMaxRespdelay(7463),
		ipv6MldInvalidRobvar(7464),
		ipv6MldInvalidLlqi(7465),
		ipv6RedistributionInvalidOperation(7466),
		ipv6InvalidMaxRouterAdvertInterval(7467),
		ipv6InvalidMinRouterAdvertInterval(7468),
		ipv6CannotSetSummaryAsFalseIfNotStubArea(7469),
		ipv6CannotModifyStubMetricIfNotStubArea(7470),
		ipv6GatewayMustBeOnMgmtInterface(7471),
		ipv6OspfNbmaNbrAlreadyExist(7472),
		ipv6OspfInterfaceNotNbma(7473),
		ipv6OspfNbmaTunnelNot624(7474),
		ipv6OspfNbmaNbrNotExist(7475),
		cannotConfigureAddrWhichIsLinkLocal(7476),
		addrEntryDoesNotExist(7477),
		ipv6TunnelCannotHaveMoreThanOneAddr(7478),
		cannotChangeAddressType(7479),
		cannotConfigureNetAddr(7480),
		invalidInetNetworkAndMask(7481), 
		cannotConfigureHostAddr(7482),
		ipv6InterfaceIdCannotBeChanged(7483),
		ipv6TunnelLocalAndRemoteIpAddressCannotBeSame(7484),
		ipv6StaticRouteWrongNexthop(7485),
		ipv6EuiInterfacePrefixCannotBeGreaterThan64(7486),
		idInvalid(7501),
		notExist(7502),
		duplicate(7503),
		nameInvalid(7504),
		notenablemixedmlt(7505),
		portconflictmixedmlt(7506),
		actInUse(7601),
		actFieldTooMany(7602),
		actPatternNotExist(7603),
		actErrApplyStateTrue(7604),
		actMaxPatternExceeded(7605),
		aclActNotExist(7606),
		aclTypeInvalid(7607),
		aclDefActionInvalid(7608),
		aclGlobActionInvalid(7609),
		vlanInvalid(7610),
		portInvalid(7611),
		aclMltInvalid(7612),
		aclInUse(7613),
		aclInvalidState(7614),
		aclActNotApplied(7615),
		aclActVlanAttrSpecified(7616),
		aclActPortAttrSpecified(7617),
		aclPortBased(7618),
		aclVlanBased(7619),
		actNoAttributesConfigured(7620),
		aclErrPortAlreadyInAcl(7621),
		aclErrVlanAlreadyInAcl(7622),
		aceAclIdInvalid(7623),
		aceAclNotExist(7624),
		aceInUse(7625),
		aceMax(7626),
		aceModeIllegal(7627),
		aceDscpIllegal(7628),
		aceDot1pIllegal(7629),
		aceUnreachIllegal(7630),
		acePoliceIllegal(7631),
		aceAclInvlanPoliceNotAllLanes(7632),
		aceInvalidAdminState(7633),
		aceEgressQueueInvalid(7634),
		aceEgressQueue1gInvalid(7635),
		aceEgressQueue10gInvalid(7636),
		aceEgressNNSCInvalid(7637),
		acePoliceInvalidMode(7638),
		aceAttrNotExistInAct(7639),
		aceInsuffActionAttr(7640),
		maxAceForSystem(7641),
		aceValMoreThanActPatternLen(7642),
		aceMltIndexIllegal(7643),
		aceModeNotPermit(7644),
		aceNotPermitIngress(7645),
		aceParmNotDefault(7646),
		aceAttrConflict(7647),
		defaultIdnoCreate(7648),
		defaultIdnoDelete(7649),
		defaultIdnoModify(7650),
		mltPortAclConflict(7651),
		aceNoModeModify(7652),
		aclNoAccept(7653),
		qosPolicyLaneExist(7701),
		qosPolicyLaneNotExist(7702),
		qosPolicyPkRateInvalid(7703),
		qosPolicySvcRateInvalid(7704),
		qosPolicyLaneInvalid(7705),
		qosPolicyValidAcesPresent(7706),
		qosTxQSetQmaxInvalid(7707),
		qosTxQSetQmaxChangeNotAllowed(7708),
		qosTxQSetBalQInvalid(7709),
		qosTxQSetHipriQInvalid(7710),
		qosTxQSetLopriQInvalid(7711),
		qosTxQSetMaxQExceed(7712),
		qosTxQSetPortNotRMod(7713),
		qosTxQSetQInvalid(7714),
		qosTxQSetQNotAssign(7715),
		qosTxQSetMinRateGtMaxrate(7716),
		qosTxQSetQMaxAfter8Adjust(7717),
		qosTxQSetPortFeIncompatibleQset64(7718),
		qosTxQSetPortGbIncompatibleQset8(7719),
		qosTxQSetModificationNotAllowed(7720),
		qosTxQSetQLengthWredModNotAllowed(7721),
		tlsTdiCannotDisableUniWithActiveEndpoints (7901),
		tlsTdiCannotDisableTdiWithActiveEndpoints (7902),
		tlsUniMultipleAccessPortNotSupported (7903),
		cannotDisableUniWithActiveCustIpVlan (7904),
		cannotDeleteUniWhileCustIpVlanExists (7905),
		mstpStpCannotBeEnabledOnOpmPort (7906),
		rstpStpCannotBeEnabledOnOpmPort (7907),
		eapGuestAndMultiMac (8001),
		eapCannotModifyMaxNonEapClients(8002),
		eapInvalidMaxNonEapValue(8003),
		eapUnknownMacAndEap(8004),
		ipfixStateAlreadyEnabled(8101),
		ipfixStateAlreadyDisabled(8102),
		ipfixInvalidSlotNumber(8103),
		ipfixNotADPMSlot(8104),
		ipfixInvalidActiveTimeout(8105),
		ipfixInvalidAgingInterval(8106),
		ipfixInvalidExportInterval(8107),
		ipfixInvalidTemplateRefIntervalSec(8108),
		ipfixInvalidTemplateRefIntervalPkts(8109),
		ipfixCollectorNotConfigured(8110),
		ipfixTwoCollectorAlreadyConfigured(8111),
		ipfixOnlyUdpProtocolSupported(8112),
		ipfixInvalidCollectorDestPort(8113),
		ipfixInvalidHashPolynomialCoeff(8114),
		ipfixInvalidHashPolynomialSeed(8115),
		ipfixInvalidHashKeyId(8116),
		ipfixInvalidSamplingRate(8117),
		aceIpfixStateIllegal(8118),
		tacacsIllegalIpAddress(8201),
		tacacsIllegalPriority(8202),
		tacacsMaxServersReached(8203),
		tacacsRadiusEnabled(8204),
		tacacsNoKeyGiven(8205),
		isisPwdInvalid (8301),
		isisKeyIdInvalid (8302),
		isisPwdExists (8303),
		isisNoKeyId (8304),
		isisInvalidAuthType (8305),
		isisCsnpIntInvalid (8306),
		isisRxmtLspIntInvalid (8307),
		isisRtrTypeInvalid (8308),
		isisNetLenInvalid (8309),
		isisSysidError (8310),
		isisManAreaAddrToomany(8311),
		isisManAreaError(8312),
		isisNetEntryExists (8313),
		isisSummAddrExists (8314),
		isisSummAddrError (8315),
		isisInvalidSubnetMask (8316),
		isisEnabledOnInterface (8317),
		isisCannotChangeMetricTypeFromWideToNarrow (8318),
		isisInvalidCircType(8319),
		isisSysIdInvalid(8320),
		isisSysIdRuntimeChange(8321),
		isisInvalidCircuitId(8322),
		isisCircuitAlreadyExists(8323),
		isisCircuitDoesNotExist(8324),
		isisInvalidIntfIndex(8325),
		isisLevelRouterDoesNotSupp(8326),
		isisManAreaNotConfigured(8327),
		isisL2OnlyNotSupported(8328),
		isisPriorityOnlyForBcastType(8329),
		isisMetricValueInvalidForNarrowType(8330),
		isisL2onlyCircuitExists(8331),
		isisMinLspIntGreaterThanMaxLspInt(8332),
		isisMaxLspIntLessThanMinLspInt(8333),
		nsnaNoRedVlan(8401),
    		nsnaRedVlanExists(8402),
		nsnaGlobalEnabled(8403),
		nsnaNoVlanColor(8404),
		nsnaVlanHasColor(8405),
		nsnaVlanNonEmpty(8406),
		nsnaNoFilterForNsnaVlan(8407),
		nsnaPortHasFilter(8408),
		nsnaNoUplinkDhcpFilter(8409),
		nsnaYellowSubnetNotSpecified(8410),
		nsnaNoNsnasSubnet(8411),
		nsnaMaxNsnasSubnet(8412),
		nsnaNoSshDaemon(8413),
		nsnaIncorrectGreenVlan(8414),
		nsnaIncorrectUplinkVlan(8415),
		nsnaIncorrectVoipVlan(8416),
		nsnaPortIsEap(8417),
		nsnaPortOperationNotAllowed(8418),
		nsnaUnknownMac(8419),
		nsnaExceedMaxNumEntry(8420),
		nsnaStaticEntryExists(8421),
		nsnaOperationNotAllowedOnMirroredPort(8422),
		nsnaInvalidHelloInact(8423),
		nsnaVlanFlushNotAllowed(8424),
		nsnaNoUplinkVlans(8425),
		nsnaVlanFilterRemapInProgress(8426),
		cfmNoParamChange(8501),
		cfmDomainExists(8502),
		cfmDomainDoesNotExists(8503),
		cfmMaintenanceAssociationExists(8504),
		cfmMaintenanceAssociationDoesNotExists(8505),
		cfmChangeNotAllowedWhenEnabled(8506),
		cfmMepExists(8507),
		cfmMepDoesNotExists(8508),
		cfmTrunkExists(8509),
		cfmTrunkDoesNotExists(8510),
		cfmOperationNotAllowedWhenMepsExist(8511),
		cfmVlanDoesNotExist(8512),
		cfmVlanIsNotPbt(8513),
		cfmVlanPortNotMember(8514),
		cfmOneTrunkPerAssociation(8515),
		cfmTrunkAlreadySpecifiedState(8516),
		cfmTrunkMissingFields(8517),
		cfmTrunkMissingRemMac (8518),
		cfmTrunkGrpExists(8519),
		cfmTrunkGrpDoesNotExists (8520),
		cfmTrunkGrpCannotReplaceTrunk(8521),
		cfmServiceGrpExists(8522),
		cfmServiceGrpDoesNotExists(8523),
		cfmDiscardUnkMacNotSet(8524),
		cfmInvalidPbtVlan(8525),
		cfmInvalidPortType(8526),
		cfmSGMissingFields(8527),
		cfmSGMissingRemMac(8528),
		cfmSgingAndPortNotAllowed(8529),
		cfmSgDualHomeRingNotSupported(8530),
		cfmMepInUse(8531),
		cfmSgPortInvalid(8532),
		cfmEndPtMissingFields(8533),
		cfmPbtVlanInUse(8534),
		cfmMaDomainNameFieldCannotBeEmptyForCreation(8535),
		indexIsBeingUsedByOtherDomain(8536),
		cfmAssnIndexCantBeZeroForCreation(8537),
		indexIsBeingUsedByOtherMaAssn(8538),
		cfmOperationNotAllowedWhenMasExistUnderMd(8539),
		cfmDomainIndexCantBeZeroForCreation(8540),
		cfmAssnDoesNotExist(8541),
		cfmMepIdCannotBeNullForCreation(8542),
		cfmMaAssnNameFieldCannotBeEmptyForCreation(8543),
		cfmMepDeleteNotAllowedWhenAlreadyAssignedToTdi(8544),
		cfmCannotDeleteRemoteMep(8545),
		cfmMdDeleteNotAllowedWhenAlreadyAssignedToTrunk(8546),
		cfmMdDeleteNotAllowedWhenAlreadyAssignedToSg(8547),
		cfmMdDeleteNotAllowedWhenAlreadyAssignedToEp(8548),
		cfmCannotDeleteIfPortInUseByPbt(8549),
		cfmCannotRemovePortFromPbtStg(8550),
		pbtVlanMustUsePbtStg(8551),
		pbtVlanCannotReassign(8552),
		pbtVlanCannotRemoveFromMlt(8553),
		cfmMepCanNotEnableWhenCfmEtherTypeIsNotSet(8554),
		invalidVrfId(8601),
		vrfInstanceAlreadyExists(8602),
		vrfInvalidVrfInstance(8603),
		communityAlreadyExists(9101),
		communityDoesnotExist(9102),
		communityStorageTypePermanent(9103),
		defaultEntryNotDeletable(9104),
		invalidAccessPolicyStrict(9105),
		targetAddressNotExist(9106),
		cannotChangeCurrentAndDeprecatedMib(9107),
		portMirroringTxNotSupportForThisHardwareRevision(9301),
		cannotSetMode(9302),
		cannotSetFraming(9303),
		cannotModifyInLaneMode(9304),
		stpIsNotAllowedToBeEnabledOnIstPort(9305),
		mirroredPortSupportRXModeOnly(9306),
		secondaryCpuNotActive(9307),
		commandNotAllowedInPrimaryCpu(9308),
		pcapUserDefinedDataInConsistency(9309),
		pcapFilterTblEntryNotFound(9310),
		pcapFilterTblDuplicateEntry(9311),
		pcapBufferSizeExceedsMaximumRamLimit(9312),
		portPcapIsActive(9313),
		pcapCommandNotAllowedWhenPcapIsEnabled(9314),
		invalidNumberOfHexDigits(9315),
		commandNotAllowedInHaCpuMode(9316),
		pcapCommandNotAllowedIn3SlotChassis(9317),
		pcapNoMemoryAllocatedForPcap(9318),
		pcapCannotBeEnabledWhenAutosaveInProgress(9319),
		pcapInvalidTimerRangeValue(9320),
		cannotSetPortAdminRouting(9322),
		smltNotAllowedObBrouterPort(9323),
		pcapOctapidNotInitialized(9324),
		pcapNoPackets(9325),
		pcapInsufficientDiskSpace(9326),
		pcapAutoSaveOrCopyCommandInProgress(9327),
		rmCommandNotAllowedWhenRemoteMirroringIsEnabled(9328),
		rmVlanNotPortBasedVlan(9329),
		rmPortNotMemberOfVlan(9330),
		rmSrcMacAddressNotSet(9331),
		rmRemoteMirroringActiveInOctapd(9332),
		rmRmtExceedsMaxLimit(9333),
		rmVlanIdNotSetForRmtPort(9334),
		rmDstMacNotSet(9335),
		rmPortDuplicateEntry(9336),
		rmPortEntryNotCreated(9337),
		invalidRxMirroringPort (9338),
		invalidTxMirroringPort (9339),
		invalidBothMirroringPort (9340),
		portIsBeingUsedForOtherSer (9341),
		portIsAlreadyConfigured (9342),
		commandNotSupport (9343),
		maxEgressMirroredPort (9344),
		portEapAuthorized(9345),
		invalidAdminDuplexSpeedCombo(9346),
		vplsMgmtVlanApplyToVplsPort (9347),
		repeaterDoesNotExist (9348),
		repeaterAlreadyExists (9349),
		repeaterIdOutOfRange (9350),
		repeaterPortNotPresent (9351),
		brouterPortCannotBeUsedAsRepeater (9352),
		portIsBeingUsedAsRepeaterPort (9353),
		vlanIsBeingUsed (9354),
		quoteNotAllowedInsideTheString (9355),
		duplicateName (9356),
		repeaterFirstAndSecondPortCannotBeSame (9357),
		repeaterPortCannotbeAssignedIp (9358),
		mltPortCannotBeRepeaterPort (9359),
		portIsRepeaterPort (9360),
		portIsNot8GELegacyPort (9361),
		portEapEnabled(9362),
		rateLimitingrmodPort(9363),
		bandwidthLimitingNonrmodPort(9364),
		egressRateLimitingNotAppToNonRModPort(9365),
		cannotSetAutoNegAd(9366),
		invalidAutoNegAdSpecified(9367),
		featureNotApplyToMixedMlt(9368),
		rateLimitingExistsForMlt(9369),
		differentPortConfigurationForMlt(9370),
		rModuleOnlyOneMirroredPortPerLane(9371),
		ieee8021pOverrideNotAppToNonRModPort(9372),
		portMirroringTxFilterNotSupportForThisHardwareRevision(9373),
		portIsDownOperationNotAllowed(9374),
		portSffdEnableError(9375),
		portTxFlowControlNotSupportedForThisHW(9376),
		portFcPause0NotSupportedForThisHW(9377),
		portFcPauseTimeNotSupportedForThisHW(9378),
		portEgressMirroringCountExceededOnCard(9379),
		slppInvalidTxInterval(9380),
		slppInvalidRxThreshold(9381),
 		recordReserveTypeInvalid(9401),
		recordReserveOutOfRange(9402),
		recordReserveExceedPhyLim(9403),
		cannotUpNonEticketCard(9404),
		cannotUpNon128KCard(9405),
		naapVlanNotConfigured(9406),
		lpMiniSlotNotPresent(9407),
		lpSlotDisabled(9408),
		lpSlotEnabled(9409),
		cannotUpNonEmmodeCard (9410),
		cannotUpNonRmodeCard (9411),
		cannotUpNonRspCard (9412),
		dnsDuplicateEntry(9413),
		dnsEntryNotFound(9414),
		dnsEntryNotCreated(9415),
		smartCpldNotSupported(9416),
		dnsEntryCantHaveBothIpv4AndIpv6Addr(9417),
		tenGEMltPortCannotBeAddedToStgWithSMLT(9501),
		tenGEPortCannotBeAddedToStgWithSMLT(9502),
		stgCannotRemoveTlsEndPointPortMember (9503),
		rstpInvalidVal (9504),
		mstpInvalidVal (9505),
		invalidMask (9506),
		bpduMacAddressRangeInUse (9507),
		bpduMacAddressRangeNotConfigured (9508),
		bpduMacAddressNotInConfiguredRange (9509),
		priorityValueMustBeAMultipleOf4096 (9510),
		valueMustBeAMultipleOf100 (9511),
		mstpCannotSetPriorityBeforeCreatingMstiBridge (9512),
		commandIsNotSupportedForMltPort (9513),
		switchIsNotInRstpMode (9514),
		switchIsNotInMstpMode (9515),
		portPriorityvalueMustBeAMultipleOf16 (9516),
		portIsNotAMemberOfThisMsti (9517),
		onlyDefaultInstanceSupportedInRstpMode (9518),
		maxAgeMustEqualOrGreatThan2XForwardDelayMinus1Second (9519),
		maxAgeMustEqualOrGreatThan2XPortHelloTimePlus1Second (9520),
		ospfOverlappingSummarizedRange(9601),
		ospfTeReservableBandwidthCannotBeBiggerThanMaxBandwidth (9602),
		ospfTeMaxBandwidthCannotBeSmallerThanReservBandwidth (9603),
		pcapBufferSetFail (9604),
		ospfHelloIntNotGreatDeadInt(9605),
		cluserInvalidId (9901),
		clusterDoesNotExist (9902),
		clusterAlreadyExists (9903),
		clusterSizeExceeded (9904),
		invalidMiniSlot (9905)
	}
	MAX-ACCESS read-only
	STATUS current
	DESCRIPTION "This variable is used primarily as an enumeration
		      to list the proprietary return codes that this
		      device can send to a management station in
		      response to a failed SNMP operation."
	DEFVAL { none }
	::= { rcError 4 }
	
-- *** ABOVE SECTION IS GENERATED FROM ../mib_tools/error.mib ***

rcErrorSendTrap OBJECT-TYPE
        SYNTAX        TruthValue
        MAX-ACCESS    read-write
        STATUS        current
        DESCRIPTION   "Indicates whether to send trap upon receiving an
                      error in the system."
	DEFVAL	      { true }
        ::= { rcError 5 }

END
