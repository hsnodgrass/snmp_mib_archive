-- The following is the SNMP trap MIB definition files from various vendors
-- that are part of NSA trap agents.  These agents are integrated into NSA
-- version 2.5 or later but they are usig generic SNMP trap PDU encodings
-- without containing NSA-specific varbind, e.g. like version varbind in its
-- SNMP trap PDU.

--
-- The following object tree is assumed for CYCLONE MIB and can be redefined.
--

CYCLONE-MIB DEFINITIONS ::= BEGIN

IMPORTS
	enterprises
		FROM RFC1155-SMI
	OBJECT-TYPE
		FROM RFC-1212
	DisplayString
		FROM RFC1213-MIB;

adaptec				OBJECT IDENTIFIER ::=  {enterprises 795}
storagemanagement		OBJECT IDENTIFIER ::=  {adaptec 2}
cyclone				OBJECT IDENTIFIER ::=  {storagemanagement 5}
cycTraps			OBJECT IDENTIFIER ::=  {cyclone 9000}

--The following are the object defined for cyclone Traps

cycManagerID		OBJECT-TYPE
	SYNTAX DisplayString    (SIZE(1..16))
	ACCESS read-only
	STATUS mandatory
	DESCRIPTION
	"ASCII String description of SCSI Manager"
::=  {cycTraps 9001}

cycHostAdapterID	OBJECT-TYPE
	SYNTAX DisplayString    (SIZE(1..16))
	ACCESS read-only
	STATUS mandatory
	DESCRIPTION
	"ASCII String description of Hostadapter"
::=  {cycTraps 9002}

cycHostAdapterNumber	OBJECT-TYPE
	SYNTAX INTEGER
	ACCESS read-only
	STATUS mandatory
	DESCRIPTION
	"The unique Hostadapter Number"
::=  {cycTraps 9003}

cycVendor		OBJECT-TYPE
	SYNTAX DisplayString    (SIZE(1..8))
	ACCESS read-only
	STATUS mandatory
	DESCRIPTION
	"This indicates the Name of the Vendor"
::=  {cycTraps 9004}

cycProduct		OBJECT-TYPE
	SYNTAX DisplayString    (SIZE(1..16))
	ACCESS read-only
	STATUS mandatory
	DESCRIPTION
	"This indicates the product information"
::=  {cycTraps 9005}

cycControllerModel	OBJECT-TYPE
	SYNTAX DisplayString    (SIZE (1..32))
	ACCESS read-only
	STATUS mandatory
	DESCRIPTION
	"The model of the associated controller e.g ATHENA, VIKING etc"
::=  {cycTraps 9006}

cycBusNumber		OBJECT-TYPE
	SYNTAX INTEGER
	ACCESS read-only
	STATUS mandatory
	DESCRIPTION
	"The PCI Bus number"
::=  {cycTraps 9007}

cycChannelNumber	OBJECT-TYPE
	SYNTAX INTEGER
	ACCESS read-only
	STATUS mandatory
	DESCRIPTION
	"Channel Number"
::=  {cycTraps 9008}

cycScsiTargetID		OBJECT-TYPE
	SYNTAX INTEGER
	ACCESS read-only
	STATUS mandatory
	DESCRIPTION
	"SCSI Target ID"
::=  {cycTraps 9009}

cycLun			OBJECT-TYPE
	SYNTAX INTEGER
	ACCESS read-only
	STATUS mandatory
	DESCRIPTION
	"The LUN of the device ID"
::=  {cycTraps 9010}

cycArrayName		OBJECT-TYPE
	SYNTAX DisplayString    (SIZE (1..32))
	ACCESS read-only
	STATUS mandatory
	DESCRIPTION
	"Array name"
::=  {cycTraps 9011}

cycMisCompares		OBJECT-TYPE
	SYNTAX INTEGER
	ACCESS read-only
	STATUS mandatory
	DESCRIPTION
	"The number of miscompares in verify "
::=  {cycTraps 9012}
			  
cycDriver		OBJECT-TYPE
	SYNTAX INTEGER
	ACCESS read-only
	STATUS mandatory
	DESCRIPTION
	"The Driver version"
::=  {cycTraps 9013}

cycManager		OBJECT-TYPE
	SYNTAX INTEGER
	ACCESS read-only
	STATUS mandatory
	DESCRIPTION
	"The CI/O Manager version"
::=  {cycTraps 9014}

cycOldArrayName		OBJECT-TYPE
	SYNTAX DisplayString    (SIZE (1..32))
	ACCESS read-only
	STATUS mandatory
	DESCRIPTION
	"Old Array name"
::=  {cycTraps 9015}

cycNewArrayName		OBJECT-TYPE
	SYNTAX DisplayString    (SIZE (1..32))
	ACCESS read-only
	STATUS mandatory
	DESCRIPTION
	"Changed Array name"
::=  {cycTraps 9016}

cycPriority		OBJECT-TYPE
	SYNTAX INTEGER
	ACCESS read-only
	STATUS mandatory
	DESCRIPTION
	"The Priority of the operation"
::=  {cycTraps 9017}

cycSenseInfo		OBJECT-TYPE
	SYNTAX INTEGER
	ACCESS read-only
	STATUS mandatory
	DESCRIPTION
	"The sense info of the PFA"
::=  {cycTraps 9018}

-- This trap is generated as soon as the SNMP agent is UP.

sCSISmart1	TRAP-TYPE
	ENTERPRISE	cyclone
	DESCRIPTION
	"SNMP Agent is up."
	--#TYPE "SNMP Agent is up."
	--#SUMMARY "SNMP Agent is up"
	--#ARGUMENTS {}
	--#SEVERITY INFORMATIONAL
	--#TIMEINDEX 100
	--#STATE OPERATIONAL
	--#HELP "scsismrt.hlp"
	--#HELPTAG 101
::=  101

-- This trap is generated as soon as the SNMP agent is Down.

sCSISmart2	TRAP-TYPE
	ENTERPRISE	cyclone
	DESCRIPTION
	"SNMP Agent is down."
	--#TYPE "SNMP Agent is down."
	--#SUMMARY "SNMP agent is down"
	--#ARGUMENTS {}
	--#SEVERITY INFORMATIONAL
	--#TIMEINDEX 100
	--#STATE OPERATIONAL
	--#HELP "scsismrt.hlp"
	--#HELPTAG 102
::=  102

-- The following are the  Traps generated by SCSI.


--This Trap is issued when ASPI database illegally contains two identical
--Hostadapter indices.

sCSISmart3	TRAP-TYPE
	ENTERPRISE	cyclone
	DESCRIPTION
	"Cyclone: duplicate hostadapter ID"
	--#TYPE "duplicate hostadapter ID"
	--#SUMMARY "duplicate hostadapter ID"
	--#ARGUMENTS {}
	--#SEVERITY WARNING
	--#TIMEINDEX 100
	--#STATE OPERATIONAL
	--#HELP "scsismrt.hlp"
	--#HELPTAG 107
::=  107

--This Trap is issued when previously unknown Host adapter if found.

sCSISmart4	TRAP-TYPE
	ENTERPRISE	cyclone
	VARIABLES {cycHostAdapterNumber, cycHostAdapterID, cycManagerID}
	DESCRIPTION
	"The HostAdapter# %d with HostAdapter Id %s and Manager Id %s is discovered"
	--#TYPE "Host Adapter Discovered"
	--#SUMMARY "The HostAdapter# %d with HostAdapter Id %s and Manager Id %s is discovered"
	--#ARGUMENTS {0,1,2}
	--#SEVERITY INFORMATIONAL
	--#TIMEINDEX 100
	--#STATE OPERATIONAL
	--#HELP "scsismrt.hlp"
	--#HELPTAG 108
::=  108 

--This Trap is issued when a Host adapter is swapped for different type one.

sCSISmart5	TRAP-TYPE
	ENTERPRISE	cyclone
	VARIABLES {cycHostAdapterNumber, cycHostAdapterID, cycManagerID}
	DESCRIPTION
	"The HostAdapter# %d has new HostAdapter Id %s and Manager Id %s"
	--#TYPE "Host Adapter changed"
	--#SUMMARY "The HostAdapter# %d has new HostAdapter Id %s and Manager Id %s"
	--#ARGUMENTS {0,1,2}
	--#SEVERITY CRITICAL
	--#TIMEINDEX 100
	--#STATE OPERATIONAL
	--#HELP "scsismrt.hlp"
	--#HELPTAG 109
::=  109

--This Trap is issued when a Host adapter fails.

sCSISmart6	TRAP-TYPE
	ENTERPRISE	cyclone
	VARIABLES {cycHostAdapterNumber}
	DESCRIPTION
	"The HostAdapter# %d has Failed"
	--#TYPE "Host adapter failed"
	--#SUMMARY "The HostAdapter# %d has Failed"
	--#ARGUMENTS {0}
	--#SEVERITY CRITICAL
	--#TIMEINDEX 100
	--#STATE OPERATIONAL
	--#HELP "scsismrt.hlp"
	--#HELPTAG 110
::=  110

--This Trap is issued when a previously failed Host adapter starts working again.

sCSISmart7	TRAP-TYPE
	ENTERPRISE	cyclone
	VARIABLES {cycHostAdapterNumber}
	DESCRIPTION
	"Host Adapter# %d recovered"
	--#TYPE "Host adapter recovered"
	--#SUMMARY"Host Adapter# %d recovered"
	--#ARGUMENTS {0}
	--#SEVERITY CRITICAL
	--#TIMEINDEX 100
	--#STATE OPERATIONAL
	--#HELP "scsismrt.hlp"
	--#HELPTAG 111
::=  111

--This Trap is issued when a previously good device fails.

sCSISmart8	TRAP-TYPE
	ENTERPRISE	cyclone
	VARIABLES {cycHostAdapterNumber, cycScsiTargetID, cycLun}
	DESCRIPTION
	"The HostAdapter# %d, TargetID %d, Lun# %d has failed"
	--#TYPE "Device failed"
	--#SUMMARY "The HostAdapter# %d , TargetID %d, Lun# %d has failed"
	--#ARGUMENTS {0,1,2}
	--#SEVERITY CRITICAL
	--#TIMEINDEX 100
	--#STATE OPERATIONAL
	--#HELP "scsismrt.hlp"
	--#HELPTAG 112
::=  112

--This Trap is issued when a previously unknown device is found.

sCSISmart9	TRAP-TYPE
	ENTERPRISE	cyclone
	VARIABLES {cycHostAdapterNumber, cycScsiTargetID, cycLun, cycVendor, cycProduct}
	DESCRIPTION
	"The HostAdapter# %d, TargetID %d, Lun# %d of vendor %s  product %s has discovered"
	--#TYPE "Device discovered"
	--#SUMMARY "The HostAdapter# %d, TargetID %d, Lun# %d of vendor %s product %s has discovered"
	--#ARGUMENTS {0,1,2,3,4}
	--#SEVERITY INFORMATIONAL
	--#TIMEINDEX 100
	--#STATE OPERATIONAL
	--#HELP "scsismrt.hlp"
	--#HELPTAG 113
::=  113

--This Trap is issued when a previously failed device starts working again.

sCSISmart10	TRAP-TYPE
	ENTERPRISE	cyclone
	VARIABLES {cycHostAdapterNumber, cycScsiTargetID, cycLun}
	DESCRIPTION
	"The HostAdapter# %d, TargetID %d,Lun# %d has recovered"
	--#TYPE "Device recovered"
	--#SUMMARY "The HostAdapter# %d, TargetID %d, Lun# %d has recovered"
	--#ARGUMENTS {0,1,2}
	--#SEVERITY CRITICAL
	--#TIMEINDEX 100
	--#STATE OPERATIONAL
	--#HELP "scsismrt.hlp"
	--#HELPTAG 114
::=  114

--This Trap is issued when a device is swapped for a different type.

sCSISmart11	TRAP-TYPE
	ENTERPRISE	cyclone
	VARIABLES {cycHostAdapterNumber, cycScsiTargetID, cycLun, cycVendor, cycProduct}
	DESCRIPTION
	"The HostAdapter# %d, TargetID %d, Lun# %d has new Vendor %s and Product %s information"
	--#TYPE "Device Changed"
	--#SUMMARY "The HostAdapter# %d, TargetID %d, Lun# %d has new Vendor %s and Product %s information"
	--#ARGUMENTS {0,1,2,3,4}
	--#SEVERITY INFORMATIONAL
	--#TIMEINDEX 100
	--#STATE OPERATIONAL
	--#HELP "scsismrt.hlp"
	--#HELPTAG 115
::=  115

--This Trap is issued when a PFA event occurs for a device.

sCSISmart12	TRAP-TYPE
	ENTERPRISE	cyclone
	VARIABLES {cycHostAdapterNumber, cycScsiTargetID, cycLun, cycVendor, cycProduct, cycSenseInfo}
	DESCRIPTION
	"The HostAdapter# %d, TargetID %d, Lun# %d has Predictive Failure Condition on vendor %s product %s with sense info MSB(sense code), next  8 bits (sense code Qual) next 8 bits (Add sense code Qual) LSB (0000) %d"
	--#TYPE "Device has SMART/Predicictive failure event"
	--#SUMMARY "The HostAdapter# %d , TargetID %d, Lun# %d has Predictive Failure Condition on vendor %s product %s with senseinfo %d"
	--#ARGUMENTS {0,1,2,3,4,5}
	--#SEVERITY INFORMATIONAL
	--#TIMEINDEX 100
	--#STATE OPERATIONAL
	--#HELP "scsismrt.hlp"
	--#HELPTAG 116
::=  116
			
--This Trap is issued when the Aspi database is cleared.

sCSISmart13	TRAP-TYPE
	ENTERPRISE	cyclone
	DESCRIPTION
	"The Aspi database is cleared and therefore all the previous information are not available"
	--#TYPE "The Aspi database is cleared"
	--#SUMMARY "The ASPI database is cleared and all the previous information are not available"
	--#ARGUMENTS {}
	--#SEVERITY INFORMATIONAL
	--#TIMEINDEX 100
	--#STATE OPERATIONAL
	--#HELP "scsismrt.hlp"
	--#HELPTAG 117
::=  117

--This Trap is issued when the Aspi crashes out, the user must restart Iomanager 
--at the server.

sCSISmart14	TRAP-TYPE
	ENTERPRISE	cyclone
	DESCRIPTION
	"The Aspi has crashed"
	--#TYPE "The Aspi has crashed"
	--#SUMMARY "The ASPI interface module has crashed"
	--#ARGUMENTS {}
	--#SEVERITY CRITICAL
	--#TIMEINDEX 100
	--#STATE OPERATIONAL
	--#HELP "scsismrt.hlp"
	--#HELPTAG 118
::=  118

--This Trap is issued when there is no memory for Aspi operation.

sCSISmart15	TRAP-TYPE
	ENTERPRISE	cyclone
	DESCRIPTION
	"No memory left for Aspi Operations"
	--#TYPE "No memory left for Aspi Operations"
	--#SUMMARY "No memory left for ASPI operation, internal software error"
	--#ARGUMENTS {}
	--#SEVERITY WARNING
	--#TIMEINDEX 100
	--#STATE OPERATIONAL
	--#HELP "scsismrt.hlp"
	--#HELPTAG 119
::=  119

--This Trap is issued when it is unable to open the aspi file for writing.

sCSISmart16	TRAP-TYPE
	ENTERPRISE	cyclone
	DESCRIPTION
	"Unable to open Aspi file for writing, problem exists in server hard disk"
	--#TYPE "Unable to open Aspi file for writing, problem exists in server hard disk"
	--#SUMMARY "Unable to open ASPI database file for writing"
	--#ARGUMENTS {}
	--#SEVERITY WARNING
	--#TIMEINDEX 100
	--#STATE OPERATIONAL
	--#HELP "scsismrt.hlp"
	--#HELPTAG 120
::=  120

--This Trap is issued when it is unable to open the aspi file.

sCSISmart17	TRAP-TYPE
	ENTERPRISE	cyclone
	DESCRIPTION
	"Unable to open Aspi file, problem exists in server hard disk"
	--#TYPE "Unable to open Aspi file"
	--#SUMMARY "Unable to open ASPI database file, problem exists in server hard disk"
	--#ARGUMENTS {}
	--#SEVERITY WARNING
	--#TIMEINDEX 100
	--#STATE OPERATIONAL
	--#HELP "scsismrt.hlp"
	--#HELPTAG 121
::=  121

--This Trap is issued when no aspi device file exists.

sCSISmart18	TRAP-TYPE
	ENTERPRISE	cyclone
	DESCRIPTION
	"Aspi device file doesnot exist"
	--#TYPE "Aspi device file doesnot exist"
	--#SUMMARY "ASPI device file does not exist"
	--#ARGUMENTS {}
	--#SEVERITY WARNING
	--#TIMEINDEX 100
	--#STATE OPERATIONAL
	--#HELP "scsismrt.hlp"
	--#HELPTAG 122
::=  122

--This Trap is issued when aspi memory allocation is failing.

sCSISmart19	TRAP-TYPE
	ENTERPRISE	cyclone
	DESCRIPTION
	"Aspi: Memory allocation is failing"
	--#TYPE "Aspi: Memory allocation is failing"
	--#SUMMARY "ASPI: memeory allocation is failing"
	--#ARGUMENTS {}
	--#SEVERITY WARNING
	--#TIMEINDEX 100
	--#STATE OPERATIONAL
	--#HELP "scsismrt.hlp"
	--#HELPTAG 123
::=  123

--This Trap is issued when it is unable to read the aspi file.

sCSISmart20	TRAP-TYPE
	ENTERPRISE	cyclone
	DESCRIPTION
	"Aspi: unable to read the file server hard disk might have problems"
	--#TYPE "Aspi: unable to read the database file"
	--#SUMMARY "ASPI: unable to read the file, server hard disk may have problems"
	--#ARGUMENTS {}
	--#SEVERITY WARNING
	--#TIMEINDEX 100
	--#STATE OPERATIONAL
	--#HELP "scsismrt.hlp"
	--#HELPTAG 124
::=  124

--This Trap is issued when aspi database is corrupted.

sCSISmart21	TRAP-TYPE
	ENTERPRISE	cyclone
	DESCRIPTION
	"Aspi: database is corrupted"
	--#TYPE "Aspi: database is corrupted"
	--#SUMMARY "ASPI: database file is corrupted"
	--#ARGUMENTS {}
	--#SEVERITY WARNING
	--#TIMEINDEX 100
	--#STATE OPERATIONAL
	--#HELP "scsismrt.hlp"
	--#HELPTAG 125
::=  125

END
