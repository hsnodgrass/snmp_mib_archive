--
-- Title: FICON MIB
-- This is in accordance with smiv2 format.
-- Intial version 1.0
--

LINK-INCIDENT-MIB DEFINITIONS ::= BEGIN
  IMPORTS
    MODULE-IDENTITY, OBJECT-TYPE,
    Integer32, OBJECT-IDENTITY, NOTIFICATION-TYPE
      FROM SNMPv2-SMI
    TEXTUAL-CONVENTION, DisplayString
      FROM SNMPv2-TC
    fcSwitch
      FROM Brocade-REG-MIB;

  linkIncidentMIB MODULE-IDENTITY
    LAST-UPDATED "0204232347Z"
    ORGANIZATION "Brocade Communications Systems, Inc.,"
    CONTACT-INFO "Customer Support Group
		  Brocade Communications Systems,
		  1745, Technology Drive,
		  San Jose, CA 95110 U.S.A
		  Tel: +1-408-392-6061
		  Fax: +1-408-392-6656
		  Email: support@Brocade.COM
		  WEB: www.brocade.com"


    DESCRIPTION	"The MIB module	defines support for FICON in Fabos. This MIB
		addresses link incident and link failure data for ficon
		host/devices connected to a Brocade switch"
	REVISION "200307110000Z"    -- July 11, 2003
    DESCRIPTION	"Initial revision"
    ::= { fcSwitch    50 }

  -- Textual conventions

 FcPortID ::= TEXTUAL-CONVENTION
    DISPLAY-HINT    "x"
    STATUS	   current
    DESCRIPTION	   "Represents Fibre Channel Address ID, a 24-bit
		    value unique within	the address space of a Fabric."
    SYNTAX	   OCTET STRING	(SIZE (3))

RLIRLinkFailureType  ::= TEXTUAL-CONVENTION
    STATUS	   current
    DESCRIPTION	   "Represents the link failure type"
    SYNTAX	   INTEGER {
			bitErrorRate(2),
			lossOfSignal(3),
			nOSRecognized(4),
			primitiveSequenceTimeout(5),
			invalidSeqForPortState(6),
			loopInitializationTimeout(7),
			lossOfSignalInLoopInit(8)
		   }

LinkWwn  ::= TEXTUAL-CONVENTION
    STATUS         current
    DESCRIPTION    "Represents the link WWN"
    SYNTAX         OCTET STRING (SIZE (8))


PortType   ::= TEXTUAL-CONVENTION
    STATUS         current
    DESCRIPTION    "Represents the Port Type"
    SYNTAX         INTEGER {
                        n-port (1),
                        nl-port (2)
                   }

LinkFormat   ::= TEXTUAL-CONVENTION
    STATUS         current
    DESCRIPTION    "Represents the frame format"
    SYNTAX         INTEGER {
                        ficon(1),
                        common(2)
                   }

RegType  ::= TEXTUAL-CONVENTION
    STATUS         current
    DESCRIPTION    "Represents the RNID Registration Type"
    SYNTAX         INTEGER {
                        conditional (1),
                        unconditional (2)
                   }

LIRRProtocol  ::= TEXTUAL-CONVENTION
    STATUS         current
    DESCRIPTION    "Represents the LIRR Protocol"
    SYNTAX         INTEGER {
                        fcp (1),
                        sb2 (2)
                   }

RNIDTagType ::= TEXTUAL-CONVENTION
    DISPLAY-HINT    "x"
    STATUS     current
    DESCRIPTION    "Represents the value of RNID Tag in Hexa Decimal format"
    SYNTAX     OCTET STRING (SIZE (2))

RNIDFlags ::= TEXTUAL-CONVENTION
    DISPLAY-HINT    "x"
    STATUS     current
    DESCRIPTION    "Represents the value of RNID Flag in Hexa Decimal format.
                    It indicates if the node is valid, not valid, or
                    not  current.  The ``Flag'' values also indi-
                    cate the following:
                         0x00      Indicates  node  ID   of   the
                                   (storage port for RNID, switch
                                   for SwitchRNID) is valid.
                         0x10      Indicates node ID of the chan-
                                   nel port is valid.
                         0x20      Indicates  the  node ID of the
                                   storage port is not current.
                         0x30      Indicates the node ID  of  the
                                   channel port is not current.
                         0x40      Indicates  the  the node ID of
                                   the (storage  port  for  RNID,
                                   switch for RLIR) is not valid.
                         0x50      Indicates the node ID  of  the
                                   channel port is not valid."
	SYNTAX		OCTET STRING (SIZE(1))

RNIDType ::= TEXTUAL-CONVENTION
    STATUS     current
    DESCRIPTION    "Represents the value of Type Number - Displays the type
                    number of the self describing node. It also describes
                    the machine type."
    SYNTAX     OCTET STRING (SIZE (6))

RNIDModel ::= TEXTUAL-CONVENTION
    STATUS     current
    DESCRIPTION    "Represents the value of Model Number."
    SYNTAX     OCTET STRING (SIZE (3))

RNIDManufacturer ::= TEXTUAL-CONVENTION
    STATUS     current
    DESCRIPTION    "Represents the Manufacturer name or code."
    SYNTAX     OCTET STRING (SIZE (3))

RNIDManufacturerPlant ::= TEXTUAL-CONVENTION
    STATUS     current
    DESCRIPTION    "The manufacture plant name or code."
    SYNTAX     OCTET STRING (SIZE (2))

RNIDSequenceNumber ::= TEXTUAL-CONVENTION
    STATUS     current
    DESCRIPTION    "Sequence number of the self describing node."
    SYNTAX     OCTET STRING (SIZE (12))

RNIDParams ::= TEXTUAL-CONVENTION
    DISPLAY-HINT    "x"
    STATUS     current
    DESCRIPTION    "Represents the value of Param.
                    It is the incident node parameters type in
                    three  bytes:  ``0xAABBCC''.   The meaning of
                    each byte is described below:

                    Byte AA:
                         0x00      Reserved
                         0x20      FC-SB-2 and updates.
                         0x40      Other FC-4s including FCP  and
                                   updates.
                         0x60      FC-SB-2  and updates and other
                                   FC-4s   including   FCP    and
                                   updates.
                         0x80      FC-4 support not specified.
                         0xa0      Reserved.
                         0xc0      Reserved.
                         0xe0      Vendor specific.

                    Byte BB:
                         0x00      Unspecified class
                         0x01      Direct  access storage device,
                                   if  it  is  an  storage  port.
                                   Otherwise,  it  is not channel
                                   to channel capable.
                         0x02      Magnetic tape,  if  it  is  an
                                   storage port. Otherwise, if it
                                   is  a  reserved  field  for  a
                                   channel port.
                         0x03      Input unit record, if it is an
                                   storage port. Otherwise, it is
                                   a reserved field for a channel
                                   port.
                         0x04      Output unit, if it is an stor-
                                   age  port.  Otherwise, it is a
                                   reserved field for  a  channel
                                   port.
                         0x05      Printer,  if  it is an storage
                                   port.   Otherwise,  it  is   a
                                   reserved  field  for a channel
                                   port.
                         0x06      Controler, if it is an storage
                                   port.   Otherwise,   it  is  a
                                   reserved field for  a  channel
                                   port.
                         0x07      Terminal  -  Full screen if it
                                   is an storage port. Otherwise,
                                   it  is  a reserved field for a
                                   channel port.

                         0x08      Terminal - Line mode if it  is
                                   an  storage  port.  Otherwise,
                                   it is an emulated control unit
                                   support only.
                         0x09      Reserved.
                         0x10      Switch,  if  it  is  a  switch
                                   device.   Otherwise,   it   is
                                   reserved.
                         0x0b 0xff Reserved.

                    Byte CC:
                         0x00      If  storage CU port has regis-
                                   tered with the switch.
                         0xID      CHIPID  if  channel  port  has
                                   registered with the switch.
                         0xPN      If  switch has registered with
                                   the channel then PN  represent
                                   the FL port number."
    SYNTAX     OCTET STRING (SIZE (3))

-- { linkIncidentMIB 1 } is reserved for future usage.

  ficonRNID  OBJECT-IDENTITY
     STATUS  current
     DESCRIPTION   "The OID sub-tree for ficonRNID. This group contains all
                     RNID group objects for FICON."
     ::= { linkIncidentMIB 2 }

  nodeRNIDTableNumEntries OBJECT-TYPE
      SYNTAX	  Integer32
      MAX-ACCESS  read-only
      STATUS	  current
      DESCRIPTION
	"The number of entries in Request Node Identification Data (RNID) table."
  ::= {	ficonRNID 1 }

 -- node RNID table
 -- Node information from attached node to the switch are stored
 -- in the node RNID table

nodeRNIDTable  OBJECT-TYPE
     SYNTAX	 SEQUENCE OF NodeRNIDEntry
     MAX-ACCESS	 not-accessible
     STATUS	 current
     DESCRIPTION
	"A table that contains, one entry for each Ficon RNID
	node attached to a switch."
 ::= { ficonRNID 2 }

nodeRNIDEntry	OBJECT-TYPE
	SYNTAX		NodeRNIDEntry
	MAX-ACCESS		not-accessible
	STATUS		current
	DESCRIPTION	"A entry containing the RNID information
			 for a ficon node"
	INDEX		{ nodeRNIDIndex }
  ::= {  nodeRNIDTable 1 }

NodeRNIDEntry	::= SEQUENCE {
	nodeRNIDIndex
		Integer32,
	nodeRNIDIncidentPortWWN
		LinkWwn,
	nodeRNIDPID
		FcPortID,
	nodeRNIDFlags
		RNIDFlags,
	nodeRNIDType
		RNIDType,
	nodeRNIDModel
		RNIDModel,
	nodeRNIDManufacturer
		RNIDManufacturer,
	nodeRNIDManufacturerPlant
		RNIDManufacturerPlant,
	nodeRNIDSequenceNumber
		RNIDSequenceNumber,
	nodeRNIDConnectedPortWWN
		LinkWwn,
	nodeRNIDPortType
		PortType,
	nodeRNIDFormat
		LinkFormat,
	nodeRNIDTag
		RNIDTagType,
	nodeRNIDParams
		RNIDParams
  }

nodeRNIDIndex	OBJECT-TYPE
	SYNTAX	  Integer32
      MAX-ACCESS  read-only
      STATUS	  current
      DESCRIPTION
	 "Index into nodeRNIDTable"
  ::= {   nodeRNIDEntry 1 }

nodeRNIDIncidentPortWWN	OBJECT-TYPE
	SYNTAX		LinkWwn
	MAX-ACCESS	read-only
	STATUS		current
	DESCRIPTION	"Port WWN for Incident port. An N-port (ficon device
			or host) is an incident port"
  ::= {   nodeRNIDEntry 2 }

nodeRNIDPID	OBJECT-TYPE
	SYNTAX		FcPortID
	MAX-ACCESS	read-only
	STATUS		current
	DESCRIPTION	"PID for an Incident port."
  ::= {   nodeRNIDEntry 3 }

nodeRNIDFlags	OBJECT-TYPE
	SYNTAX		RNIDFlags
	MAX-ACCESS	read-only
	STATUS		current
	DESCRIPTION	"RNID flags for an Incident port."
  ::= {   nodeRNIDEntry 4 }

nodeRNIDType	OBJECT-TYPE
	SYNTAX		RNIDType
	MAX-ACCESS	read-only
	STATUS		current
	DESCRIPTION	"Number associate with a node"
  ::= {   nodeRNIDEntry 5 }

nodeRNIDModel	OBJECT-TYPE
	SYNTAX		RNIDModel
	MAX-ACCESS	read-only
	STATUS		current
	DESCRIPTION	"Model number of the RNID node"
  ::= {   nodeRNIDEntry 6 }

nodeRNIDManufacturer	OBJECT-TYPE
	SYNTAX		RNIDManufacturer
	MAX-ACCESS	read-only
	STATUS		current
	DESCRIPTION	"Identifies the manufaturer of the node."
  ::= {   nodeRNIDEntry 7 }

nodeRNIDManufacturerPlant	OBJECT-TYPE
	SYNTAX		RNIDManufacturerPlant
	MAX-ACCESS	read-only
	STATUS		current
	DESCRIPTION	"Identifies the manufacturer plant of the node."
  ::= {   nodeRNIDEntry 8 }

nodeRNIDSequenceNumber	OBJECT-TYPE
	SYNTAX		RNIDSequenceNumber
	MAX-ACCESS	read-only
	STATUS		current
	DESCRIPTION	"Identifies the sequence number of the node."
  ::= {   nodeRNIDEntry 9 }

nodeRNIDConnectedPortWWN	OBJECT-TYPE
	SYNTAX		LinkWwn
	MAX-ACCESS	read-only
	STATUS		current
	DESCRIPTION	"WWN of the connected port."
  ::= {   nodeRNIDEntry 10 }

nodeRNIDPortType		OBJECT-TYPE
	SYNTAX		PortType
	MAX-ACCESS	read-only
	STATUS		current
	DESCRIPTION	"Port type (N, NL or virtual port) of the connected port."
  ::= {   nodeRNIDEntry 11 }

nodeRNIDFormat			OBJECT-TYPE
	SYNTAX			LinkFormat
	MAX-ACCESS		read-only
	STATUS		current
	DESCRIPTION	"Node identification data format of the connected port."
  ::= {   nodeRNIDEntry 12 }

nodeRNIDTag			OBJECT-TYPE
	SYNTAX			RNIDTagType
	MAX-ACCESS		read-only
	STATUS		current
	DESCRIPTION	"Node identification tag of the connected port."
  ::= {   nodeRNIDEntry 13 }

nodeRNIDParams			OBJECT-TYPE
	SYNTAX			RNIDParams
	MAX-ACCESS		read-only
	STATUS		current
	DESCRIPTION	"Node parameters of the connected port."
  ::= {   nodeRNIDEntry 14 }

switchRNIDTableNumEntries  OBJECT-TYPE
      SYNTAX	  Integer32
      MAX-ACCESS  read-only
      STATUS	  current
      DESCRIPTION
	 "The number of entries in RNID table which corresponds to switch."
  ::= {	ficonRNID 3 }

 -- switchRNIDTable - This table contains the RNID info. for the
 -- switch node. Normally, there will be only one entry in the table.

switchRNIDTable   OBJECT-TYPE
     SYNTAX	 SEQUENCE OF SwitchRNIDEntry
     MAX-ACCESS	 not-accessible
     STATUS	 current
     DESCRIPTION
	"A table that contains, one entry for each switch ficon node."
 ::= { ficonRNID 4 }

switchRNIDEntry	OBJECT-TYPE
	SYNTAX		SwitchRNIDEntry
	MAX-ACCESS		not-accessible
	STATUS		current
	DESCRIPTION	""
	INDEX		{ switchRNIDIndex }
  ::= {  switchRNIDTable 1 }

SwitchRNIDEntry	::= SEQUENCE {
	switchRNIDIndex		Integer32,
	switchRNIDSwitchWWN
       	LinkWwn,
	switchRNIDFlags
		RNIDFlags,
	switchRNIDType
		RNIDType,
	switchRNIDModel
		RNIDModel,
	switchRNIDManufacturer
		RNIDManufacturer,
	switchRNIDManufacturerPlant
		RNIDManufacturerPlant,
	switchRNIDSequenceNumber
		RNIDSequenceNumber,
	switchRNIDTag
		RNIDTagType,
	switchRNIDParams
		RNIDParams
  }

switchRNIDIndex	OBJECT-TYPE
	SYNTAX		Integer32
	MAX-ACCESS	read-only
	STATUS		current
	DESCRIPTION	"Index into switchRNIDTable."
  ::= {   switchRNIDEntry 1 }

switchRNIDSwitchWWN	OBJECT-TYPE
	SYNTAX		LinkWwn
	MAX-ACCESS	read-only
	STATUS		current
	DESCRIPTION	"WWN of the switch."
  ::= {   switchRNIDEntry 2 }

switchRNIDFlags	OBJECT-TYPE
	SYNTAX		RNIDFlags
	MAX-ACCESS	read-only
	STATUS		current
	DESCRIPTION	"RNID flags for switch."
  ::= {   switchRNIDEntry 3 }

switchRNIDType	OBJECT-TYPE
	SYNTAX		RNIDType
	MAX-ACCESS	read-only
	STATUS		current
	DESCRIPTION	"Type Number associate with a switch."
  ::= {   switchRNIDEntry 4 }

switchRNIDModel	OBJECT-TYPE
	SYNTAX		RNIDModel
	MAX-ACCESS	read-only
	STATUS		current
	DESCRIPTION	"Model number of the RNID switch."
  ::= {   switchRNIDEntry 5 }

switchRNIDManufacturer	OBJECT-TYPE
	SYNTAX		RNIDManufacturer
	MAX-ACCESS	read-only
	STATUS		current
	DESCRIPTION	"Identifies the manufaturer of the switch."
  ::= {   switchRNIDEntry 6 }

switchRNIDManufacturerPlant	OBJECT-TYPE
	SYNTAX		RNIDManufacturerPlant
	MAX-ACCESS	read-only
	STATUS		current
	DESCRIPTION	"Identifies the manufacturer plant of the switch."
  ::= {   switchRNIDEntry 7 }

switchRNIDSequenceNumber	OBJECT-TYPE
	SYNTAX		RNIDSequenceNumber
	MAX-ACCESS	read-only
	STATUS		current
	DESCRIPTION	"Identifies the sequence number of the switch."
  ::= {   switchRNIDEntry 8 }

switchRNIDTag			OBJECT-TYPE
	SYNTAX			RNIDTagType
	MAX-ACCESS		read-only
	STATUS		current
	DESCRIPTION	"Identification tag of the switch."
  ::= {   switchRNIDEntry 9 }

switchRNIDParams			OBJECT-TYPE
	SYNTAX			RNIDParams
	MAX-ACCESS		read-only
	STATUS		current
	DESCRIPTION	"Parameters of the switch."
  ::= {   switchRNIDEntry 10 }

 -- LIRRTable - This group contains LIRR info for each listener port.
  ficonLIRR  OBJECT-IDENTITY
     STATUS  current
     DESCRIPTION   "The OID sub-tree for ficonLIRR. This group contains all
                     LIRR group objects for FICON."
     ::= { linkIncidentMIB 3 }

lIRRTableNumEntries   OBJECT-TYPE
      SYNTAX	  Integer32
      MAX-ACCESS  read-only
      STATUS	  current
      DESCRIPTION
	 "The number of entries in Link Incident Record
	  Registration (LIRR) table"
 ::= {	ficonLIRR 1 }


lIRRTable	OBJECT-TYPE
     SYNTAX	 SEQUENCE OF LIRREntry
     MAX-ACCESS	 not-accessible
     STATUS	 current
     DESCRIPTION
	"A table that contains, one entry for each LIRR incident
	for an attached FICON device."
 ::= { ficonLIRR 2 }

lIRREntry	OBJECT-TYPE
	SYNTAX		LIRREntry
	MAX-ACCESS		not-accessible
	STATUS		current
	DESCRIPTION	"An entry containing LIRR information."
	INDEX		{ lIRRIndex }
  ::= {  lIRRTable 1 }

LIRREntry	::= SEQUENCE {
	lIRRIndex
		Integer32,
	lIRRListenerPortWWN
		LinkWwn,
	lIRRListenerPID
		FcPortID,
	lIRRRegType
		RegType,
	lIRRProtocol
		LIRRProtocol,
	lIRRPortType
		PortType,
	lIRRFormat
		LinkFormat
}

lIRRIndex	OBJECT-TYPE
	SYNTAX		Integer32
	MAX-ACCESS	read-only
	STATUS		current
	DESCRIPTION	"Index into the LIRR table."
  ::= {   lIRREntry 1 }

lIRRListenerPortWWN   OBJECT-TYPE
	SYNTAX		LinkWwn
	MAX-ACCESS	read-only
	STATUS		current
	DESCRIPTION	"WWN of the Listener port."
  ::= {   lIRREntry 2 }

lIRRListenerPID	OBJECT-TYPE
	SYNTAX		FcPortID
	MAX-ACCESS	read-only
	STATUS		current
	DESCRIPTION	"PID for the listener port."
  ::= {   lIRREntry 3 }

lIRRRegType	OBJECT-TYPE
	SYNTAX		RegType
	MAX-ACCESS	read-only
	STATUS		current
	DESCRIPTION	"Registration type - conditional or unconditional."
  ::= {   lIRREntry 4 }

lIRRProtocol	OBJECT-TYPE
	SYNTAX		LIRRProtocol
	MAX-ACCESS	read-only
	STATUS		current
	DESCRIPTION	"Protocol type supported."
  ::= {   lIRREntry 5 }

lIRRPortType	OBJECT-TYPE
	SYNTAX		PortType
	MAX-ACCESS	read-only
	STATUS		current
	DESCRIPTION	"Attached port type."
  ::= {   lIRREntry 6 }

lIRRFormat	OBJECT-TYPE
	SYNTAX		LinkFormat
	MAX-ACCESS	read-only
	STATUS		current
	DESCRIPTION	"Registration type - conditional or unconditional."
  ::= {   lIRREntry 7 }

-- RLIR group - This group contains RLIR info. for each link incident"
  ficonRLIR  OBJECT-IDENTITY
     STATUS  current
     DESCRIPTION   "The OID sub-tree for ficonRLIR. This group contains all
                     RLIR group objects for FICON."
     ::= { linkIncidentMIB 4 }

rLIRTableNumEntries   OBJECT-TYPE
      SYNTAX	  Integer32
      MAX-ACCESS  read-only
      STATUS	  current
      DESCRIPTION
	 "The number of entries in switch Registered Link
   	  Incident Report (RLIR) table"
 ::= {	ficonRLIR 1 }


rLIRTable	OBJECT-TYPE
     SYNTAX	 SEQUENCE OF RLIREntry
     MAX-ACCESS	 not-accessible
     STATUS	 current
     DESCRIPTION
	"A table that contains, one entry for each LIRR incident
	for an attached FICON device."
 ::= { ficonRLIR  2 }

rLIREntry	OBJECT-TYPE
	SYNTAX		RLIREntry
	MAX-ACCESS		not-accessible
	STATUS		current
	DESCRIPTION	"An entry containing RLIR information."
	INDEX		{ rLIRIndex }
  ::= {  rLIRTable 1 }

RLIREntry	::= SEQUENCE {
	rLIRIndex		Integer32,
	rLIRIncidentPortWwn	LinkWwn,
	rLIRIncidentNodeWwn	LinkWwn,
	rLIRIncidentPortType	PortType,
	rLIRIncidentPID		FcPortID,
	rLIRIncidentPortNumber	Integer32,
	rLIRConnectedPortWwn	LinkWwn,
	rLIRConnectedNodeWwn	LinkWwn,
	rLIRFabricWwn		LinkWwn,
	rLIRLinkFailureType	RLIRLinkFailureType,
	--rLIRTimeStamp		DisplayString(SIZE (0..64)),
	rLIRTimeStamp		DisplayString(SIZE(64)),
	rLIRFormat		LinkFormat
}

rLIRIndex	OBJECT-TYPE
	SYNTAX		Integer32
	MAX-ACCESS	read-only
	STATUS		current
	DESCRIPTION	"Index into RLIR table."
  ::= {   rLIREntry 1 }

rLIRIncidentPortWwn	OBJECT-TYPE
	SYNTAX		LinkWwn
	MAX-ACCESS	read-only
	STATUS		current
	DESCRIPTION	"Port WWN for RLIR Incident port."
  ::= {   rLIREntry 2 }

rLIRIncidentNodeWwn	OBJECT-TYPE
	SYNTAX		LinkWwn
	MAX-ACCESS	read-only
	STATUS		current
	DESCRIPTION	"Incident node WWN."
  ::= {   rLIREntry 3 }

rLIRIncidentPortType	OBJECT-TYPE
	SYNTAX		PortType
	MAX-ACCESS	read-only
	STATUS		current
	DESCRIPTION	"RLIR Incident port type."
  ::= {   rLIREntry 5 }

rLIRIncidentPID	OBJECT-TYPE
	SYNTAX		FcPortID
	MAX-ACCESS	read-only
	STATUS		current
	DESCRIPTION	"RLIR Incident PID."
  ::= {   rLIREntry 6 }

rLIRIncidentPortNumber	OBJECT-TYPE
	SYNTAX		Integer32
	MAX-ACCESS	read-only
	STATUS		current
	DESCRIPTION	"RLIR Incident port number.This is vendor specific
			port number."
  ::= {   rLIREntry 7 }

rLIRConnectedPortWwn	OBJECT-TYPE
	SYNTAX		LinkWwn
	MAX-ACCESS	read-only
	STATUS		current
	DESCRIPTION	"RLIR Connected port WWN."
  ::= {   rLIREntry 8 }

rLIRConnectedNodeWwn	OBJECT-TYPE
	SYNTAX		LinkWwn
	MAX-ACCESS	read-only
	STATUS		current
	DESCRIPTION	"RLIR Connected node WWN."
  ::= {   rLIREntry 9 }

rLIRFabricWwn	OBJECT-TYPE
	SYNTAX		LinkWwn
	MAX-ACCESS	read-only
	STATUS		current
	DESCRIPTION	"RLIR Fabric Wwn."
  ::= {   rLIREntry 10 }

rLIRLinkFailureType  OBJECT-TYPE
	SYNTAX		RLIRLinkFailureType
	MAX-ACCESS	read-only
	STATUS		current
	DESCRIPTION	"RLIR Link failure type."
  ::= {   rLIREntry 11 }

rLIRTimeStamp	OBJECT-TYPE
	SYNTAX		DisplayString(SIZE (0..64))
	MAX-ACCESS	read-only
	STATUS		current
	DESCRIPTION	"RLIR time stamp."
  ::= {   rLIREntry 12 }

rLIRFormat	OBJECT-TYPE
	SYNTAX		LinkFormat
	MAX-ACCESS	read-only
	STATUS		current
	DESCRIPTION	"RLIR Format."
  ::= {   rLIREntry 13 }

-- { linkIncidentMIB 5..20 } are reserved for new mib objects in future.

-- Related traps

	linkIncidentMIBTraps      OBJECT-IDENTITY
      STATUS     current
      DESCRIPTION "The OID sub-tree for Link Incident trap."
    ::= { linkIncidentMIB 21 }

    linkIncidentMIBTrapPrefix OBJECT-IDENTITY
      STATUS     current
      DESCRIPTION "The Link Incident traps."
    ::= { linkIncidentMIBTraps 0 }

   linkRNIDDeviceRegistration NOTIFICATION-TYPE
        OBJECTS { nodeRNIDIndex, nodeRNIDIncidentPortWWN, nodeRNIDConnectedPortWWN }
	STATUS  current
        DESCRIPTION
            " A device registered with the switch"
        ::= {linkIncidentMIBTrapPrefix 1}

    linkRNIDDeviceDeRegistration NOTIFICATION-TYPE
        OBJECTS { nodeRNIDIndex, nodeRNIDIncidentPortWWN, nodeRNIDConnectedPortWWN }
        STATUS  current
	DESCRIPTION
            " A device de-regsitered with the switch"
        ::= {linkIncidentMIBTrapPrefix 2}

    linkLIRRListenerAdded   NOTIFICATION-TYPE
        OBJECTS {lIRRListenerPortWWN, lIRRListenerPID, lIRRIndex}
	STATUS  current
        DESCRIPTION
            " A listener for link failure incident is added"
        ::= {linkIncidentMIBTrapPrefix 3}

     linkLIRRListenerRemoved NOTIFICATION-TYPE
        OBJECTS {lIRRListenerPortWWN, lIRRListenerPID, lIRRIndex}
        STATUS  current
        DESCRIPTION
            " A listener for link failure incident is removed"
        ::= {linkIncidentMIBTrapPrefix 4}

    linkRLIRFailureIncident  NOTIFICATION-TYPE
        OBJECTS { nodeRNIDIndex, lIRRIndex, rLIRIncidentPortWwn,
		rLIRConnectedPortWwn,
		rLIRIndex, rLIRLinkFailureType, lIRRListenerPID }
	STATUS  current
        DESCRIPTION
            " A link failure incident has occured. The value of
              lIRRIndex will be -2147483647 and lIRRListenerPID will
              be 0 (zero) , if there is no listener for incident."
        ::= {linkIncidentMIBTrapPrefix 5}

END
  -- End of Object Definitions
