NEWEXPOSE-MIB DEFINITIONS ::= BEGIN

IMPORTS
    mgmt, NetworkAddress, IpAddress, Gauge, Counter,
    TimeTicks, enterprises
        FROM RFC1155-SMI
    OBJECT-TYPE, TRAP-TYPE
        FROM RFC-1212;


fasttrack OBJECT IDENTIFIER ::= { enterprises 944 }

expose OBJECT IDENTIFIER ::= { fasttrack 1 }

winnt OBJECT IDENTIFIER ::= { fasttrack 2 }

performance OBJECT IDENTIFIER ::= { winnt 1 }

memory OBJECT IDENTIFIER ::= { performance 10 }

sysinfo OBJECT IDENTIFIER ::= { winnt 2 }

agtInfo OBJECT IDENTIFIER ::= { sysinfo 6 }

osInfo OBJECT IDENTIFIER ::= { sysinfo 5 }

serverInfo OBJECT IDENTIFIER ::= { sysinfo 4 }



memoryAvailableBytes OBJECT-TYPE
    SYNTAX Counter
    ACCESS read-only
    STATUS mandatory
    DESCRIPTION
       "Available Bytes displays the size of the virtual memory currently on the 
        Zeroed, Free, and Standby lists. Zeroed and Free memory is ready for use, 
        with Zeroed memory cleared to zeros. Standby memory is memory removed from a 
        process's Working Set but still available. Notice that this is an 
        instantaneous count, not an average over the time interval."
    ::= { memory 1 }


memoryCommitLimit OBJECT-TYPE
    SYNTAX Counter
    ACCESS read-only
    STATUS mandatory
    DESCRIPTION
       "Commit Limit is the size (in bytes) of virtual memory that can be committed 
        without having to extend the paging file(s). If the paging file(s) can be 
        extended, this is a soft limit."
    ::= { memory 5 }

memoryCommittedBytes OBJECT-TYPE
    SYNTAX Counter
    ACCESS read-only
    STATUS mandatory
    DESCRIPTION
       "Committed Bytes displays the size of virtual memory (in bytes) that has been 
        Committed (as opposed to simply reserved). Committed memory must have 
        backing (i.e., disk) storage available, or must be assured never to need 
        disk storage (because main memory is large enough to hold it.) Notice that 
        this is an instantaneous count, not an average over the time interval."
    ::= { memory 6 }


osProcUtil1 OBJECT-TYPE
    SYNTAX Gauge
    ACCESS read-only
    STATUS mandatory
    DESCRIPTION
       "System Utilization over the last minute."
    ::= { osInfo 1 }



svrInfoTotalPhysicalRam OBJECT-TYPE
    SYNTAX Counter
    ACCESS read-only
    STATUS mandatory
    DESCRIPTION
       "The amount of physical RAM in bytes."
    ::= { serverInfo 6 }



agtMajRev OBJECT-TYPE
    SYNTAX INTEGER
    ACCESS read-only
    STATUS mandatory
    DESCRIPTION
       "Agent Major Revision"
    ::= { agtInfo 1 }


END
