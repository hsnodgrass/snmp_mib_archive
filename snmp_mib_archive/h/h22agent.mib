--  Digital Equipment Corporation SWCC Agent Private MIB 
--
--  MIB for release 2.0 of StorageWorks Command Console Daemon Agent.
--  
--  Copyright (c) 1996,1997,1998 Digital Equipment Corporation.  All Rights Reserved.
--  Reproduction of this document is authorized on condition that the 
--  foregoing notice is included.
--
--  This SNMP MIB Specification contains Digital SWCC's confidential
--  and proprietary intellectual property.  Digital retains all title and 
--  ownership in the Specification, including any revisions.
--
--  It is Digital's intent to encourage the widespread use of this
--  Specification in connection with the management of storage subsystems
--  using the Command Console or Enterprise Storage Manager Graphical User Interface or 
--  other SNMP management utilities.  Digital grants vendors, end-users,
--  and other interested parties a non-exclusive license to use this 
--  Specification in connection with the management of Digital StorageWorks
--  RAID Controller products.
--   
--  This Specification is supplied AS IS, and Digital makes no warranty,
--  either expressed or implied, as to the use, operation, condition, or
--  performance of the Specification.
--
--
--     StorageWorks Enterprise Array Manager (STEAM) Management Information Base (MIB)
--
--  iso(1) org(3) dod(6) internet(1) private(4) enterprises(1) dec(36)
--  ema(2) sysobjids(15)


	 RAIDMANAGER2-MIB DEFINITIONS ::= BEGIN

	 IMPORTS
		 enterprises
			 FROM RFC1155-SMI
		 OBJECT-TYPE
			 FROM RFC-1212
		 DisplayString
			 FROM RFC-1213;

	dec              OBJECT IDENTIFIER ::= { enterprises 36 }
	ema              OBJECT IDENTIFIER ::= { dec 2 }
	sysobjids        OBJECT IDENTIFIER ::= { ema 15 }

-- raidmanager MIB
	agent            OBJECT IDENTIFIER ::= { sysobjids 1 }
	workstation      OBJECT IDENTIFIER ::= { sysobjids 2 }
	subsys           OBJECT IDENTIFIER ::= { sysobjids 3 }

--      Agent Information Group

	agManufacturer OBJECT-TYPE
	     SYNTAX  DisplayString
	     ACCESS  read-only
	     STATUS  mandatory
	     DESCRIPTION
		     "The name of the Enterprise Storage Manager Agent manufacturer."
		      
	     ::= { agent 1 }
	
	agMajVersion OBJECT-TYPE
	     SYNTAX  INTEGER
	     ACCESS  read-only
	     STATUS  mandatory
	     DESCRIPTION
		     "Enterprise Storage Manager Agent Major Version Number (e.g., 3 
		     for 3.0)."
		      
	     ::= { agent 2 }

	agMinVersion OBJECT-TYPE
	     SYNTAX  INTEGER
	     ACCESS  read-only
	     STATUS  mandatory
	     DESCRIPTION
		     "Enterprise Storage Manager Agent Minor Version Number (e.g., 0 
		     for 3.0)."
		      
	     ::= { agent 3 }

	agHostName OBJECT-TYPE
	     SYNTAX  DisplayString
	     ACCESS  read-only
	     STATUS  mandatory
	     DESCRIPTION
		     "The Host System Network Name where the agent resides."
		      
	     ::= { agent 4 }


	agEnterprise OBJECT-TYPE
	     SYNTAX  OBJECT IDENTIFIER
	     ACCESS  read-only
	     STATUS  mandatory
	     DESCRIPTION
		     "The Enterprise ID subtree for Enterprise Storage Manager Agent MIB 
		      is registered."
		      
	     ::= { agent 5 }

	agDescription OBJECT-TYPE
	     SYNTAX  DisplayString
	     ACCESS  read-only
	     STATUS  mandatory
	     DESCRIPTION
		     "The Enterprise Array Storage Agent description."
		      
	     ::= { agent 6 }

	
-- Workstation Group

	wsCPU OBJECT-TYPE
	     SYNTAX  DisplayString
	     ACCESS  read-only
	     STATUS  mandatory
	     DESCRIPTION
		     "The workstation CPU type (e.g., 80486)."
		      
	     ::= { workstation 1 }

	wsComputerType OBJECT-TYPE
	     SYNTAX  DisplayString
	     ACCESS  read-only
	     STATUS  mandatory
	     DESCRIPTION
		     "The workstation Computer type (e.g., PC/AT)."
		      
	     ::= { workstation 2 }

	wsModel OBJECT-TYPE
	     SYNTAX  INTEGER
	     ACCESS  read-only
	     STATUS  mandatory
	     DESCRIPTION
		     "The workstation model number."
		      
	     ::= { workstation 3 }

	wsSubModel OBJECT-TYPE
	     SYNTAX  INTEGER
	     ACCESS  read-only
	     STATUS  mandatory
	     DESCRIPTION
		     "The workstation submodel number."
		      
	     ::= { workstation 4 }

	wsBiosVersion OBJECT-TYPE
	     SYNTAX  DisplayString
	     ACCESS  read-only
	     STATUS  mandatory
	     DESCRIPTION
		     "The workstation BIOS Version."
		      
	     ::= { workstation 5 }

	wsOS OBJECT-TYPE
	     SYNTAX  DisplayString
	     ACCESS  read-only
	     STATUS  mandatory
	     DESCRIPTION
		     "The workstation operating system name (e.g., WINNT)."
		      
	     ::= { workstation 6 }

	wsOSMajVersion OBJECT-TYPE
	     SYNTAX  INTEGER
	     ACCESS  read-only
	     STATUS  mandatory
	     DESCRIPTION
		     "The workstation OS major version number 
		     (e.g., 3 for WINNT 3.51)."
		      
	     ::= { workstation 7 }

	wsOSMinVersion OBJECT-TYPE
	     SYNTAX  INTEGER
	     ACCESS  read-only
	     STATUS  mandatory
	     DESCRIPTION
		     "The workstation OS minor version number (e.g., 51 for
		     WINNT 3.51)."
		      
	     ::= { workstation 8 }


-- Subsystem Group

	ssTotalSubSystems OBJECT-TYPE
	     SYNTAX  INTEGER 
	     ACCESS  read-only
	     STATUS  mandatory
	     DESCRIPTION
		     "The total number of subsystems presently serviced
		      by this agent."
		      
	     ::= { subsys 1 }


-- Subsystem Status Group

	ssStatusTable OBJECT-TYPE                                  
	     SYNTAX  SEQUENCE OF SsEntry
	     ACCESS  not-accessible
	     STATUS  mandatory
	     DESCRIPTION
		     "This table holds the status information for
		      each subsystem."
		      
	     ::= { subsys 2 }

	ssEntry OBJECT-TYPE
	     SYNTAX  SsEntry
	     ACCESS  not-accessible
	     STATUS  mandatory
	     DESCRIPTION
	     "The subsystem information entry."
	     INDEX   { ssEntryIndex }
		      
	     ::= { ssStatusTable 1 }

	SsEntry ::=                                              
	  SEQUENCE{
		ssEntryIndex
			INTEGER,
		ssSubsysName           
			DisplayString,
		ssOverallStatus         
			INTEGER,
		ssDiskStatus            
			INTEGER,
		ssPowerStatus           
			INTEGER,
		ssFanStatus             
			INTEGER,
		ssCacheBatteryStatus    
			INTEGER,
		ssTemperatureStatus     
			INTEGER,
		ssCommStatus            
			INTEGER,
		ssEmuExtInputStatus     
			INTEGER,
		ssEmuPresent            
			INTEGER,
		ssController1Status     
			INTEGER,
		ssController1SerNum     
			DisplayString,
		ssController1RDAC       
			INTEGER,
		ssController1Type       
			DisplayString,
		ssController1ProdID       
			DisplayString,
		ssController1FwRev       
			DisplayString,
		ssController1HwRev       
			DisplayString,
		ssController2Status     
			INTEGER,
		ssController2SerNum     
			DisplayString,
		ssController2RDAC       
			INTEGER,
		ssController2Type       
			DisplayString,
		ssController2ProdID       
			DisplayString,
		ssController2FwRev       
			DisplayString,
		ssController2HwRev       
			DisplayString,
		ssUpsStatus       
			INTEGER,
		ssLunStatus       
			INTEGER
	  }

	ssEntryIndex OBJECT-TYPE
	     SYNTAX  INTEGER
	     ACCESS  read-only
	     STATUS  mandatory
	     DESCRIPTION
		     "The index into ssStatusTable ."
		      
	     ::= { ssEntry 1 }

	ssSubsysName OBJECT-TYPE
	     SYNTAX  DisplayString
	     ACCESS  read-only
	     STATUS  mandatory
	     DESCRIPTION
		     "The local Subsystem Name."
		      
	     ::= { ssEntry 2 }

	ssOverallStatus OBJECT-TYPE
             SYNTAX  INTEGER  {
                          GREEN(0),
                          YELLOW(1),
                          RED(2)
                      }
 	     ACCESS  read-only
	     STATUS  mandatory
	     DESCRIPTION
		      "This variable reports the overall status of the
		       storage subsystem. 
		       GREEN: Normal Operating Condition
		       YELLOW: Warning Condition
		       RED: Subsystem Communication Failure; No response to Agent requests."
					      
	     ::= { ssEntry 3 }

	ssDiskStatus OBJECT-TYPE
             SYNTAX  INTEGER  {
                          ALL_OK(0),
                          AT_LEAST_1_FAILURE(1)
                     }
 	     ACCESS  read-only
	     STATUS  mandatory
	     DESCRIPTION
		     "This variable reports the overall status for the
		      physical devices in the subsystem." 

	     ::= { ssEntry 4 }

	ssPowerStatus OBJECT-TYPE
            SYNTAX  INTEGER  {
                          ALL_OK(0),
                          AT_LEAST_1_FAILURE(1)
                      }
 	     ACCESS  read-only
	     STATUS  mandatory
	     DESCRIPTION
		     "This variable reports the status for the
		      Power Supply system in the subsystem." 

	     ::= { ssEntry 5 }

	ssFanStatus OBJECT-TYPE
            SYNTAX  INTEGER  {
                          ALL_OK(0),
                          AT_LEAST_1_FAILURE(1)
                      }
	     ACCESS  read-only
	     STATUS  mandatory
	     DESCRIPTION
		     "This variable reports the status for the
		      FAN system in the subsystem." 

	     ::= { ssEntry 6 }


	ssCacheBatteryStatus OBJECT-TYPE
            SYNTAX  INTEGER  {
                          NORMAL_CHARGE(0),
                          LOW_CHARGE(1)
                      }
	     ACCESS  read-only
	     STATUS  mandatory
	     DESCRIPTION
		     "This variable reports the status for the
		      Cache Battery in the subsystem. This status object is currently
		      non-functional but in place for future use."

	     ::= { ssEntry 7 }

	ssTemperatureStatus OBJECT-TYPE
            SYNTAX  INTEGER  {
                          NORMAL(0),
                          OVER_TEMP_CONDITION(1)
                      }
	     ACCESS  read-only
	     STATUS  mandatory
	     DESCRIPTION
		     "This variable reports the status for the
		      Temperature in the subsystem." 

	     ::= { ssEntry 8 }

	ssCommStatus OBJECT-TYPE
            SYNTAX  INTEGER  {
                          NORMAL(0),
                          COMMUNICATION_FAILURE(1)
                      }
	     ACCESS  read-only
	     STATUS  mandatory
	     DESCRIPTION
		     "This variable reports the status for the
		      communication to the Primary Controller." 

	     ::= { ssEntry 9 }

	ssEmuExtInputStatus OBJECT-TYPE
            SYNTAX  INTEGER  {
                          ALL_OK(0),
                          AT_LEAST_1_FAILURE(1)
                      }
	     ACCESS  read-only
	     STATUS  mandatory
	     DESCRIPTION
		     "This variable reports the status for the
		      EMU external input." 

	     ::= { ssEntry 10 }

	ssEmuPresent OBJECT-TYPE
            SYNTAX  INTEGER  {
                          EMU_NOT_PRESENT(0),
                          EMU_PRESENT(1)
                      }
	      ACCESS  read-only
	      STATUS  mandatory
	      DESCRIPTION
		      "This variable reports the availability of the
		       Environment Monitoring Unit for the storage subsystem." 

	     ::= { ssEntry 11 }


	ssController1Status OBJECT-TYPE
            SYNTAX  INTEGER  {
                          NORMAL(0),
                          FAILED(1)
                      }
	     ACCESS  read-only
	     STATUS  mandatory
	     DESCRIPTION
		     "This variable reports the status for the
		      Primary Controller."

	     ::= { ssEntry 12 }

	ssController1SerNum OBJECT-TYPE
	     SYNTAX  DisplayString
	     ACCESS  read-only
	     STATUS  mandatory
	     DESCRIPTION
		     "The Primary Controller's Serial Number."
		      
	     ::= { ssEntry 13 }

	ssController1RDAC OBJECT-TYPE
            SYNTAX  INTEGER  {
                          SINGLE_MODE(0),
                          DUAL_MODE(1)
                      }
	     ACCESS  read-only
	     STATUS  mandatory
	     DESCRIPTION
		     "The Primary Controller MODE."
		      
	     ::= { ssEntry 14 }

	ssController1Type OBJECT-TYPE
	     SYNTAX  DisplayString
	     ACCESS  read-only
	     STATUS  mandatory
	     DESCRIPTION
		     "The Primary Controller's Type indicator."
		      
	     ::= { ssEntry 15 }

	ssController1ProdID OBJECT-TYPE
	     SYNTAX  DisplayString
	     ACCESS  read-only
	     STATUS  mandatory
	     DESCRIPTION
		     "The Primary Controller's Product ID."
		      
	     ::= { ssEntry 16 }

	ssController1FwRev OBJECT-TYPE
	     SYNTAX  DisplayString
	     ACCESS  read-only
	     STATUS  mandatory
	     DESCRIPTION
		     "The Primary Controller's Firmware Revision."
		      
	     ::= { ssEntry 17 }

	ssController1HwRev OBJECT-TYPE
	     SYNTAX  DisplayString
	     ACCESS  read-only
	     STATUS  mandatory
	     DESCRIPTION
		     "The Primary Controller's Hardware Revision."
		      
	     ::= { ssEntry 18 }

	ssController2Status OBJECT-TYPE
            SYNTAX  INTEGER  {
                          NORMAL(0),
                          FAILED(1)
                      }
	     ACCESS  read-only
	     STATUS  mandatory
	     DESCRIPTION
		     "This variable reports the status for the
		      Secondary Controller."

	     ::= { ssEntry 19 }

	ssController2SerNum OBJECT-TYPE
	     SYNTAX  DisplayString
	     ACCESS  read-only
	     STATUS  mandatory
	     DESCRIPTION
		     "The Secondary Controller's Serial Number."
		      
	     ::= { ssEntry 20 }

	ssController2RDAC OBJECT-TYPE
            SYNTAX  INTEGER  {
                          SINGLE_MODE(0),
                          DUAL_MODE(1)
                      }
	     ACCESS  read-only
	     STATUS  mandatory
	     DESCRIPTION
		     "The Secondary Controller MODE."
		      
	     ::= { ssEntry 21 }

	ssController2Type OBJECT-TYPE
	     SYNTAX  DisplayString
	     ACCESS  read-only
	     STATUS  mandatory
	     DESCRIPTION
		     "The Secondary Controller's Type indicator."
		      
	     ::= { ssEntry 22 }

	ssController2ProdID OBJECT-TYPE
	     SYNTAX  DisplayString
	     ACCESS  read-only
	     STATUS  mandatory
	     DESCRIPTION
		     "The Secondary Controller's Product ID."
		      
	     ::= { ssEntry 23 }

	ssController2FwRev OBJECT-TYPE
	     SYNTAX  DisplayString
	     ACCESS  read-only
	     STATUS  mandatory
	     DESCRIPTION
		     "The Secondary Controller's Firmware Revision."
		      
	     ::= { ssEntry 24 }

	ssController2HwRev OBJECT-TYPE
	     SYNTAX  DisplayString
	     ACCESS  read-only
	     STATUS  mandatory
	     DESCRIPTION
		     "The Secondary Controller's Hardware Revision."
		      
	     ::= { ssEntry 25 }

	ssUpsStatus OBJECT-TYPE
            SYNTAX  INTEGER  {
                          UPS_NOT_PRESENT(0),
                          UPS_PRESENT(1)
                      }
	     ACCESS  read-only
	     STATUS  mandatory
	     DESCRIPTION
		     "Uninterruptable Power Supply status."
	      
	     ::= { ssEntry 26 }

	ssLunStatus OBJECT-TYPE
            SYNTAX  INTEGER  {
                          UPS_NOT_PRESENT(0),
                          UPS_PRESENT(1)
                      }
	     ACCESS  read-only
	     STATUS  mandatory
	     DESCRIPTION
		     "LUN status."
	      
	     ::= { ssEntry 27 }

	 END
