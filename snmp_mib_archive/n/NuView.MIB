--******************************************************************************
--
--  NuView, Inc. SNMP Management Information Base
--  Copyright (c) 1998 NuView, Inc.  All Rights Reserved.
--
--  The information in this document is subject to change without notice.
--
--  The NuView enterprise number is:  2427
--
--  The ASN.1 object identifier prefix to the NuView enterprise is:
--  1.3.6.1.4.1.2427
--
--******************************************************************************
--  Summary of NuView Information MIB
--******************************************************************************
--
--  NuView  (1.3.6.1.4.1.2427)
--
--    ClusterX Group (1.3.6.1.4.1.2427.2)
--
--      clxMibStats Group                 (ClusterX.1)
--        clxMibStatsMajRev               (ClusterX.1.1)
--        clxMibStatsMinRev               (ClusterX.1.2)
--        clxMibStatsVendorName           (ClusterX.1.3)
--
--      clxTrapData Group                 (ClusterX.2)
--        clxTrapDataString01             (ClusterX.2.1)
--	  clxTrapDataNodeName	  	  (ClusterX.2.2)	
--        clxTrapDataClusterName          (ClusterX.2.3)	
--	  clxTrapDataResourceName         (ClusterX.2.4)	
--	  clxTrapDataResourceType         (ClusterX.2.5)	
--	  clxTrapDataSeverityValue	  (ClusterX.2.6)	
--	  clxTrapDataNetwork              (ClusterX.2.7)	
--	  clxTrapEventDate	          (ClusterX.2.8)	
--	  clxTrapEventTime	          (ClusterX.2.9)	
--	  clxTrapEventSource	          (ClusterX.2.10)	
--	  clxTrapEventCategory            (ClusterX.2.11)	
--	  clxTrapEventID	          (ClusterX.2.12)	
--	  clxTrapEventUser	          (ClusterX.2.13)	
--	  clxTrapEventComputer	          (ClusterX.2.14)	
--        clxTrapDataNetworkName          (ClusterX.2.15)
--      clxUptimeStats Group              (ClusterX.3)
--
--      clxAvailabilityStats Group        (ClusterX.4)
--
--******************************************************************************

NuView-MIB DEFINITIONS ::= BEGIN

  IMPORTS
    enterprises    FROM RFC1155-SMI
    DisplayString  FROM RFC1213-MIB
    OBJECT-TYPE    FROM RFC-1212
    TRAP-TYPE      FROM RFC-1215;

  NuView                   OBJECT IDENTIFIER ::= { enterprises 2427 }

    ClusterX               OBJECT IDENTIFIER ::= { NuView 2 }
      clxMibStats          OBJECT IDENTIFIER ::= { ClusterX 1 }
      clxTrapData          OBJECT IDENTIFIER ::= { ClusterX 2 }
--      clxUptimeStats       OBJECT IDENTIFIER ::= { ClusterX 3 }
--      clxAvailabilityStats OBJECT IDENTIFIER ::= { ClusterX 4 }

--******************************************************************************
--  clxMibStats Information
--******************************************************************************

clxMibStatsMajRev OBJECT-TYPE
  SYNTAX  INTEGER (1..65535)
  ACCESS  read-only
  STATUS  mandatory
  DESCRIPTION
    "The major revision level of the ClusterX SNMP extension agent MIB."
  ::= { clxMibStats 1 }

clxMibStatsMinRev OBJECT-TYPE
  SYNTAX  INTEGER (1..65535)
  ACCESS  read-only
  STATUS  mandatory
  DESCRIPTION
    "The minor revision level of the ClusterX SNMP extension agent MIB."
  ::= { clxMibStats 2 }

clxMibStatsVendorName OBJECT-TYPE
  SYNTAX  DisplayString
  ACCESS  read-only
  STATUS  mandatory
  DESCRIPTION
    "The name of the vendor supplying the ClusterX SNMP extension agent MIB."
  ::= { clxMibStats 3 }

--******************************************************************************
--  clxTrapData Information
--******************************************************************************

clxTrapDataString01 OBJECT-TYPE
  SYNTAX  DisplayString
  ACCESS  not-accessible
  STATUS  mandatory
  DESCRIPTION
    "Custom string 1 (Varbind #1) for NuView ClusterX trap."
  ::= { clxTrapData 1 }

clxTrapDataNodeName OBJECT-TYPE
  SYNTAX  DisplayString
  ACCESS  not-accessible
  STATUS  mandatory
  DESCRIPTION
    "Name of the MSCS Node. "
  ::= { clxTrapData  2 }

clxTrapDataClusterName OBJECT-TYPE
  SYNTAX  DisplayString
  ACCESS  not-accessible
  STATUS  mandatory
  DESCRIPTION
    "Name of the MSCS Cluster. "
  ::= { clxTrapData   3 }

clxTrapDataResourceName OBJECT-TYPE
  SYNTAX  DisplayString
  ACCESS  not-accessible
  STATUS  mandatory
  DESCRIPTION
    "Name of the MSCS Resource. "
  ::= { clxTrapData 4 }

clxTrapDataResourceType OBJECT-TYPE
  SYNTAX  DisplayString
  ACCESS  not-accessible
  STATUS  mandatory
  DESCRIPTION
    "Type of the MSCS Resource. "
  ::= { clxTrapData 5 }

clxTrapDataSeverityValue OBJECT-TYPE
  SYNTAX INTEGER
  {
     info(0),                -- Information
     warning(1),            --  Warning
     error(2)                  -- Error
  }
  ACCESS    read-only
  STATUS    mandatory
  DESCRIPTION
     "The severity value type."
  ::= {clxTrapData 6 }

clxTrapDataNetwork OBJECT-TYPE
  SYNTAX  DisplayString
  ACCESS  not-accessible
  STATUS  mandatory
  DESCRIPTION
    "Network Info "
  ::= {clxTrapData 7 }

clxTrapEventDate OBJECT-TYPE
  SYNTAX  DisplayString
  ACCESS  not-accessible
  STATUS  mandatory
  DESCRIPTION
    "Date of the Event created in NT event log file "
  ::= { clxTrapData 8 }


clxTrapEventTime OBJECT-TYPE
  SYNTAX  DisplayString
  ACCESS  not-accessible
  STATUS  mandatory
  DESCRIPTION
    "Time of the Event created in NT event log file "
  ::= { clxTrapData 9 }


clxTrapEventSource OBJECT-TYPE
  SYNTAX  DisplayString
  ACCESS  not-accessible
  STATUS  mandatory
  DESCRIPTION
    "Source of the Event created in NT event log file "
  ::= { clxTrapData 10 }

clxTrapEventCategory OBJECT-TYPE
  SYNTAX  DisplayString
  ACCESS  not-accessible
  STATUS  mandatory
  DESCRIPTION
    "Category of the Event created in NT event log file "
  ::= { clxTrapData 11 }

clxTrapEventID OBJECT-TYPE
  SYNTAX  DisplayString
  ACCESS  not-accessible
  STATUS  mandatory
  DESCRIPTION
    "ID of the Event created in NT event log file"
  ::= { clxTrapData 12 }

clxTrapEventUser OBJECT-TYPE
  SYNTAX  DisplayString
  ACCESS  not-accessible
  STATUS  mandatory
  DESCRIPTION
    "User which created the event in NT event log file "
  ::= { clxTrapData 13 }

clxTrapEventComputer OBJECT-TYPE
  SYNTAX  DisplayString
  ACCESS  not-accessible
  STATUS  mandatory
  DESCRIPTION
    "Computer which created Event in NT event log file"
  ::= { clxTrapData 14 }

clxTrapDataNetworkName OBJECT-TYPE
  SYNTAX  DisplayString
  ACCESS  not-accessible
  STATUS  mandatory
  DESCRIPTION
    "Network Name"
  ::= { clxTrapData 15 }

--******************************************************************************
--  clxUptimeStats Information
--******************************************************************************

--******************************************************************************
--  clxAvailabilityStats Information
--******************************************************************************

--******************************************************************************
--  Traps
--******************************************************************************

NuViewTrapStr TRAP-TYPE
  ENTERPRISE   NuView
  VARIABLES    { clxTrapDataString01 }
  DESCRIPTION
    "Generic SNMP trap generated by NuView applications and services.
     Varbind #1:  Custom string."
  ::= 1

ClusterXTrapStr TRAP-TYPE
  ENTERPRISE   ClusterX
  VARIABLES    { clxTrapDataString01 }
  DESCRIPTION
    "Generic SNMP trap generated by NuView ClusterX applications and services.
     Varbind #1:  Custom string."
  ::= 1

ClusterXTrapNodeFail TRAP-TYPE
  ENTERPRISE   ClusterX
  VARIABLES    { clxTrapDataClusterName, clxTrapDataNodeName}
  DESCRIPTION
    "This trap is sent when ClusterX detects the failure of a node in an MSCS cluster. The trap identifies the 
     cluster,the name of the node that failed "
  --#SEVERITY MINOR
  ::= 2

ClusterXTrapClusterFail TRAP-TYPE
  ENTERPRISE   ClusterX
  VARIABLES    { clxTrapDataClusterName}
  DESCRIPTION
    "This trap is sent when ClusterX detects the failure of an MSCS cluster. The trap identifies the name of the failed 
     cluster "
  --#SEVERITY CRITICAL
  ::= 3

ClusterXTrapResourceFail TRAP-TYPE
  ENTERPRISE   ClusterX
  VARIABLES    { clxTrapDataClusterName ,clxTrapDataNodeName, clxTrapDataResourceName}
  DESCRIPTION
    "This trap is sent when ClusterX detects the failure of a resource on an MSCS cluster. The trap identifies the names 
     of the cluster, node and resource "
  --#SEVERITY INFORMATIONAL
  ::= 4

ClusterXTrapNodeJoins TRAP-TYPE
  ENTERPRISE   ClusterX
  VARIABLES    { clxTrapDataClusterName, clxTrapDataNodeName}
  DESCRIPTION
    "This trap is sent when ClusterX detects that node has joined or rejoined an MSCS cluster. The trap identifes the 
     name of the cluster and the name of the node that joined."
  --#SEVERITY INFORMATIONAL
  ::= 5

ClusterXTrapNetworkFail TRAP-TYPE
  ENTERPRISE   ClusterX
  VARIABLES    { clxTrapDataClusterName, clxTrapDataNetworkName}
  DESCRIPTION
    "This trap is sent when ClusterX detects the failure of the private or public cluster interconnects on an MSCS 
     cluster."
  --#SEVERITY MAJOR
  ::= 6

ClusterXTrapNormalClusterServiceLog TRAP-TYPE
  ENTERPRISE   ClusterX
  VARIABLES    {clxTrapEventDate, clxTrapEventTime, clxTrapEventSource, clxTrapEventCategory, clxTrapEventID, clxTrapEventUser, clxTrapEventComputer}
  DESCRIPTION
    "This trap is generated when ClusterX detects that the Cluster Service has written a new entry in the Windows NT 
     Event Log on a managed cluster.It contains the information about cluster service log"
  --#SEVERITY INFORMATIONAL
  ::= 7

ClusterXTrapWarningClusterServiceLog TRAP-TYPE
  ENTERPRISE   ClusterX
  VARIABLES    {clxTrapEventDate, clxTrapEventTime, clxTrapEventSource, clxTrapEventCategory, clxTrapEventID, clxTrapEventUser, clxTrapEventComputer}
  DESCRIPTION
    "This trap is generated when ClusterX detects that the Cluster Service has written a new entry in the Windows NT 
     Event Log on a managed cluster.It contains the information about cluster service log"
  --#SEVERITY WARNING
  ::= 8

ClusterXTrapCriticalClusterServiceLog TRAP-TYPE
  ENTERPRISE   ClusterX
  VARIABLES    {clxTrapEventDate, clxTrapEventTime, clxTrapEventSource, clxTrapEventCategory, clxTrapEventID, clxTrapEventUser, clxTrapEventComputer}
  DESCRIPTION
    "This trap is generated when ClusterX detects that the Cluster Service has written a new entry in the Windows NT 
     Event Log on a managed cluster.It contains the information about cluster service log" 
  --#SEVERITY CRITICAL
  ::= 9

END
