CERAGON-MIB DEFINITIONS ::= BEGIN
--Title:     CERAGON   MIB

-- Copyright 1997 CERAGON.
-- All Rights Reserved.

-- It is CERAGON's intent to encourage the widespread use of
-- this Specification in connection with the management of
-- CERAGON's products. CERAGON grants vendors, end-users,
-- and other interested parties a non-exclusive license to
-- use this Specification in connection with the management
-- of CERAGON's products.

-- This Specification is supplied "as is," and CERAGON makes
-- no warranty, either express or implied, as to the use,
-- operation, condition, or performance of the Specification.

IMPORTS
      Counter, enterprises,
       IpAddress, Gauge       FROM RFC1155-SMI
      DisplayString, ifIndex          FROM RFC1213-MIB
      OBJECT-TYPE                     FROM RFC-1212
      TRAP-TYPE                       FROM RFC-1215;
--      Gauge32                    FROM SNMPv2-SMI;
--      sonetSectionCurrentStatus  FROM SONET-MIB;
--      RowStatus                       FROM SNMPv2-TC;



-- Some MIB compilers need those two lines:
-- enterprises OBJECT IDENTIFIER ::=
--                     { iso org(3) dod(6) internet(1) private(4) 1 }


ceragon OBJECT IDENTIFIER ::= { enterprises 2281 }

-- Version:   5.00i
-- ***************************** 1500P ****************************
-- Supported by IDC version 4.6xx for Regenerator and Jupiter (DS3).
-- Supported by IDC version O2.88 for Omega (Encryption).
-- Supported by IDC version 3.10  for Falcon (FE+8E1\T1).
-- Supported by IDC version 4.7xxx for Typhoon (GbE+8E1\T1)
-- Supported by IDC version 4.9xxx for Summit (64E1\T1+FE)
-- ***************************** 3200T ****************************
-- Supported by IDC version 5.0xxx for AVALON (N+1)
-- ***************************** 1500 *****************************
-- Supported by IDC version 5.22  for (FibeAir15xx)

--First Version Date:    15.04.97

--Last Update:  06.11.2006


gnOID OBJECT IDENTIFIER ::= { ceragon 1}  --    list of CERAGON products

gnFirstOID OBJECT IDENTIFIER ::= { gnOID 1 } -- First product

gnSystem OBJECT IDENTIFIER ::= { ceragon 2 }

--This group contains general parameters of the system.
gnGeneral OBJECT IDENTIFIER ::= { gnSystem 1}

--gnGenHWVersion OBJECT-TYPE
--        SYNTAX  DisplayString
--        ACCESS  read-only
--        STATUS mandatory
--        DESCRIPTION
--        "This parameter specifies the version of the hardware."
--        ::= { gnGeneral 1 }

--gnGenSWVersion OBJECT-TYPE
--        SYNTAX  DisplayString
--        ACCESS  read-only
--        STATUS mandatory
--        DESCRIPTION
--        "This parameter specifies the version of the software."
--        ::= { gnGeneral 2 }

gnGenStandardOrg OBJECT-TYPE
        SYNTAX  INTEGER {
                etsi(2),
                fcc(3),
                japan(4),
                lmds(5),
                cmds(6),
                australia(7),
                other(8)
        }
        ACCESS  read-only
        STATUS mandatory
        DESCRIPTION
        "This parameter specifies which international standard is used."
        ::= { gnGeneral 1 }

gnGenTxFreqRange OBJECT-TYPE
        SYNTAX  INTEGER {
                from37000to37350(2), -- FCC RX Range: 37700->38050
                from37350to37700(3), -- FCC RX Range: 38050->38400
                from37700to38050(4), -- FCC
                from38050to38400(5), -- FCC
                from38600to38950(6), -- FCC RX Range: 39300->39650
                from38950to39300(7),  -- FCC RX Range: 39650->40000
                from39300to39650(8), -- FCC
                from39650to40000(9),  --FCC
                from37058to37618(10), --ETSI  RX Range: 38318->38878
                from37618to38178(11), --ETSI  RX Range: 38878->39438
                from38318to38878(12), --ETSI
                from38878to39438(13), --ETSI
                notUsed(14)

                }
        ACCESS  read-only
        STATUS mandatory
        DESCRIPTION
        "This parameter specifies frequency ranges in Hertz. Value 1 to 13 are used
when the link
         is working with channels. The notUsed value is used when the link is
working with frequency."
        ::= { gnGeneral 2 }

gnGenRemoteConnection OBJECT-TYPE
        SYNTAX  INTEGER {
                connected(2),
                disconnected(3)
        }
        ACCESS  read-only
        STATUS mandatory
        DESCRIPTION
        "Is the connection between the local manager and
         the remote manager."
        ::= { gnGeneral 3 }

gnGenRemoteDistance OBJECT-TYPE
        SYNTAX  INTEGER (100..30000)
        ACCESS  read-write
        STATUS mandatory
        DESCRIPTION
        "This field is the distance between the local and remote ODU, in meters.
        This attribute does not auto-detect the distance.
        It is used as part of the unfaded RSL calculation feature in CERAGONView."
        ::= { gnGeneral 4 }

gnGenInterLenLocalRemote OBJECT-TYPE
        SYNTAX  INTEGER
        ACCESS  read-write
        STATUS mandatory
        DESCRIPTION
        "This field is the FEC interleaver length - DONT CHANGE THIS FIELD !!!.
        WRITE will change both local and remote sides."
        ::= { gnGeneral 5 }

gnGenTxFreqLocalRemote OBJECT-TYPE
        SYNTAX  INTEGER (0..20)
        ACCESS  read-write
        STATUS mandatory
        DESCRIPTION
        "This parameter indicates the radio TX channel number.
        WRITE will change both LOCAL and REMOTE sides.
        Not all radios will support TX frequency change via channel numbers."
        DEFVAL { 1}
        ::= { gnGeneral 6}


gnGenRealTimeandDate OBJECT-TYPE
        SYNTAX OCTET STRING(SIZE(8))
        ACCESS  read-write
        STATUS mandatory
        DESCRIPTION
        "This parameter specifies the real time and date
          Format 'YYYY-MM-DD,HH:MM:SS' (Hexadecimal).
            A date-time specification.

            field  octets  contents                  range
            -----  ------  --------                  -----
              1      1-2   year                      0..65536
              2       3    month                     1..12
              3       4    day                       1..31
              4       5    hour                      0..23
              5       6    minutes                   0..59
                  6       7    seconds                   0..60
                           (use 60 for leap-second)
              7       8    deci-seconds              0..9
              8       9    direction from UTC        '+' / '-'
              9      10    hours from UTC            0..11
             10      11    minutes from UTC          0..59

            For example, Tuesday May 26, 1992 at 1:30:15 PM EDT
            would be displayed as:        07 c8 05 1a 0d 1e 0f 00
                                                                  ( 1992 -5 -26,13:30:15 )

            Note that if only local time is known, then timezone
            information (fields 8-10) is not present."

        ::= { gnGeneral 7 }


gnGenCfgDeviceTable  OBJECT-TYPE
        SYNTAX  SEQUENCE OF GnGenCfgDeviceEntry
        ACCESS  not-accessible
        STATUS mandatory
        DESCRIPTION
        "This table contains general configuration info
          per device, local and remote."
        ::= { gnGeneral 8 }


gnGenCfgDeviceEntry OBJECT-TYPE
        SYNTAX GnGenCfgDeviceEntry
        ACCESS  not-accessible
        STATUS mandatory
          DESCRIPTION
          "Entry containing general configuration information, for both local and
remote sides."
        INDEX { gnGenCfgDeviceId }
        ::= { gnGenCfgDeviceTable 1 }

GnGenCfgDeviceEntry ::=
            SEQUENCE {
        gnGenCfgDeviceId
                     INTEGER,
        gnGenCfgDeviceResetPerfMon
          INTEGER,
        gnGenCfgDeviceOperation
          INTEGER,
        gnGenCfgActivateLoopback
          INTEGER,
        gnGenCfgF1DataChanConnector -- was LineConnector;
-- if DB9 connector, indicates NEW regenerator hardware.
          INTEGER,
        gnGenCfgWaySideConnector --was RadioConnector
                INTEGER,
        gnGenCfgActivateChanLoopback
                  INTEGER,
        gnGenCfgInterLenLocalOnly
                 INTEGER ,
        gnGenCfgSlipIp
                 IpAddress,
        gnGenCfgSlipModemConnection
                 DisplayString,
        gnGenCfgSlipSpeed
                 INTEGER,
        gnGenCfgAlarmSeverity
                OCTET STRING,
        gnGenCfgODUSerialNumber
                DisplayString,
        gnGenCfgIDUSerialNumber
                DisplayString,
        gnGenCfgAlarmText
                DisplayString,
        gnGenCfgTrapSeverity
                 INTEGER,
        gnGenCfgProductType                  -- merge with tftp
                        INTEGER,
        gnGenCfgLeftMediumConnector
            INTEGER,
        gnGenCfgMiddleMediumConnector
            INTEGER,
    gnGenCfgPrimaryClockSource
                        INTEGER,
    gnGenCfgSecondaryClockSource
                        INTEGER,
        gnGenCfgTrapOption
                 INTEGER,
        gnGenCfgCLLI
                        DisplayString,
        gnGenCfgHeartbeatPeriod
                 INTEGER,
        gnGenCfgGetRemoteData
                        INTEGER,
        gnGenCfgClearLoopTimeout
                        INTEGER,
        gnGenCfgSubProductType
                        INTEGER
        }

gnGenCfgDeviceId OBJECT-TYPE
        SYNTAX  INTEGER
        {
                local(1),
                remote(2)
        }
                ACCESS  read-only
           STATUS mandatory
                DESCRIPTION
              "This value indicates the device table entry (local or
Remote)."
        ::= { gnGenCfgDeviceEntry 1 }


gnGenCfgDeviceResetPerfMon OBJECT-TYPE
        SYNTAX  INTEGER {
                reset(2),
                noAction(3),
                clearFastEthernetStatistics(4)
        }
        ACCESS  read-write
        STATUS mandatory
        DESCRIPTION
        "Reset performance monitoring. "
        DEFVAL { noAction }
        ::= { gnGenCfgDeviceEntry 2 }

gnGenCfgDeviceOperation OBJECT-TYPE
        SYNTAX  INTEGER {
                noOperation(2),
        softwareReset(3),
        setDefaultConf(4),
                clearMainManagerSoftware(5),
                resetODU(6),
                resetMUX(7),
                resetSwOdu(8)          -- phos odu only.
        }
        ACCESS  read-write
        STATUS mandatory
        DESCRIPTION
        "This parameter allows the NMS to perform operations.
      (3) will implement software RESET
      (4) will SET all factory default configurations, including IP address!
      (5) will CLEAR IDU software
        NOTE: CLEARING IDU software will cause the IDU to use the factory BOOT
software version.
          4 and 5 will take place only after reset of the IDU"
        DEFVAL { noOperation }
        ::= { gnGenCfgDeviceEntry 3 }


gnGenCfgActivateLoopback OBJECT-TYPE
        SYNTAX  INTEGER {
                noOperation(2),
                loopbackSPI(3),
---                    loopbackMUX(4),
                      loopbackMDM(5),
                loopbackOuterSPI(6),
--                localTechnSPIloopback(7),
--                     localTechnMUXloopback(8),
--                     localTechnMDMloopback(9),
                localODUloopback(10)
        }
        ACCESS  read-write
        STATUS mandatory
        DESCRIPTION
        "This parameter controls the loop back diagnostics operations.
        For remote units, only SPI, MUX and MDM loopbacks are allowed.
        "
        DEFVAL { noOperation }
        ::= { gnGenCfgDeviceEntry 4 }

gnGenCfgF1DataChanConnector OBJECT-TYPE
        SYNTAX  INTEGER {
                noInterface(1), -- No interface
                rs232db25(2),  -- V24
                v35(3),
                rs422db25(4),  --RS-530
                rj45CoDirect(5),
                rj45bridge(6), -- Ethernet bridge
                x21db15(7),
                rs232db9(8)    -- New regenerator hardware
        }
        ACCESS  read-only
        STATUS mandatory
        DESCRIPTION
        "This is the physical interface of the F1 line data channel
        (USER CHANNEL connection). "
        DEFVAL { rs232db25 }
        ::= { gnGenCfgDeviceEntry 5 }

gnGenCfgWaySideConnector OBJECT-TYPE
        SYNTAX  INTEGER {
                noInterface(1), -- No interface
                rs232db25(2),  -- V24
                v35(3),
                rs422db25(4),  -- RS-530
                connectorE1(5),
                rj45bridge(6), -- Ethernet Bridge
                x21db15(7),
                connectorT1(8),
                                lineSTM4(9),
        clockUnit2M(10),
        clockUnit1dot5M(11)
        }
        ACCESS  read-only
        STATUS mandatory
        DESCRIPTION
        "This is the physical interface of the radio E1 way side channel
        (WAYSIDE CHANNEL connection)."
        DEFVAL { noInterface }
        ::= { gnGenCfgDeviceEntry 6 }


gnGenCfgActivateChanLoopback OBJECT-TYPE
        SYNTAX  INTEGER {
                noOperation(2),
                      loopbackDataChan(3),
                      loopbackWaySide(4)

        }
        ACCESS  read-write
        STATUS mandatory
        DESCRIPTION
        "This parameter controls the USER CHANNEL and WAYSIDE channel
        loopback diagnostic operations.
        (3) will activate the 64k data channel loopback (USER CHANNEL)
      (4) will activate the WAYSIDE CHANNEL loopback."
        DEFVAL { noOperation }
        ::= { gnGenCfgDeviceEntry 7 }


gnGenCfgInterLenLocalOnly OBJECT-TYPE
        SYNTAX  INTEGER
        ACCESS  read-write
        STATUS mandatory
        DESCRIPTION
        "This field is the FEC interleaver length .DONT CAHNGE THIS FIELD !!! .
        WRITE will change the local side only."
        ::= { gnGenCfgDeviceEntry 8 }


gnGenCfgSlipIp OBJECT-TYPE
        SYNTAX  IpAddress
        ACCESS  read-write
        STATUS mandatory
        DESCRIPTION
        "This is the SERIAL interface IP address.
        Included for future development, not currently supported."
        ::= { gnGenCfgDeviceEntry 9 }

gnGenCfgSlipModemConnection OBJECT-TYPE
        SYNTAX  DisplayString
        ACCESS  read-write
        STATUS mandatory
        DESCRIPTION
        "The telephone number to which the modem will initialize a call,
        upon generation of a TRAP.
        The number must be entered numerically (for example 18001234567)."
        ::= { gnGenCfgDeviceEntry 10 }


gnGenCfgSlipSpeed OBJECT-TYPE
        SYNTAX  INTEGER {
                baud9600(1),
                baud19200(2),
                baud38400(3),
                baud57600(4),
                baud115200(5)
        }
              ACCESS  read-write
              STATUS  mandatory
              DESCRIPTION
              "The SERIAL interface baud rate."
              ::= { gnGenCfgDeviceEntry 11 }


gnGenCfgAlarmSeverity  OBJECT-TYPE
              SYNTAX OCTET STRING(SIZE(15))
              ACCESS  read-write
              STATUS  mandatory
              DESCRIPTION
              "This field is used only by the Ceraview management
application
                           Every Trap severity 4 bits.
                 15 (MAJOR), 7 (MINOR), 3 (WARNING) and 1 (EVENT) options.
                 The first 4 bits ODU Power supply severity,
               then the Synthesizer severity ,then Tx level then RX level
               ODU temperature, ODU loopback , IDU power supply , Cable,
               Modem, IDU temperature, IDU loopbacks, External Alarm 1,
               External Alarm 2 ,External Alarm 3, External Alarm 4,
               External Alarm 5, External Alarm 6, External Alarm 7,
               External Alarm 8, Remote connectivity, LOF, LOS, EXC, SD
               J0 mismatch and system fault."
              ::= { gnGenCfgDeviceEntry 12 }

gnGenCfgODUSerialNumber OBJECT-TYPE
        SYNTAX  DisplayString(SIZE(0..20))
        ACCESS  read-only
        STATUS mandatory
        DESCRIPTION
        "This is the ODU serial number - up to 20 characters "
        ::= { gnGenCfgDeviceEntry 13 }

gnGenCfgIDUSerialNumber OBJECT-TYPE
        SYNTAX  DisplayString(SIZE(0..20))
        ACCESS  read-only
        STATUS mandatory
        DESCRIPTION
        "This is the IDU serial number - up to 20 characters "
        ::= { gnGenCfgDeviceEntry 14}

gnGenCfgAlarmText OBJECT-TYPE
        SYNTAX  DisplayString
        ACCESS  read-only
        STATUS mandatory
        DESCRIPTION
        "The private trap text, describing the last generated trap text."
        ::= { gnGenCfgDeviceEntry 15}

gnGenCfgTrapSeverity OBJECT-TYPE

        SYNTAX  INTEGER
        {
                clear                (0),
                event                (1),
                warning                (3),
                minor                (7),
                major                (15),
                critical        (31)
        }
        ACCESS  read-only
        STATUS  mandatory
        DESCRIPTION
        "The current Trap severity, describing the last generated trap
severity"
         ::= { gnGenCfgDeviceEntry 16 }
-- *******************************************************************
-- The following fields were added for the Access product
-- *******************************************************************

gnGenCfgProductType        OBJECT-TYPE
        SYNTAX  INTEGER
                {
                                accessMux                                    (2),
                            sdhRegenerator                         (3),
                                narrowBandPdhRepeater        (4),
                                accessMuxStm0                        (5),
                                plex6200                                (6),
                                adm                                                (7)
                }
        ACCESS  read-only
        STATUS  mandatory
        DESCRIPTION
        "The product type."
         ::= { gnGenCfgDeviceEntry 17 }


gnGenCfgLeftMediumConnector OBJECT-TYPE
        SYNTAX  INTEGER {
                noInterface(1), -- No interface
                twoDS3(2),
                oneDS3(3),
                twoE3(4),
                oneE3(5),
                oneFastEthernet(6),
                fiberSTM1(7),
                electricalSTM1(8),
                utpSTM1(9),
                stpSTM1(10),
                twoSTM1(11),
                eightE1(12),
                eightT1(13),
                hitLess(14),
                fiberSTM1Trib(15),
                electricalSTM1Trib(16),
                hitLessWithBridge(17),
                opticalFastEthernet(18)

        }
        ACCESS  read-only
        STATUS mandatory
        DESCRIPTION
        "For ACCESS hardware, this indicates the first (left) interface connector."
        DEFVAL { twoDS3 }
        ::= { gnGenCfgDeviceEntry 18 }

gnGenCfgMiddleMediumConnector OBJECT-TYPE
        SYNTAX  INTEGER {
                noInterface(1), -- No interface
                twoDS3(2),
                oneDS3(3),
                twoE3(4),
                oneE3(5),
                oneFastEthernet(6),
                fiberSTM1(7),
                electricalSTM1(8),
                utpSTM1(9),
                stpSTM1(10),
                twoSTM1(11),
                eightE1(12),
                eightT1(13),
                hitLess(14),
                fiberSTM1Trib(15),
                electricalSTM1Trib(16),
                hitLessWithBridge(17),
                opticalFastEthernet(18)
        }
        ACCESS  read-only
        STATUS mandatory
        DESCRIPTION
        "For ACCESS hardware, this indicates the second (right)interface connector."
        DEFVAL { oneDS3 }
        ::= { gnGenCfgDeviceEntry 19 }

gnGenCfgPrimaryClockSource OBJECT-TYPE
        SYNTAX  INTEGER {
                                internalClock(2),
                external2MB(3),
                radioClock(4),
                fiberClock(5),
                external2MHz(6),
                external1AndHalfMB(7),
                                tributaryClock1(8),
                                tributaryClock2(9),
                                tributaryClock3(10),
                                tributaryClock4(11),
                                tributaryClock5(12),
                                tributaryClock6(13),
                                tributaryClock7(14),
                                tributaryClock8(15),
                                tributaryClock9(16),
                                tributaryClock10(17),
                                tributaryClock11(18),
                                tributaryClock12(19),
                                tributaryClock13(20),
                                tributaryClock14(21),
                                tributaryClock15(22),
                                tributaryClock16(23),
                                tribSTM1(24)
        }
        ACCESS  read-write
        STATUS mandatory
        DESCRIPTION
        "The primary clock source, configurable for ACCESS radios only."
        DEFVAL { internalClock }
        ::= { gnGenCfgDeviceEntry 20 }

gnGenCfgSecondaryClockSource OBJECT-TYPE
        SYNTAX  INTEGER {
                                internalClock(2),
                external2MB(3),
                radioClock(4),
                fiberClock(5),
                external2MHz(6),
                external1AndHalfMB(7),
                                tributaryClock1(8),
                                tributaryClock2(9),
                                tributaryClock3(10),
                                tributaryClock4(11),
                                tributaryClock5(12),
                                tributaryClock6(13),
                                tributaryClock7(14),
                                tributaryClock8(15),
                                tributaryClock9(16),
                                tributaryClock10(17),
                                tributaryClock11(18),
                                tributaryClock12(19),
                                tributaryClock13(20),
                                tributaryClock14(21),
                                tributaryClock15(22),
                                tributaryClock16(23),
                                tribSTM1(24)
        }
        ACCESS  read-write
        STATUS mandatory
        DESCRIPTION
        "The secondary clock source, configurable for ACCESS radios only."
        DEFVAL { internalClock }
        ::= { gnGenCfgDeviceEntry 21 }

gnGenCfgTrapOption OBJECT-TYPE
        SYNTAX INTEGER (0..31)
        ACCESS read-write
        STATUS mandatory
        DESCRIPTION
        " This item defines various trap options (0-31):

          0 - SNSN (STANDARD TRAPS DO NOT INCLUDE SERIAL NUMBER)
          1 - ASN  (ALL TRAPS INCLUDE SERIAL NUMBER)
          2 - SNSN, DNLR (DO NOT REPORT LOCAL TRAPS FROM REMOTE IDU)
          3 - ASN, DNLR
          4 - SNSN, EVT (USE DIFFERENT TRAP ID FOR EACH ALARM TYPE)
          5 - ASN, EVT
          6 - SNSN, DNLR, EVT
          7 - ASN, DNLR, EVT

          * - Add 8 to your choice for excluding traps with id >= 128.
                    Example: for SNSN, DNLR with this filter write 10 (=8+2).
          ** - Add another 16 to your choice in order to send 'clear' traps with zero severity."
        DEFVAL { 0 }
        ::= { gnGenCfgDeviceEntry 22 }

gnGenCfgCLLI OBJECT-TYPE
        SYNTAX DisplayString (SIZE(0..30))
        ACCESS read-write
        STATUS mandatory
        DESCRIPTION
        " Common Language Location Identifier (maximum length: 30)"
        ::= { gnGenCfgDeviceEntry 23 }

gnGenCfgHeartbeatPeriod OBJECT-TYPE
        SYNTAX INTEGER (0..65535)
        ACCESS read-write
        STATUS mandatory
        DESCRIPTION
        " This item defines the number of minutes between each trap"
        DEFVAL { 0 }
        ::= { gnGenCfgDeviceEntry 24 }

gnGenCfgGetRemoteData OBJECT-TYPE
        SYNTAX  INTEGER {
                                off(2),
                     on(3)
                                }
    ACCESS  read-write
    STATUS mandatory
        DESCRIPTION
        "."
        DEFVAL        {off}
    ::= { gnGenCfgDeviceEntry 25 }

gnGenCfgClearLoopTimeout OBJECT-TYPE
        SYNTAX INTEGER (0..1440)
        ACCESS read-write
        STATUS mandatory
        DESCRIPTION
        "  This item defines the clear loopbacks timeout in minutes.
        possible values: 0..1440.
        0 means disable. "
        DEFVAL { 0 }
        ::= { gnGenCfgDeviceEntry 26 }

gnGenCfgSubProductType OBJECT-TYPE
        SYNTAX  INTEGER
        ACCESS  read-only
        STATUS mandatory
                DESCRIPTION
                "lsb bit: 1 if fibeair 1500i or 1528i 0 otherwise."
        ::= { gnGenCfgDeviceEntry 27 }


gnGenStatDeviceTable  OBJECT-TYPE
        SYNTAX  SEQUENCE OF GnGenStatDeviceEntry
        ACCESS  not-accessible
        STATUS mandatory
        DESCRIPTION
        "This table contains general configuration info
          per device; local and remote."
        ::= { gnGeneral 9 }


gnGenStatDeviceEntry OBJECT-TYPE
        SYNTAX GnGenStatDeviceEntry
        ACCESS  not-accessible
        STATUS mandatory
          DESCRIPTION
          "Entry containing general configuration information per device, both
local and remote sides."
        INDEX { gnGenStatDeviceId }
        ::= { gnGenStatDeviceTable 1 }

GnGenStatDeviceEntry ::=
            SEQUENCE {
        gnGenStatDeviceId
             INTEGER,
        gnGenStatDeviceCelsiusTemp
             INTEGER,
        gnGenStatDeviceFahrenheitTemp
             INTEGER,
-- The following variables are concerning the service of the IDU
        gnGenStatDevicePowerSupply
          OCTET STRING,
        gnGenStatDeviceCable
          INTEGER,
        gnGenStatDeviceDryContact
          OCTET STRING,
        gnGenStatDeviceLeds
          OCTET STRING,
        gnGenStatInternalCommunication
           OCTET STRING ,
        gnGenStatDeviceFanStatus
           OCTET STRING,
        gnGenStatDeviceODUStatus
           OCTET STRING,
        gnGenStatDeviceIDUStatus
           OCTET STRING,
        gnGenStatDeviceRSTStatus
           OCTET STRING
}


gnGenStatDeviceId OBJECT-TYPE
        SYNTAX  INTEGER
        {
                local(1),
                remote(2),
                drawer1(3),
                drawer2(4)
        }
        ACCESS  read-only
           STATUS mandatory
        DESCRIPTION
        "This value indicates which device is involved
        in the specific row."
        ::= { gnGenStatDeviceEntry 1 }

gnGenStatDeviceCelsiusTemp OBJECT-TYPE
        SYNTAX  INTEGER (-10..70)
        ACCESS  read-only
        STATUS mandatory
        DESCRIPTION
        "This is the temperature of the modem of the IDU in degrees of
Celsius."
        ::= { gnGenStatDeviceEntry 2 }

gnGenStatDeviceFahrenheitTemp OBJECT-TYPE
        SYNTAX  INTEGER (14..158)
        ACCESS  read-only
        STATUS mandatory
        DESCRIPTION
        "This is the temperature of the modem of the IDU in degrees of
Fahrenheit."
        ::= { gnGenStatDeviceEntry 3 }

gnGenStatDevicePowerSupply OBJECT-TYPE
        SYNTAX OCTET STRING(SIZE(1))
        ACCESS  read-only
        STATUS mandatory
        DESCRIPTION
        "This octet represents the status of the power
        supplies of the IDU:
        bit 1 on = 3.3V faulty
        bit 2 on = -5V faulty
        bit 3 on = 5V faulty.
      bit 4 on = +8V faulty "

        ::= { gnGenStatDeviceEntry 4 }

gnGenStatDeviceCable OBJECT-TYPE
        SYNTAX  INTEGER {
                ok(2),
                short(3),
                open(4)
        }
        ACCESS  read-only
        STATUS mandatory
        DESCRIPTION
        "Status of the cable to the ODU."
        ::= { gnGenStatDeviceEntry 5 }


gnGenStatDeviceDryContact OBJECT-TYPE
        SYNTAX OCTET STRING(SIZE(2))
        ACCESS  read-only
        STATUS mandatory
        DESCRIPTION
        "The status of the dry contacts, Each input status is represented by a bit.
         When the input is on, the bit value is 0.When the input is off, the bit
value is 1.
         The MSB represents external alarm 8. For example when only external alarm
1 is
         on the status value will be 0xFE00"
        ::= { gnGenStatDeviceEntry 6 }

gnGenStatDeviceLeds OBJECT-TYPE
        SYNTAX OCTET STRING(SIZE(3))
        ACCESS  read-only
        STATUS mandatory
        DESCRIPTION
        "The status of the IDU front panel LEDs. For the management station use. "
        ::= { gnGenStatDeviceEntry 7 }

gnGenStatInternalCommunication  OBJECT-TYPE
        SYNTAX  OCTET STRING (SIZE(1))
        ACCESS  read-only
        STATUS mandatory
        DESCRIPTION
        "The status of internal communication problem
         bit 1 = 1: between main CPU and ODU CPU.
         bit 2 = 1: between main CPU and MUX CPU.
         bit 3 = 1: between master main CPU and slave main CPU."
        ::= { gnGenStatDeviceEntry 8 }

gnGenStatDeviceFanStatus  OBJECT-TYPE
        SYNTAX  OCTET STRING (SIZE(1))
        ACCESS  read-only
        STATUS mandatory
        DESCRIPTION
        "The status of the IDU fans 1-2 or 1-4.
         bit 1 = IDU Fan1 is faulty.
         bit 2 = IDU Fan2 is faulty.
         bit 3 = IDU Fan2 is faulty.
         bit 4 = IDU Fan2 is faulty."
        ::= { gnGenStatDeviceEntry 9 }

gnGenStatDeviceODUStatus  OBJECT-TYPE
        SYNTAX  OCTET STRING (SIZE(2))
        ACCESS  read-only
        STATUS mandatory
        DESCRIPTION
        "ODU status reported with this parameter.
         Bit1 is MSB. The bit is set when a fault occurs.
         The bit is cleared when the fault clears.
         bit 1 = Power Supply status
         bit 2 = Synthesizer lock status
         bit 3 = Tx level status
         bit 4 = ATPC status
         bit 5 = Rx level status
         bit 6 = Not currently used.
         bit 7 = Temperature status
         bit 8 = Not currently used.
         bit 9 = ODU loopback status.
         bit 10 = Internal use (by application).
         bit 11 = Tx is in Mute.
         "
        ::= { gnGenStatDeviceEntry 10 }

gnGenStatDeviceIDUStatus  OBJECT-TYPE
        SYNTAX  OCTET STRING (SIZE(4))
        ACCESS  read-only
        STATUS mandatory
        DESCRIPTION
        "IDU status reported with this parameter. Bit1 is MSB.
         The bit is set when a fault occurs. The bit is
          cleared when the fault clears.

         bit 1  = Power status
         bit 2  = Cable open status
         bit 3  = Cable short status
         bit 4  = Modem Lock status
         bit 5  = Temperature status
         bit 6  = No signal from ODU (Phos only)
         bit 7  = loopback status
         bit 8  = External alarm 1 status
         bit 9  = External alarm 2 status
         bit 10 = External alarm 3 status
         bit 11 = External alarm 4 status
         bit 12 = External alarm 5 status
         bit 13 = External alarm 6 status
         bit 14 = External alarm 7 status
         bit 15 = External alarm 8 status
         bit 16 = Remote connectivity status.
         bit 17 = Inner communication status.
         bit 18 = Link ID mismatch status.
         bit 19 = Configuration mismatch status.
         bit 20 = Shelf Id mismatch status (Phos only).
         bit 21 = General HW failure.
         bit 22 = No power to MUX board.
         bit 23 = No power to MODEM board.
         bit 24 = IDC disk firmware cinfiguration mismatch.
         bit 25 = Modem configuration file.
         bit 26 = Wayside channel E1/T1 LOS
         bit 27 = loopback on Wayside channel
         "
        ::= { gnGenStatDeviceEntry 11 }

gnGenStatDeviceRSTStatus  OBJECT-TYPE
        SYNTAX  OCTET STRING (SIZE(2))
        ACCESS  read-only
        STATUS mandatory
        DESCRIPTION
        "The bit is set when a fault occurs. The bit is
          cleared when the fault clears.

         bit 1 = Line loss of frame status
         bit 2 = Radio loss of frame status
         bit 3 = Line  EXC status
         bit 4 = Radio EXC status
         bit 5 = Line  SD status
         bit 6 = Radio SD status
         bit 7 = loss of signal status
         bit 8 = J0 mismatch.
         bit 9 = Line UNE status.
         "
        ::= { gnGenStatDeviceEntry 12 }

gnGenChannelBandwidth OBJECT-TYPE
        SYNTAX  INTEGER
        ACCESS  read-only
        STATUS mandatory
        DESCRIPTION
        "The TX channel bandwidth, displayed in 1/100 MHz.
        For example:
        An STM-1 ETSI TX channel bandwidth of 56MHz is displayed as the value 5600."
        ::= { gnGeneral 10 }

gnGenTxFreqNumLocalRemote OBJECT-TYPE
        SYNTAX  INTEGER
        ACCESS  read-write
        STATUS mandatory
        DESCRIPTION
        "Indicates the radio transmit frequency, displayed in
        1/100 MHz. WRITE changes the local and remote sides. Only for systems that
        support        frequency configuration (Not channel)."
        ::= { gnGeneral 11}

gnGenProtocolType OBJECT-TYPE
        SYNTAX  INTEGER {
                gnSDH(2),
                      gnSONET(3),
                      gnSONET-C(4),
                                gnSDH-C(5)        --SDH-concatenated for plex6200 (stm4)
        }
        ACCESS  read-write
        STATUS mandatory
        DESCRIPTION
        "This is the radio mapping protocol. -C represents 'concatenated'.  "
        ::= { gnGeneral 12}

gnGenLinkId OBJECT-TYPE
        SYNTAX INTEGER (0..65535)
        ACCESS  read-write
        STATUS mandatory
                DESCRIPTION
                "0 for 'old' system that doesn't support the link ID.
                the user can enter values from 1 to 65535"
            DEFVAL        {0}
        ::= { gnGeneral 13 }

gnGenMibVersion OBJECT-TYPE
                SYNTAX  DisplayString (SIZE(0..15))
        ACCESS  read-only
        STATUS mandatory
                DESCRIPTION
                "The current software version supports this MIB version (and the previous MIB versions)."
        ::= { gnGeneral 14 }

gnGenModemType OBJECT-TYPE
        SYNTAX  INTEGER {
                                gn16QAM(2),
                     gn32QAM(3),
                      gn128QAM(4),
                                gn256QAM(5),
                      gn64QAM(6),
                      gn4QAM(7)
                }
        ACCESS  read-only
        STATUS mandatory
                DESCRIPTION
                "The system modem type."
        ::= { gnGeneral 15 }

gnGenRadioSide OBJECT-TYPE
        SYNTAX  INTEGER {
                                east(2),
                     west(3)
                }
        ACCESS  read-write
        STATUS mandatory
            DEFVAL        {east}
        ::= { gnGeneral 16 }

gnGenSystemWorkTime OBJECT-TYPE
        SYNTAX  INTEGER
        ACCESS  read-write
        STATUS mandatory
                DESCRIPTION
                "The System Work Time (hours)."
            DEFVAL        {0}
        ::= { gnGeneral 17 }

gnGenRxFreqNumLocalRemote OBJECT-TYPE
        SYNTAX  INTEGER
        ACCESS  read-write
        STATUS mandatory
        DESCRIPTION
        "Indicates the radio receive frequency, displayed in
        1/100 MHz. WRITE changes the local and remote sides. Only for systems that
        support        frequency configuration (Not channel)."
        ::= { gnGeneral 18}

gnGenLastCfgTimeandDate OBJECT-TYPE
        SYNTAX OCTET STRING(SIZE(8))
        ACCESS  read-write
        STATUS mandatory
        DESCRIPTION
        "This parameter specifies the last configuration change time and date
          Format 'YYYY-MM-DD,HH:MM:SS' (Hexadecimal).
            A date-time specification.

            field  octets  contents                  range
            -----  ------  --------                  -----
              1      1-2   year                      0..65536
              2       3    month                     1..12
              3       4    day                       1..31
              4       5    hour                      0..23
              5       6    minutes                   0..59
                  6       7    seconds                   0..60
                           (use 60 for leap-second)
              7       8    deci-seconds              0..9
              8       9    direction from UTC        '+' / '-'
              9      10    hours from UTC            0..11
             10      11    minutes from UTC          0..59

            For example, Tuesday May 26, 1992 at 1:30:15 PM EDT
            would be displayed as:        07 c8 05 1a 0d 1e 0f 00
                                                                  ( 1992 -5 -26,13:30:15 )

            Note that if only local time is known, then timezone
            information (fields 8-10) is not present."
        ::= { gnGeneral 19 }

gnGenMostSevereAlarm OBJECT-TYPE
        SYNTAX  INTEGER {
                clear                (0),
                event                (1),
                warning                (3),
                minor                (7),
                major                (15),
                critical        (31)
        }
        ACCESS  read-only
        STATUS mandatory
        DESCRIPTION
        "This parameter specifies the current moset severe alarm in the system."
        ::= { gnGeneral 20 }

gnGenIdcCfgTable  OBJECT-TYPE
        SYNTAX  SEQUENCE OF GnGenIdcCfgEntry
        ACCESS  not-accessible
        STATUS mandatory
        DESCRIPTION
        ""
        ::= { gnGeneral 21 }

gnGenIdcCfgEntry OBJECT-TYPE
        SYNTAX GnGenIdcCfgEntry
        ACCESS  not-accessible
        STATUS mandatory
          DESCRIPTION
          ""
        INDEX { gnGenIdcCfgId }
        ::= { gnGenIdcCfgTable 1 }

GnGenIdcCfgEntry ::=
            SEQUENCE {
        gnGenIdcCfgId
                        INTEGER,
        gnGenIdcCfgXpicMode
                        INTEGER,
        gnGenIdcCfgResetPerfMon
                    INTEGER,
        gnGenIdcCfgOperation
                    INTEGER,
        gnGenIdcCfgWaySideConnector
                        INTEGER,
        gnGenIdcCfgHeartbeatPeriod
                        INTEGER,
        gnGenIdcCfgClearLoopTimeout
                        INTEGER,
        gnGenIdcCfgSlipIp
                IpAddress,
        gnGenIdcCfgSlipModemConnection
                DisplayString,
        gnGenIdcCfgSlipSpeed
                INTEGER,
        gnGenIdcCfgAlarmSeverity
                OCTET STRING,
        gnGenIdcCfgIDUSerialNumber
                DisplayString,
        gnGenIdcCfgTrapOption
                        INTEGER,
        gnGenIdcCfgCLLI
                DisplayString,
        gnGenIdcCfgEowCascadeStatus
                INTEGER,
		gnGenIdcCfgSerialPPPAdminStatus
				INTEGER
        }

gnGenIdcCfgId OBJECT-TYPE
        SYNTAX  INTEGER
        {
                local(1)
        }
    ACCESS  read-only
           STATUS mandatory
                DESCRIPTION
              " "
        ::= { gnGenIdcCfgEntry 1 }

gnGenIdcCfgXpicMode OBJECT-TYPE
        SYNTAX  INTEGER {
                enable(2),
                disable(3)
        }
        ACCESS  read-write
        STATUS mandatory
        DESCRIPTION
        "  "
        DEFVAL { disable }
        ::= { gnGenIdcCfgEntry 2 }

gnGenIdcCfgResetPerfMon OBJECT-TYPE
        SYNTAX  INTEGER {
                reset(2),
                noAction(3),
                clearFastEthernetStatistics(4)
        }
        ACCESS  read-write
        STATUS mandatory
        DESCRIPTION
        "Reset performance monitoring. "
        DEFVAL { noAction }
        ::= { gnGenIdcCfgEntry 3 }


gnGenIdcCfgOperation OBJECT-TYPE
        SYNTAX  INTEGER {
                noOperation(2),
        softwareReset(3),
        setDefaultConf(4),
                setIDCDefaultConf(5),
                hardwareColdReset(6),
                hardwareSoftReset(7)
        }
        ACCESS  read-write
        STATUS mandatory
        DESCRIPTION
        "."
        DEFVAL { noOperation }
        ::= { gnGenIdcCfgEntry 4 }

gnGenIdcCfgWaySideConnector OBJECT-TYPE
        SYNTAX  INTEGER {
                noInterface(1), -- No interface
        connectorE1(2),
                connectorT1(3),
                connectorDualE1(4),
                connectorDualT1(5),
                connectorDual10baseT(6) -- Ethernet Bridge
        }
        ACCESS  read-only
        STATUS mandatory
        DESCRIPTION
        "This is the physical interface of the radio E1 way side channel
        (WAYSIDE CHANNEL connection)."
        DEFVAL { noInterface }
        ::= { gnGenIdcCfgEntry 5 }

gnGenIdcCfgHeartbeatPeriod OBJECT-TYPE
        SYNTAX INTEGER (0..65535)
        ACCESS read-write
        STATUS mandatory
        DESCRIPTION
        " This item defines the number of minutes between each trap"
        DEFVAL { 0 }
        ::= { gnGenIdcCfgEntry 6 }

gnGenIdcCfgClearLoopTimeout OBJECT-TYPE
        SYNTAX INTEGER (0..1440)
        ACCESS read-write
        STATUS mandatory
        DESCRIPTION
        "  This item defines the clear loopbacks timeout in minutes.
        possible values: 0..1440.
        0 means disable. "
        DEFVAL { 0 }
        ::= { gnGenIdcCfgEntry 7 }


gnGenIdcCfgSlipIp OBJECT-TYPE
        SYNTAX  IpAddress
        ACCESS  read-write
        STATUS mandatory
        DESCRIPTION
        "This is the SERIAL interface IP address."
        ::= { gnGenIdcCfgEntry 8 }

gnGenIdcCfgSlipModemConnection OBJECT-TYPE
        SYNTAX  DisplayString
        ACCESS  read-write
        STATUS mandatory
        DESCRIPTION
        "The telephone number to which the modem will initialize a call,
        upon generation of a TRAP.
        The number must be entered numerically (for example 18001234567)."
        ::= { gnGenIdcCfgEntry 9 }


gnGenIdcCfgSlipSpeed OBJECT-TYPE
        SYNTAX  INTEGER {
                baud9600(1),
                baud19200(2),
                baud38400(3),
                baud57600(4),
                baud115200(5)
        }
              ACCESS  read-write
              STATUS  mandatory
              DESCRIPTION
              "The SERIAL interface baud rate."
              ::= { gnGenIdcCfgEntry 10  }

gnGenIdcCfgAlarmSeverity  OBJECT-TYPE
              SYNTAX OCTET STRING(SIZE(15))
              ACCESS  read-write
              STATUS  mandatory
              DESCRIPTION
              "This field is used only by the Ceraview management application."
              ::= { gnGenIdcCfgEntry 11 }

gnGenIdcCfgIDUSerialNumber OBJECT-TYPE
        SYNTAX  DisplayString(SIZE(0..20))
        ACCESS  read-only
        STATUS mandatory
        DESCRIPTION
        "This is the IDU serial number - up to 20 characters "
        ::= { gnGenIdcCfgEntry 12}

gnGenIdcCfgTrapOption OBJECT-TYPE
        SYNTAX INTEGER (0..31)
        ACCESS read-write
        STATUS mandatory
        DESCRIPTION
        " This item defines various trap options (0-15):

          0 - SNSN (STANDARD TRAPS DO NOT INCLUDE SERIAL NUMBER)
          1 - ASN  (ALL TRAPS INCLUDE SERIAL NUMBER)
          2 - SNSN, DNLR (DO NOT REPORT LOCAL TRAPS FROM REMOTE IDU)
          3 - ASN, DNLR
          4 - SNSN, EVT (EVENTS ARE REPORTED AS TRAPS)
          5 - ASN, EVT
          6 - SNSN, DNLR, EVT
          7 - ASN, DNLR, EVT

          * - Add 8 to your choice for excluding traps with id >= 128.
                    Example: for SNSN, DNLR with this filter write 10 (=8+2).
          ** - Add another 16 to your choice in order to send 'clear' traps with zero severity."
        DEFVAL { 0 }
        ::= { gnGenIdcCfgEntry 13 }

gnGenIdcCfgCLLI OBJECT-TYPE
        SYNTAX DisplayString (SIZE(0..30))
        ACCESS read-write
        STATUS mandatory
        DESCRIPTION
        " Common Language Location Identifier (maximum length: 30)"
        ::= { gnGenIdcCfgEntry 14 }

gnGenIdcCfgEowCascadeStatus OBJECT-TYPE
        SYNTAX  INTEGER {
                        enable(2),
                        disable(3)
        }
        ACCESS  read-write
        STATUS mandatory
        DESCRIPTION
        " Not used!!."
        DEFVAL { disable }
        ::= { gnGenIdcCfgEntry 15 }

gnGenIdcCfgSerialPPPAdminStatus OBJECT-TYPE
        SYNTAX  INTEGER {
            enable(2),
            disable(3)
        }
        ACCESS  read-write
        STATUS mandatory
        DESCRIPTION
        "Enable\Disable PPP over serial interface."
        DEFVAL { enable }
        ::= { gnGenIdcCfgEntry 16 }

-- Deleted two parameters (15 and 16) Eitan 16.11.
-- Add tftp server suppot (15) Haim

gnGenIdcStatTable  OBJECT-TYPE
        SYNTAX  SEQUENCE OF GnGenIdcStatEntry
        ACCESS  not-accessible
        STATUS mandatory
        DESCRIPTION
        ""
        ::= { gnGeneral 22 }

gnGenIdcStatEntry OBJECT-TYPE
        SYNTAX GnGenIdcStatEntry
        ACCESS  not-accessible
        STATUS mandatory
          DESCRIPTION
          ""
        INDEX { gnGenIdcStatId }
        ::= { gnGenIdcStatTable 1 }

GnGenIdcStatEntry ::=
            SEQUENCE {
        gnGenIdcStatId
                        INTEGER,
        gnGenIdcStatXpicSupport
                        INTEGER,
        gnGenIdcStatLeds
                        OCTET STRING,
        gnGenIdcStatIDUStatus
                        OCTET STRING,
        gnGenIdcStatMMCCardStatus
                        OCTET STRING,
        gnGenIdcStatDryContact
                        OCTET STRING,
    gnGenIdcStatFanStatus
                           OCTET STRING,
        gnGenIdcStatLeftDrawerStatus
                        INTEGER,
        gnGenIdcStatRightDrawerStatus
                        INTEGER,
        gnGenIdcStatHitlessSupport
                        INTEGER,
        gnGenIdcStatEowExistence
                        INTEGER,
        gnGenIdcStatEowSupport
                        INTEGER,
        gnGenIdcStatIduPosition
                        INTEGER,
        gnGenIdcStatBoardType
                        INTEGER,
        gnGenIdcStatAgentIPAddress
                        IpAddress,
        gnGenIdcStatInterfaceConnector
                        INTEGER,
        gnGenIdcStatIfTableCounter
                        INTEGER
        }

gnGenIdcStatId OBJECT-TYPE
        SYNTAX  INTEGER
        {
                local(1)
        }
    ACCESS  read-only
           STATUS mandatory
                DESCRIPTION
              " "
        ::= { gnGenIdcStatEntry 1 }

gnGenIdcStatXpicSupport OBJECT-TYPE
        SYNTAX  INTEGER
        {
                yes(2),
                no(3)
        }
        ACCESS  read-only
        STATUS mandatory
        DESCRIPTION
        " "
        ::= { gnGenIdcStatEntry 2 }

gnGenIdcStatLeds OBJECT-TYPE
        SYNTAX OCTET STRING(SIZE(3))
        ACCESS  read-only
        STATUS mandatory
        DESCRIPTION
        " "
        ::= { gnGenIdcStatEntry 3 }

gnGenIdcStatIDUStatus  OBJECT-TYPE
        SYNTAX  OCTET STRING (SIZE(3))
        ACCESS  read-only
        STATUS mandatory
        DESCRIPTION
        "IDU status reported with this parameter. Bit1 is MSB.
         The bit is set when a fault occurs. The bit is
          cleared when the fault clears.

         bit 1  = Fans status
         bit 2  = configuration mismatch
         bit 3  = Internal use
         bit 4  = Internal use
         bit 5  = XPIC cable swap
         bit 6  = External alarm 1 status
         bit 7  = External alarm 2 status
         bit 8 =  External alarm 3 status
         bit 9 =  External alarm 4 status
         bit 10 = External alarm 5 status
         bit 12 = External alarm 6 status
         bit 13 = External alarm 7 status
         bit 14 = External alarm 8 status
         bit 15 = Auxiliary interface card is down
         "
        ::= { gnGenIdcStatEntry 4 }

gnGenIdcStatMMCCardStatus OBJECT-TYPE
        SYNTAX  OCTET STRING (SIZE(1))
        ACCESS  read-only
        STATUS mandatory
        DESCRIPTION
        "Bit1 is MSB.
         bit 1  = 0=MMC card exist, 1=MMC card not exist
         bit 2  = MMC card status: 0=ok, 1=fault "
        ::= { gnGenIdcStatEntry 5 }


gnGenIdcStatDryContact OBJECT-TYPE
        SYNTAX OCTET STRING(SIZE(2))
        ACCESS  read-only
        STATUS mandatory
        DESCRIPTION
        "The status of the dry contacts, Each input status is represented by a bit."
        ::= { gnGenIdcStatEntry 6 }

gnGenIdcStatFanStatus  OBJECT-TYPE
        SYNTAX  OCTET STRING (SIZE(1))
        ACCESS  read-only
        STATUS mandatory
        DESCRIPTION
        "The status of the IDU fans 1-2 or 1-4.
         bit 1 = IDU Fan1 is faulty.
         bit 2 = IDU Fan2 is faulty.
         bit 3 = IDU Fan2 is faulty.
         bit 4 = IDU Fan2 is faulty."
        ::= { gnGenIdcStatEntry 7 }

gnGenIdcStatLeftDrawerStatus OBJECT-TYPE
        SYNTAX  INTEGER
        {
                noDrawer(2),
                drawerDown(3),
                drawerUp(4)
        }
        ACCESS  read-only
        STATUS mandatory
        DESCRIPTION
        " "
        ::= { gnGenIdcStatEntry 8 }

gnGenIdcStatRightDrawerStatus OBJECT-TYPE
        SYNTAX  INTEGER
        {
                noDrawer(2),
                drawerDown(3),
                drawerUp(4)
        }
        ACCESS  read-only
        STATUS mandatory
        DESCRIPTION
        " "
        ::= { gnGenIdcStatEntry 9 }

gnGenIdcStatHitlessSupport  OBJECT-TYPE
        SYNTAX  INTEGER {
                supported(2),
                notSupported(3)
        }
        ACCESS  read-only
        STATUS mandatory
        DESCRIPTION
    "Indication for hitless support."
        ::= { gnGenIdcStatEntry 10 }

gnGenIdcStatEowExistence  OBJECT-TYPE
        SYNTAX  INTEGER {
                exist(2),
                notExist(3)
        }
        ACCESS  read-only
        STATUS mandatory
        DESCRIPTION
    "This parameter sight physical existence of the EOW connector."
        ::= { gnGenIdcStatEntry 11 }

gnGenIdcStatEowSupport  OBJECT-TYPE
        SYNTAX  INTEGER {
                supported(2),
                notSupported(3)
        }
        ACCESS  read-only
        STATUS mandatory
        DESCRIPTION
    "Indication for EOW (cascade) support."
        ::= { gnGenIdcStatEntry 12 }

gnGenIdcStatIduPosition   OBJECT-TYPE
        SYNTAX  INTEGER {
                upper(2),
                lower(3),
                single(4)
        }
        ACCESS  read-only
        STATUS mandatory
        DESCRIPTION
    "Indication for idu position."
        ::= { gnGenIdcStatEntry 13 }

gnGenIdcStatBoardType   OBJECT-TYPE
        SYNTAX  INTEGER {
                v1(2),  
                v2(3)   
        }
        ACCESS  read-only
        STATUS mandatory
        DESCRIPTION
    "Indication for the board type."
        ::= { gnGenIdcStatEntry 14 }

gnGenIdcStatAgentIPAddress   OBJECT-TYPE
        SYNTAX  IpAddress
        ACCESS  read-only
        STATUS mandatory
        DESCRIPTION
    "Indication for the Agent IP address."
        ::= { gnGenIdcStatEntry 15 }

gnGenIdcStatInterfaceConnector   OBJECT-TYPE
        SYNTAX  INTEGER {
                notExist(2),
                oneFEplus64E1(3),
                twoFEplus64E1(4)
        }
        ACCESS  read-only
        STATUS mandatory
        DESCRIPTION
    "Indication for the interface connector type."
        ::= { gnGenIdcStatEntry 16 }

gnGenIdcStatIfTableCounter   OBJECT-TYPE
        SYNTAX  INTEGER 
        ACCESS  read-only
        STATUS mandatory
        DESCRIPTION
    	"This counter is initialize to a random number and increment on every change of the IfTable
    	(This is for NMS use)."
        ::= { gnGenIdcStatEntry 17 }

gnGeneralXTable  OBJECT-TYPE
        SYNTAX  SEQUENCE OF GnGeneralXEntry
        ACCESS  not-accessible
        STATUS mandatory
        DESCRIPTION
        ""
        ::= { gnGeneral 23 }

gnGeneralXEntry OBJECT-TYPE
        SYNTAX GnGeneralXEntry
        ACCESS  not-accessible
        STATUS mandatory
          DESCRIPTION
          ""
        INDEX { gnGenXId }
        ::= { gnGeneralXTable 1 }

GnGeneralXEntry ::=
            SEQUENCE {
        gnGenXId
                        INTEGER,
        gnGenXStandardOrg
                  INTEGER,
        gnGenXRemoteConnection
                        INTEGER,
        gnGenXLinkId
                        INTEGER,
        gnGenXModemType
                        INTEGER,
        gnGenXRadioSide
                        INTEGER,
        gnGenXSystemWorkTime
                        INTEGER,
        gnGenXOperation
                        INTEGER,
        gnGenXResetPerfMon
                        INTEGER,
        gnGenXAlarmSeverity
                        OCTET STRING,
        gnGenXCarrierSerialNumber
                        DisplayString,
        gnGenXMUXSerialNumber
                        DisplayString,
        gnGenXProductType
                        INTEGER,
        gnGenXCarrierConnector
                        INTEGER,
    gnGenXInterfacesLeds
                           OCTET STRING,
        gnGenXMultiRateMultiConsConf
                        INTEGER,
        gnGenXMultiRateMultiConsSupport
                OCTET STRING,
        gnGenXWaysideChannel
                        INTEGER,
        gnGenXWaySideLoopback
                        INTEGER,
        gnGenXSyncIdcDataBase
                        INTEGER,
        gnGenXAesEnable
                        INTEGER,
        gnGenXAesMkeyMode
                        INTEGER,
        gnGenXActNumOfInterfaceOnClass1
                        INTEGER,
        gnGenXActNumOfInterfaceOnClass2
                        INTEGER,
        gnGenXActNumOfInterfaceOnClass3
                        INTEGER,
        gnGenXEowStatus
                        INTEGER,
        gnGenXTempLicenseEnable
                        INTEGER,
        gnGenXTempLicenseTimer
                        INTEGER,
		gnGenXDefectBlocks
                        INTEGER,
		gnGenXBytesCorrected
                        INTEGER,
        gnGenXPrbsTest
						INTEGER,
        gnGenXClearCounters
						INTEGER
        }

gnGenXId OBJECT-TYPE
        SYNTAX  INTEGER
        {
                drawer1(3),
                drawer2(4)
        }
    ACCESS  read-only
           STATUS mandatory
                DESCRIPTION
              " "
        ::= { gnGeneralXEntry 1 }

gnGenXStandardOrg OBJECT-TYPE
        SYNTAX  INTEGER {
                etsi(2),
                fcc(3),
                japan(4),
                lmds(5),
                cmds(6),
                australia(7),
                other(8)
        }
        ACCESS  read-only
        STATUS mandatory
        DESCRIPTION
        "This parameter specifies which international standard is used."
        ::= { gnGeneralXEntry 2 }

gnGenXRemoteConnection OBJECT-TYPE
        SYNTAX  INTEGER {
                connected(2),
                disconnected(3)
        }
        ACCESS  read-only
        STATUS mandatory
        DESCRIPTION
        "Is the connection between the local manager and
         the remote manager."
        ::= { gnGeneralXEntry 3 }

gnGenXLinkId OBJECT-TYPE
        SYNTAX INTEGER (0..65535)
        ACCESS  read-write
        STATUS mandatory
                DESCRIPTION
                "0 for 'old' system that doesn't support the link ID.
                the user can enter values from 1 to 65535"
            DEFVAL        {0}
        ::= { gnGeneralXEntry 4 }

gnGenXModemType OBJECT-TYPE
        SYNTAX  INTEGER {
                                gn16QAM(2),
                     gn32QAM(3),
                      gn128QAM(4),
                                gn256QAM(5),
                      gn64QAM(6),
                      gn4QAM(7)
                }
        ACCESS  read-only
        STATUS mandatory
                DESCRIPTION
                "The system modem type."
        ::= { gnGeneralXEntry 5 }

gnGenXRadioSide OBJECT-TYPE
        SYNTAX  INTEGER {
                                east(2),
                     west(3)
                }
        ACCESS  read-write
        STATUS mandatory
            DEFVAL        {east}
        ::= { gnGeneralXEntry 6 }

gnGenXSystemWorkTime OBJECT-TYPE
        SYNTAX  INTEGER
        ACCESS  read-write
        STATUS mandatory
                DESCRIPTION
                "The System Work Time (hours)."
            DEFVAL        {0}
        ::= { gnGeneralXEntry 7 }

gnGenXOperation OBJECT-TYPE
                SYNTAX  INTEGER
                {
                        noOperation(2),
                        setMuxDefaultConf(3),
                        hardwareColdReset(4),
                        hardwareWarmReset(5),
                        softwareODCReset(6),
                        hardwareODCReset(7)
                }
                ACCESS  read-write
                STATUS mandatory
                DESCRIPTION
                "."
                DEFVAL { noOperation }
                ::= { gnGeneralXEntry 8 }

gnGenXResetPerfMon OBJECT-TYPE
        SYNTAX  INTEGER {
                reset(2),
                noAction(3),
                clearFastEthernetStatistics(4)
        }
        ACCESS  read-write
        STATUS mandatory
        DESCRIPTION
        "Reset performance monitoring. "
        DEFVAL { noAction }
        ::= { gnGeneralXEntry 9 }

gnGenXAlarmSeverity  OBJECT-TYPE
        SYNTAX OCTET STRING(SIZE(15))
        ACCESS  read-write
        STATUS  mandatory
    DESCRIPTION
    "This field is used only by the Ceraview management
           application Every Trap severity 4 bits.
           15 (MAJOR), 7 (MINOR), 3 (WARNING) and 1 (EVENT) options.
           The first 4 bits ODU Power supply severity,
           then the Synthesizer severity ,then Tx level then RX level
           ODU temperature, ODU loopback , IDU power supply , Cable,
           Modem, IDU temperature, IDU loopbacks, External Alarm 1,
           External Alarm 2 ,External Alarm 3, External Alarm 4,
           External Alarm 5, External Alarm 6, External Alarm 7,
           External Alarm 8, Remote connectivity, LOF, LOS, EXC, SD
           J0 mismatch and system fault."
    ::= { gnGeneralXEntry 10 }

gnGenXCarrierSerialNumber OBJECT-TYPE
        SYNTAX  DisplayString(SIZE(0..20))
        ACCESS  read-only
        STATUS mandatory
        DESCRIPTION
        "This is the carrier serial number - up to 20 characters "
        ::= { gnGeneralXEntry 11 }

gnGenXMUXSerialNumber OBJECT-TYPE
        SYNTAX  DisplayString(SIZE(0..20))
        ACCESS  read-only
        STATUS mandatory
        DESCRIPTION
        "This is the MUX serial number - up to 20 characters "
        ::= { gnGeneralXEntry 12 }

gnGenXProductType        OBJECT-TYPE
        SYNTAX  INTEGER
                {
                                accessMux                                    (2),
                            sdhRegenerator                         (3),
                                narrowBandPdhRepeater        (4),
                                accessMuxStm0                        (5),
                                plex6200                                (6),
                                adm                                                (7)
                }
    ACCESS  read-only
    STATUS  mandatory
    DESCRIPTION
        "The product type."
         ::= { gnGeneralXEntry 13 }

gnGenXCarrierConnector OBJECT-TYPE
	SYNTAX  INTEGER {
		noInterface(2),
		oneElectricalSTM1(3),
		oneFiberSTM1SingleMode(4),
		oneFiberSTM1MultiMode(5),
		twoElectricalSTM1(6),
		twoFiberSTM1SingleMode(7),
		twoFiberSTM1MultiMode(8),
		oneFEOnly(9),
		oneFEplus4E1(10),
		oneFEplus8E1(11),
		oneFEplus4T1(12),
		oneFEplus8T1(13),
		twoFEOnly(14),
		twoFEplus4E1(15),
		twoFEplus8E1(16),
		twoFEplus4T1(17),
		twoFEplus8T1(18),
		oneDS3(19),
		threeDS3(20),
		oneE3(21),
		threeE3(22),
		oneOpticalGBEOnly(23),
		oneOpticalGBEPlus8E1(24),
		oneOpticalGBEPlus8T1(25),
	  	oneElectricalGBEOnly(26),
		oneElectricalGBEPlus8E1(27),
		oneElectricalGBEPlus8T1(28),
		oneFEplus64E1(29),
		oneFEplus64T1(30),
        eightE1Only(31),
        eightT1Only(32),
		oneStm1XC(33),
		twoStm1XC(34)
	}
	ACCESS  read-only
	STATUS mandatory
	DESCRIPTION
	"For ACCESS hardware, this indicates the first (left) interface connector."
	::= { gnGeneralXEntry 14 }

gnGenXInterfacesLeds OBJECT-TYPE
        SYNTAX OCTET STRING(SIZE(4))
        ACCESS  read-only
        STATUS mandatory
        DESCRIPTION
        "The status of the Interface LEDs. For the management station use.
         Each two bits represents one led as follows: 00 - Gray, 01 - Green, 10 - Orange, 11 - Red.
         The led order: Led1 is msb 2 bits , after it led2, till led 16 - 2 lsb bits."
        ::= { gnGeneralXEntry 15 }

gnGenXMultiRateMultiConsConf        OBJECT-TYPE
        SYNTAX  INTEGER        {
                                mrmc1528                                    (1),
                            mrmc1550                             (2),
                                mrmc3156                (3),
                                mrmc3150                (4),
                                mrmc1228                    (5),
                                mrmc1540                                    (6),
                            mrmc4410                             (7),
                                mrmc4420                (8),
                                mrmc4440                (9),
                                mrmc1125                    (10),
                                mrmc2050                (11),
                                mrmc2030                (12),
                                mrmc1340                    (13)
                }
    ACCESS  read-write
    STATUS  mandatory
    DESCRIPTION
        "The Link data capacity"
         ::= { gnGeneralXEntry 16 }

gnGenXMultiRateMultiConsSupport OBJECT-TYPE
        SYNTAX OCTET STRING(SIZE(4))
        ACCESS  read-only
        STATUS mandatory
        DESCRIPTION
        ""
        ::= { gnGeneralXEntry 17 }


gnGenXWaysideChannel OBJECT-TYPE
        SYNTAX  INTEGER {
                enable(2),
                disable(3)
        }
        ACCESS  read-write
        STATUS mandatory
        DESCRIPTION
        " Enable Disable drawer wayside channel "
        DEFVAL { disable }
        ::= { gnGeneralXEntry 18 }



gnGenXWaySideLoopback OBJECT-TYPE
        SYNTAX  INTEGER {
                        noloopback(2),
                        waySideLoop(3)
        }
        ACCESS  read-write
        STATUS mandatory
        DESCRIPTION
        "This parameter controls the WAYSIDE channel loopback diagnostic operations."
        DEFVAL { noloopback }
        ::= { gnGeneralXEntry 19 }

        gnGenXSyncIdcDataBase OBJECT-TYPE
        SYNTAX  INTEGER {
                        noOperation(2),
                        idcToDrawer(3),
                        drawerToIdc(4)
        }
        ACCESS  read-write
        STATUS mandatory
        DESCRIPTION
        "."
        DEFVAL { noOperation }
        ::= { gnGeneralXEntry 20 }

        gnGenXAesEnable OBJECT-TYPE
        SYNTAX  INTEGER {
                        enable(2),
                        disable(3),
                        notSupport(4),
                        systemFailure(5)
        }
        ACCESS  read-only
        STATUS mandatory
        DESCRIPTION
        "This parameter defines encryption admin mode."
        DEFVAL { disable }
        ::= { gnGeneralXEntry 21 }

        gnGenXAesMkeyMode OBJECT-TYPE
        SYNTAX  INTEGER {
                        auto(2),
                        manual(3)
        }
        ACCESS  read-only
        STATUS mandatory
        DESCRIPTION
        "This parameter is not used."
        DEFVAL { auto }
        ::= { gnGeneralXEntry 22 }

        gnGenXActNumOfInterfaceOnClass1 OBJECT-TYPE
        SYNTAX  INTEGER (0..65535)
        ACCESS  read-only
        STATUS mandatory
        DESCRIPTION
        "This value indicates the actual number of interfaces on class 1."
        DEFVAL { 0 }
        ::= { gnGeneralXEntry 23 }

        gnGenXActNumOfInterfaceOnClass2 OBJECT-TYPE
        SYNTAX  INTEGER (0..65535)
        ACCESS  read-only
        STATUS mandatory
        DESCRIPTION
        "This value indicates the actual number of interfaces on class 2."
        DEFVAL { 0 }
        ::= { gnGeneralXEntry 24 }

        gnGenXActNumOfInterfaceOnClass3 OBJECT-TYPE
        SYNTAX  INTEGER (0..65535)
        ACCESS  read-only
        STATUS mandatory
        DESCRIPTION
        "This value indicates the actual number of interfaces on class 3."
        DEFVAL { 0 }
        ::= { gnGeneralXEntry 25 }

        gnGenXEowStatus OBJECT-TYPE
        SYNTAX  INTEGER {
                        enable(2),
                        disable(3)
        }
        ACCESS  read-write
        STATUS mandatory
        DESCRIPTION
        "Not used."
        DEFVAL { disable }
        ::= { gnGeneralXEntry 26 }

        gnGenXTempLicenseEnable OBJECT-TYPE
        SYNTAX  INTEGER {
                        enable(2),
                        disable(3),
						notSupported(4)
        }
        ACCESS  read-write
        STATUS mandatory
        DESCRIPTION
        "Set temporary license enable or disable."
        DEFVAL { disable }
        ::= { gnGeneralXEntry 27 }

        gnGenXTempLicenseTimer OBJECT-TYPE
        SYNTAX  INTEGER (0..65535)
        ACCESS  read-only
        STATUS mandatory
        DESCRIPTION
        "This value indicates the temporary license timer."
        DEFVAL { 0 }
        ::= { gnGeneralXEntry 28 }


		gnGenXDefectBlocks OBJECT-TYPE
        SYNTAX  INTEGER
        ACCESS  read-only
        STATUS mandatory
        DESCRIPTION
        "The number of defected blocks that could not be corrected by the
         FEC "
        ::= { gnGeneralXEntry 29 }

		gnGenXBytesCorrected OBJECT-TYPE
        SYNTAX  INTEGER
        ACCESS  read-only
        STATUS mandatory
        DESCRIPTION
        " Number of bytes corrected by the FEC"
        ::= { gnGeneralXEntry 30 }


gnGenXPrbsTest OBJECT-TYPE
        SYNTAX  INTEGER {
                notActive(2),
                active(3)
                }
        ACCESS  read-write
        STATUS mandatory
        DESCRIPTION
        " This parameter enable the user to activate the PRBS test."
        DEFVAL { notActive }
        ::= { gnGeneralXEntry  31 }

gnGenXClearCounters OBJECT-TYPE
        SYNTAX  INTEGER {
                noAction(2),
				clearCounters(3)
        }
        ACCESS  read-write
        STATUS mandatory
        DESCRIPTION
        " This parameter enable the user to clear the PRBS counters."
        DEFVAL { noAction }
        ::= { gnGeneralXEntry  32 }



gnGenAddAlarmExtToTraps OBJECT-TYPE
        SYNTAX  INTEGER {
                no                (2),
                yes                (3)
        }
        ACCESS  read-write
        STATUS mandatory
        DESCRIPTION
        "If chose 'yes', the Alarm Id, Origin and Unit from gnAgnCurrentAlarmTable
         will be bind to the end of each ceragon private trap."
        DEFVAL { no }
        ::= { gnGeneral 24 }

gnGenFeatureSupport OBJECT-TYPE
        SYNTAX OCTET STRING(SIZE(8))
        ACCESS  read-only
        STATUS mandatory
        DESCRIPTION
        "Inidcation for feature support. msb is for bit #1.
         The bit is set when a specific feature is support.
         Bit #1 - Tftp server support.
         Bit #2 - Cold reset support.
         Bit #3 - Severity critical for external alarm.
         Bit #4 - MRMC filter table.
         Bit #5 - NeighborIP Support Fast and DS3.
         Bit #6 - Auxiliary channel drawer routing support.
         Bit #7 - Single drawer external protection support.
         Bit #8 - dual drawer external protection not support.
         Bit #9 - Left Drawer XPIC hardware support (0 - support, 1 - not support).
         Bit #10 - Right Drawer XPIC hardware support (0 - support, 1 - not support).
         Bit #11 - Internal Protection Not Supported (0 - support, 1 - not support).
         Bit #12 - One Ws Channel Only (0 - FALSE, 1 - TRUE).
         Bit #13 - Protect option not support (0 - support, 1 - not support).
         Bit #14 - UC ethernet support (0 - not support, 1 - support).
         Bit #15 - WSC only disable (0 - enable & disable, 1 - only disable).
         Bit #16 - UC only disable (0 - enable & disable, 1 - only disable).
         Bit #17 - EOW only disable (0 - enable & disable, 1 - only disable).
		 Bit #18 - Left Drawer modem latency Not support (0 - support, 1 - not support).
		 Bit #19 - Right Drawer modem latency Not support (0 - support, 1 - not support).
		 Bit #20 - Clear PM for drawer (0 - support, 1 - not support).
		 Bit #21 - Allow Sync mode in UC#2 (0 - not allow, 1 - allow)."
                         ::= { gnGeneral 25 }

gnGeneralMrmcXTable  OBJECT-TYPE
        SYNTAX  SEQUENCE OF GnGeneralMrmcXEntry
        ACCESS  not-accessible
        STATUS mandatory
        DESCRIPTION
        ""
        ::= {gnGeneral 26}

gnGeneralMrmcXEntry  OBJECT-TYPE
                SYNTAX  GnGeneralMrmcXEntry
        ACCESS  not-accessible
        STATUS mandatory
        DESCRIPTION
            "This table indicates the supported modem configuration script for each drawer."
        INDEX { gnGenMrmcXId, gnGenMrmcXMrmcVal}
        ::= { gnGeneralMrmcXTable 1 }

GnGeneralMrmcXEntry ::=
            SEQUENCE {
        gnGenMrmcXId
                        INTEGER,
        gnGenMrmcXMrmcVal
                  INTEGER,
        gnGenMrmcXBitRate
                        INTEGER,
        gnGenMrmcXBandWidth
                        INTEGER,
        gnGenMrmcXQam
                        INTEGER
        }

gnGenMrmcXId OBJECT-TYPE
        SYNTAX  INTEGER
        {
                drawer1(3),
                drawer2(4)
        }
    ACCESS  read-only
           STATUS mandatory
    DESCRIPTION
    "Drawer number."
    ::= { gnGeneralMrmcXEntry 1 }

gnGenMrmcXMrmcVal OBJECT-TYPE
        SYNTAX  INTEGER
        ACCESS  read-only
        STATUS mandatory
        DESCRIPTION
        "This parameter specifies MRMC value."
        ::= { gnGeneralMrmcXEntry 2 }

gnGenMrmcXBitRate OBJECT-TYPE
        SYNTAX  INTEGER
        ACCESS  read-only
        STATUS mandatory
        DESCRIPTION
        "This parameter specifies transfer bit rate."
        ::= { gnGeneralMrmcXEntry 3 }

gnGenMrmcXBandWidth OBJECT-TYPE
        SYNTAX INTEGER
        ACCESS  read-only
        STATUS mandatory
                DESCRIPTION
                "This parameter specifies channel band width."
        ::= { gnGeneralMrmcXEntry 4 }

gnGenMrmcXQam OBJECT-TYPE
        SYNTAX  INTEGER
        ACCESS  read-only
        STATUS mandatory
                DESCRIPTION
                "This parameter specifies modem qam."
        ::= { gnGeneralMrmcXEntry 5 }

gnGenDrawerXTable  OBJECT-TYPE
        SYNTAX  SEQUENCE OF GnGenDrawerXEntry
        ACCESS  not-accessible
        STATUS mandatory
        DESCRIPTION
        "This table indicates drawer x."
        ::= { gnGeneral 27 }

gnGenDrawerXEntry OBJECT-TYPE
        SYNTAX GnGenDrawerXEntry
        ACCESS  not-accessible
        STATUS mandatory
          DESCRIPTION
          "Entry containing drawer x namd and id."
        INDEX { gnGenDrawerXId}
        ::= { gnGenDrawerXTable 1 }

GnGenDrawerXEntry ::=
            SEQUENCE {
        gnGenDrawerXId
             INTEGER,
    gnGenDrawerXName
                    DisplayString (SIZE(0..20)),
        gnGenDrawerXSlot1Status
             INTEGER,
        gnGenDrawerXSlot2Status
             INTEGER,
        gnGenDrawerXDeviceLeds
                           OCTET STRING,
        gnGenDrawerXInternalCommunication
                           OCTET STRING,
        gnGenDrawerXDeviceIDUStatus
                           OCTET STRING
    }

gnGenDrawerXId OBJECT-TYPE
        SYNTAX  INTEGER
        {
                drawer1(3),
                drawer2(4)
        }
        ACCESS  read-only
           STATUS mandatory
        DESCRIPTION
              "This value indicates the drawer's id"
        ::= { gnGenDrawerXEntry 1 }

gnGenDrawerXName OBJECT-TYPE
        SYNTAX  DisplayString (SIZE(0..20))
        ACCESS  read-write
           STATUS mandatory
        DESCRIPTION
              "This value indicates the drawer's name"
        ::= { gnGenDrawerXEntry 2 }

gnGenDrawerXSlot1Status OBJECT-TYPE
        SYNTAX  INTEGER {
                notExist(2),
                powerOff(3),
                powerOn(4),
				dbReady(5)
        }
        ACCESS  read-only
        STATUS mandatory
        DESCRIPTION
        "notExist - board not exist.
         powerOff - board inserted and power off.
         powerOn - board inserted and power on.
         dbReady - board is power on and DB ready."
        DEFVAL { notExist }
        ::= { gnGenDrawerXEntry 3 }

gnGenDrawerXSlot2Status OBJECT-TYPE
        SYNTAX  INTEGER {
                notExist(2),
                powerOff(3),
                powerOn(4),
				dbReady(5)
        }
        ACCESS  read-only
        STATUS mandatory
        DESCRIPTION
        "notExist - board not exist.
         powerOff - board inserted and power off.
         powerOn - board inserted and power on.
         dbReady - board is power on and DB ready."
        DEFVAL { notExist }
        ::= { gnGenDrawerXEntry 4 }

gnGenDrawerXDeviceLeds OBJECT-TYPE
        SYNTAX OCTET STRING(SIZE(3))
        ACCESS  read-only
        STATUS mandatory
        DESCRIPTION
        "The status of the IDU front panel LEDs. For the management station use. "
        ::= { gnGenDrawerXEntry 5 }

gnGenDrawerXInternalCommunication  OBJECT-TYPE
        SYNTAX  OCTET STRING (SIZE(1))
        ACCESS  read-only
        STATUS mandatory
        DESCRIPTION
        "The status of internal communication problem
         bit 1 = 1: between main CPU and ODU CPU.
         bit 2 = 1: between main CPU and MUX CPU.
         bit 3 = 1: between master main CPU and slave main CPU."
        ::= { gnGenDrawerXEntry 6 }

gnGenDrawerXDeviceIDUStatus  OBJECT-TYPE
        SYNTAX  OCTET STRING (SIZE(4))
        ACCESS  read-only
        STATUS mandatory
        DESCRIPTION
        "IDU status reported with this parameter. Bit1 is MSB.
                 The bit is set when a fault occurs. The bit is
        cleared when the fault clears.

         bit 1  = Power status
         bit 2  = Cable open status
         bit 3  = Cable short status
         bit 4  = Modem Lock status
         bit 5  = Temperature status
         bit 6  = No signal from ODU (Phos only)
         bit 7  = loopback status
         bit 8  = External alarm 1 status
         bit 9  = External alarm 2 status
         bit 10 = External alarm 3 status
         bit 11 = External alarm 4 status
         bit 12 = External alarm 5 status
         bit 13 = External alarm 6 status
         bit 14 = External alarm 7 status
         bit 15 = External alarm 8 status
         bit 16 = Remote connectivity status.
         bit 17 = Inner communication status.
         bit 18 = Link ID mismatch status.
         bit 19 = Configuration mismatch status.
         bit 20 = Shelf Id mismatch status (Phos only).
         bit 21 = General HW failure.
         bit 22 = No power to MUX board.
         bit 23 = No power to MODEM board.
         bit 24 = IDC disk firmware cinfiguration mismatch.
         bit 25 = Modem configuration file.
         bit 26 = Wayside channel E1/T1 LOS
         bit 27 = loopback on Wayside channel
         "
        ::= { gnGenDrawerXEntry 7 }


gnCluster OBJECT IDENTIFIER ::= { gnGeneral 28 }

cluster OBJECT IDENTIFIER ::= { gnCluster 1}

clusterSystemType OBJECT-TYPE
        SYNTAX  INTEGER {
                unknown(2),
                p1500(3),
                t3200(4)
        }
    ACCESS  read-only
           STATUS mandatory
    DESCRIPTION
    "This value indicates the system type: Phophorus, Avalon or Unknown Backplane"
    ::= { cluster 1 }

clusterNumOfSubRacks OBJECT-TYPE
        SYNTAX  INTEGER (1..3)
    ACCESS  read-only
           STATUS mandatory
    DESCRIPTION
    "This value indicates the number of subrack, 1st phase supporsts only 1"
    ::= { cluster 3 }

clusterSubRackNum OBJECT-TYPE
        SYNTAX  INTEGER (0..3)
    ACCESS  read-only
           STATUS mandatory
    DESCRIPTION
    "This value indicates the subrack's number"
    ::= { cluster 4 }

clusterFloorNum OBJECT-TYPE
        SYNTAX  INTEGER (0..9)
    ACCESS  read-only
           STATUS mandatory
    DESCRIPTION
    "This value indicates the subrack's number"
    ::= { cluster 5 }

clusterIPBase OBJECT-TYPE
        SYNTAX  IpAddress
    ACCESS  read-only
           STATUS mandatory
    DESCRIPTION
    "This value indicates the Cluster IP base "
    ::= { cluster 6 }

clusterIDCRole OBJECT-TYPE
        SYNTAX  INTEGER {
                clusterPrime(2),
                member(3),
                subrackManager(4)
        }
    ACCESS  read-only
           STATUS mandatory
    DESCRIPTION
    "This value indicates - ClusterPrime - 2nd floor of 1st rack, SubRackManager - 2nd floor of other racks."
    ::= { cluster 7 }

clusterPrimeIPAddress OBJECT-TYPE
        SYNTAX  IpAddress
    ACCESS  read-only
           STATUS mandatory
    DESCRIPTION
    "This value enable CV/PV to know the server IP even if it is not connected"
    ::= { cluster 8 }

clusterPeerIPLastChangeTime OBJECT-TYPE
        SYNTAX  INTEGER
    ACCESS  read-only
           STATUS mandatory
    DESCRIPTION
    "This value indicates The last time when the Peer IP Table changed"
    ::= { cluster 9 }

addressesTable  OBJECT-TYPE
        SYNTAX  SEQUENCE OF AddressesEntry
        ACCESS  not-accessible
        STATUS mandatory
        DESCRIPTION
        "This table indicates the cluster's IP Addresses."
        ::= { gnCluster 2 }

addressesEntry OBJECT-TYPE
        SYNTAX AddressesEntry
        ACCESS  not-accessible
        STATUS mandatory
          DESCRIPTION
          "Entry containing the cluster's IP Addresses."
        INDEX { addressesPeerIPId}
        ::= { addressesTable 1 }

AddressesEntry ::=
            SEQUENCE {
        addressesPeerIPId
             INTEGER,
    addressesPeerIPAddress
                    IpAddress
    }

addressesPeerIPId OBJECT-TYPE
        SYNTAX  INTEGER (1..9)
        ACCESS  read-only
           STATUS mandatory
        DESCRIPTION
              "This value indicates the peer IP id"
        ::= { addressesEntry 1 }

addressesPeerIPAddress OBJECT-TYPE
        SYNTAX  IpAddress
        ACCESS  read-only
        STATUS mandatory
        DESCRIPTION
        "This value indicates the  IP address of a Server/Client. "
        ::= { addressesEntry 2 }

primeIDC OBJECT IDENTIFIER ::= { gnCluster 3}

primeIDCAutoInternalClockDistribution OBJECT-TYPE
        SYNTAX  INTEGER {
                enable(2),
                disable(3)
        }
    ACCESS  read-write
           STATUS mandatory
    DESCRIPTION
    "This value indicates whether the internal clock distribution is enabled or disabled. "
    ::= { primeIDC 1 }

primeIDCSynchronizeClockInCluster OBJECT-TYPE
        SYNTAX  INTEGER {
                noaction(2),
                synchronize(3)
        }
    ACCESS  read-write
           STATUS mandatory
    DESCRIPTION
    "This value indicates whether to synchronize the clock in the cluster. "
    ::= { primeIDC 2 }

backplaneSlotMappingTable  OBJECT-TYPE
        SYNTAX  SEQUENCE OF BackplaneSlotMappingEntry
        ACCESS  not-accessible
        STATUS mandatory
        DESCRIPTION
        "This table indicates the cluster's IP Addresses."
        ::= { gnCluster 4 }

backplaneSlotMappingEntry OBJECT-TYPE
        SYNTAX BackplaneSlotMappingEntry
        ACCESS  not-accessible
        STATUS mandatory
          DESCRIPTION
          "Entry containing the cluster's IP Addresses."
        INDEX { backplaneSlotMappingSubrackId, backplaneSlotMappingFloorId, backplaneSlotMappingDrawerId, backplaneSlotMappingSubDrawerId}
        ::= { backplaneSlotMappingTable 1 }

BackplaneSlotMappingEntry ::=
            SEQUENCE {
        backplaneSlotMappingSubrackId
             INTEGER (1..3),
        backplaneSlotMappingFloorId
             INTEGER (1..100),
        backplaneSlotMappingDrawerId
             INTEGER (1..3),
        backplaneSlotMappingSubDrawerId
             INTEGER (1..2),
        backplaneSlotMappingUnitType
             INTEGER,
        backplaneSlotMappingUnitNumber
             INTEGER (1..15),
        backplaneSlotMappingUnitIndex
             INTEGER
    }

backplaneSlotMappingSubrackId OBJECT-TYPE
        SYNTAX  INTEGER (1..3)
        ACCESS  read-only
           STATUS mandatory
        DESCRIPTION
              "This value indicates the subrack index. "
        ::= { backplaneSlotMappingEntry 1 }

backplaneSlotMappingFloorId OBJECT-TYPE
        SYNTAX  INTEGER (1..100)
        ACCESS  read-only
           STATUS mandatory
        DESCRIPTION
              "This value indicates the floor id
                          The 4U floor index (upper) will be 99. "
        ::= { backplaneSlotMappingEntry 2 }

backplaneSlotMappingDrawerId OBJECT-TYPE
        SYNTAX  INTEGER (1..3)
        ACCESS  read-only
           STATUS mandatory
        DESCRIPTION
              "For floors 1-3: IDC=1, Drawer 1=2, Drwaer2 =3. For 4U floor (floor #99), Aux=1, Power=2. "
        ::= { backplaneSlotMappingEntry 3 }

backplaneSlotMappingSubDrawerId OBJECT-TYPE
        SYNTAX  INTEGER (1..2)
        ACCESS  read-only
           STATUS mandatory
        DESCRIPTION
              "This value indicates the sub drawer id
                           IDC, Drawer 1 & 2 will be only 1. XC main (up) will be 1 and XC backup (lower) will be 2. "
        ::= { backplaneSlotMappingEntry 4 }

backplaneSlotMappingUnitType OBJECT-TYPE
        SYNTAX  INTEGER {
                idc(2),
                odu(3),
                mux(4),
                modem(5),
                drawer(6),
                unknown(7),
                none(8),
                xc(9),
                auxInterface(10),
                power(11)
        }
        ACCESS  read-only
           STATUS mandatory
        DESCRIPTION
              "The values are the same as in gnAgnCurrentAlarm Unit. "
        ::= { backplaneSlotMappingEntry 5 }

backplaneSlotMappingUnitNumber OBJECT-TYPE
        SYNTAX  INTEGER (1..15)
        ACCESS  read-only
           STATUS mandatory
        DESCRIPTION
              "This value indicates the unit number. "
        ::= { backplaneSlotMappingEntry 6 }

backplaneSlotMappingUnitIndex OBJECT-TYPE
        SYNTAX  INTEGER
        ACCESS  read-only
           STATUS mandatory
        DESCRIPTION
              "This value indicates the unit number. "
        ::= { backplaneSlotMappingEntry 7 }

gnSubrack OBJECT IDENTIFIER ::= { gnGeneral 29 }

powerInputTable  OBJECT-TYPE
        SYNTAX  SEQUENCE OF PowerInputEntry
        ACCESS  not-accessible
        STATUS mandatory
        DESCRIPTION
        "This table indicates the Power Input."
        ::= { gnSubrack 1 }

powerInputEntry OBJECT-TYPE
        SYNTAX PowerInputEntry
        ACCESS  not-accessible
        STATUS mandatory
          DESCRIPTION
          "Entry containing the Power Input."
        INDEX { powerInputId}
        ::= { powerInputTable 1 }

PowerInputEntry ::=
            SEQUENCE {
        powerInputId
             INTEGER (1..6),
        powerInputAdmin
             INTEGER,
        powerInputStatus
             INTEGER,
        powerInputLedStatus
             OCTET STRING (SIZE(1))
    }

powerInputId OBJECT-TYPE
        SYNTAX  INTEGER (1..6)
    ACCESS  read-only
           STATUS mandatory
    DESCRIPTION
    "This value indicates the power input Id. "
    ::= { powerInputEntry 1 }

powerInputAdmin OBJECT-TYPE
        SYNTAX  INTEGER {
                enable(2),
                disable(3)
        }
    ACCESS  read-write
           STATUS mandatory
    DESCRIPTION
    "This value indicates whether the power input Admin is enables or disabled. "
    ::= { powerInputEntry 2 }

powerInputStatus OBJECT-TYPE
        SYNTAX  INTEGER {
                notexist(2),
                unknown(3),
                down(4),
                up(5)
        }
    ACCESS  read-only
           STATUS mandatory
    DESCRIPTION
    "This value indicates whether the power input is up or down, Notexist when power input card not exist. unknown when no A-Aux."
    ::= { powerInputEntry 3 }

powerInputLedStatus OBJECT-TYPE
        SYNTAX  OCTET STRING (SIZE(1))
    ACCESS  read-only
           STATUS mandatory
    DESCRIPTION
    "This value, Led1 is MSB 2 bits.
         Each two bits represents one led:00 - Gray,01 - Green, 10 - Orange, 11 - Red. "
    ::= { powerInputEntry 4 }

auxiliaryDrawer OBJECT IDENTIFIER ::= { gnSubrack 2 }

auxiliaryDrawerAuxCardType OBJECT-TYPE
        SYNTAX  INTEGER {
                na(2),
                v1(3)
        }
    ACCESS  read-only
           STATUS mandatory
    DESCRIPTION
    "This value indicates whether the Auxiliary Card type."
    ::= { auxiliaryDrawer 1 }

auxiliaryDrawerLedsStatus OBJECT-TYPE
        SYNTAX  OCTET STRING (SIZE(4))
    ACCESS  read-only
           STATUS mandatory
    DESCRIPTION
    "This value, Led16 is MSB 2 bits, Led1 is LSB 2 bits.
         Each two bits represents one led:00 - Gray,01 - Green, 10 - Orange, 11 - Red.
		 Led 1:  Status of WSC/UC Ethernet (upper connector, left side).
		 Led 2:  Status of WSC/UC Ethernet (upper connector, right side).
		 Led 3:  Status of WSC/UC Ethernet (lower connector, left side).
		 Led 4:  Status of WSC/UC Ethernet (lower connector, right side).
		 Led 5:  Reserved - Status of managment link (upper connector).
		 Led 6:  Reserved - Status of managment activity (upper connector).
		 Led 7:  Reserved - Status of managment link (lower connector).
		 Led 8:  Reserved - Status of managment activity (lower connector).
		 Led 9:  Status of WSC E1/T1 (upper connector, left side).
		 Led 10: Status of WSC E1/T1 (upper connector, right side).
		 Led 11: Status of WSC E1/T1 (lower connector, left side).
		 Led 12: Status of WSC E1/T1 (lower connector, right side).
		 Led 13: Reserved - Status of external fans (upper connector, left side).
		 Led 14: Reserved - Status of external fans (upper connector, right side).
		 Led 15: Reserved - Status of EOW Chaining (lower connector, left side).
		 Led 16: Reserved - Status of EOW Chaining (lower connector, right side)."
    ::= { auxiliaryDrawer 2 }

auxiliaryDrawerBoardHWVersion OBJECT-TYPE
        SYNTAX  INTEGER
    ACCESS  read-only
           STATUS mandatory
    DESCRIPTION
    "This value indicates the EEPROM value."
    ::= { auxiliaryDrawer 3 }

auxiliaryDrawerBoardFWVersion OBJECT-TYPE
        SYNTAX  DisplayString (SIZE(0..15))
    ACCESS  read-only
           STATUS mandatory
    DESCRIPTION
    "This value indicates the Register value ."
    ::= { auxiliaryDrawer 4 }

auxiliaryDrawerBoardPostResetFWVersion OBJECT-TYPE
        SYNTAX  DisplayString (SIZE(0..15))
    ACCESS  read-only
           STATUS mandatory
    DESCRIPTION
    "This value indicates the Register value ."
    ::= { auxiliaryDrawer 5 }

auxiliaryDrawerSerialNumber OBJECT-TYPE
        SYNTAX  DisplayString (SIZE(0..20))
    ACCESS  read-only
           STATUS mandatory
    DESCRIPTION
    "This value indicates the EEPROM value."
    ::= { auxiliaryDrawer 6 }

auxiliaryDrawerBoardReset OBJECT-TYPE
        SYNTAX  INTEGER {
                noaction(2),
                reset(3)
        }
    ACCESS  read-write
           STATUS mandatory
    DESCRIPTION
    "This value indicates whether to reset board."
    ::= { auxiliaryDrawer 7 }

auxiliaryDrawerOrderWireChaining OBJECT-TYPE
        SYNTAX  INTEGER {
                enable(2),
                disable(3)
        }
    ACCESS  read-write
           STATUS mandatory
    DESCRIPTION
    "This value indicates whether the Order Wire chaining is enables or disabled. "
    ::= { auxiliaryDrawer 8 }

xcDrawerTable  OBJECT-TYPE
        SYNTAX  SEQUENCE OF XCDrawerEntry
        ACCESS  not-accessible
        STATUS mandatory
        DESCRIPTION
        "This table indicates the XC Drawer."
        ::= { gnSubrack 3 }

xcDrawerEntry OBJECT-TYPE
        SYNTAX XCDrawerEntry
        ACCESS  not-accessible
        STATUS mandatory
          DESCRIPTION
          "Entry containing the XC Drawer."
        INDEX { xcDrawerXCId}
        ::= { xcDrawerTable 1 }

XCDrawerEntry ::=
            SEQUENCE {
        xcDrawerXCId
             INTEGER (1..6),
        xcDrawerLedsStatus
             OCTET STRING (SIZE(1)),
        xcDrawerBoardHWVersion
                         INTEGER,
        xcDrawerBoardFWVersion
                         DisplayString (SIZE(0..20)),
        xcDrawerBoardPostResetFWVersion
                         DisplayString (SIZE(0..20)),
        xcDrawerSerialNumber
                         DisplayString (SIZE(0..20)),
        xcDrawerResetXCBoard
             INTEGER,
        xcDrawerXCSelfTestResult
             INTEGER,
        xcDrawerXCActivityRole
             INTEGER,
        xcDrawerSyncIdcDataBase
             INTEGER,
        xcDrawerXCConnector
             INTEGER
   }

xcDrawerXCId OBJECT-TYPE
        SYNTAX  INTEGER (1..6)
    ACCESS  read-only
           STATUS mandatory
    DESCRIPTION
    "This value, 1-2 for 1st rack, 3-4 for 2nd, 5-6 for 3rdy. "
    ::= { xcDrawerEntry 1 }

xcDrawerLedsStatus OBJECT-TYPE
        SYNTAX  OCTET STRING (SIZE(1))
    ACCESS  read-only
           STATUS mandatory
    DESCRIPTION
    "This value, Led1 is MSB 2 bits, Led4 is LSB .
         Each two bits represents one led:00 - Gray,01 - Green, 10 - Orange, 11 - Red. "
    ::= { xcDrawerEntry 2 }

xcDrawerBoardHWVersion OBJECT-TYPE
        SYNTAX  INTEGER
    ACCESS  read-only
           STATUS mandatory
    DESCRIPTION
    "This value indicates the EEPROM value."
    ::= { xcDrawerEntry 3 }

xcDrawerBoardFWVersion OBJECT-TYPE
        SYNTAX  DisplayString (SIZE(0..20))
    ACCESS  read-only
           STATUS mandatory
    DESCRIPTION
    "This value indicates the Register value ."
    ::= { xcDrawerEntry 4 }

xcDrawerBoardPostResetFWVersion OBJECT-TYPE
        SYNTAX  DisplayString (SIZE(0..20))
    ACCESS  read-only
           STATUS mandatory
    DESCRIPTION
    "This value indicates the Register value ."
    ::= { xcDrawerEntry 5 }

xcDrawerSerialNumber OBJECT-TYPE
        SYNTAX  DisplayString (SIZE(0..20))
    ACCESS  read-only
           STATUS mandatory
    DESCRIPTION
    "This value indicates the EEPROM value."
    ::= { xcDrawerEntry 6 }

xcDrawerResetXCBoard OBJECT-TYPE
        SYNTAX  INTEGER {
                noaction(2),
                reset(3)
        }
    ACCESS  read-write
           STATUS mandatory
    DESCRIPTION
    "This value indicates whether to reset XC."
    ::= { xcDrawerEntry 7 }

xcDrawerXCSelfTestResult OBJECT-TYPE
        SYNTAX  INTEGER {
                passed(2),
                failed(3)
        }
    ACCESS  read-only
           STATUS mandatory
    DESCRIPTION
    "This value indicates the XC self test result."
    ::= { xcDrawerEntry 8 }

xcDrawerXCActivityRole OBJECT-TYPE
        SYNTAX  INTEGER {
                active(2),
                standby(3)
        }
    ACCESS  read-only
           STATUS mandatory
    DESCRIPTION
    "This value indicates the XC activity role."
    ::= { xcDrawerEntry 9 }

xcDrawerSyncIdcDataBase OBJECT-TYPE
        SYNTAX  INTEGER {
                        noOperation(2),
                        idcToXC(3),
                        xcToIdc(4)
        }
        ACCESS  read-write
        STATUS mandatory
        DESCRIPTION
        "."
        DEFVAL { noOperation }
        ::= { xcDrawerEntry 10 }

xcDrawerXCConnector OBJECT-TYPE
        SYNTAX  INTEGER {
                oneStm1XC(2)
        }
    ACCESS  read-only
           STATUS mandatory
    DESCRIPTION
    "This value indicates the XC activity role."
    ::= { xcDrawerEntry 11 }

gnGenCarrierXTable  OBJECT-TYPE
        SYNTAX  SEQUENCE OF GnGenCarrierXEntry
        ACCESS  not-accessible
        STATUS mandatory
        DESCRIPTION
        "This table indicates carrier x."
        ::= { gnGeneral 30 }

gnGenCarrierXEntry OBJECT-TYPE
        SYNTAX GnGenCarrierXEntry
        ACCESS  not-accessible
        STATUS mandatory
                  DESCRIPTION
                  "Entry of carrier x."
        INDEX { gnGenCarrierXId}
        ::= { gnGenCarrierXTable 1 }

GnGenCarrierXEntry ::=
            SEQUENCE {
        gnGenCarrierXId
             INTEGER,
        gnGenCarrierXResetPerfMon
             INTEGER,
        gnGenCarrierXSyncIdcDataBase
             INTEGER
    }

gnGenCarrierXId OBJECT-TYPE
        SYNTAX  INTEGER
        {
                carrier1(3),
                carrier2(4)
        }
    ACCESS  read-only
           STATUS mandatory
    DESCRIPTION
    "This value indicates the carrier id"
    ::= { gnGenCarrierXEntry 1 }

gnGenCarrierXResetPerfMon OBJECT-TYPE
        SYNTAX  INTEGER {
                reset(2),
                noAction(3)
        }
        ACCESS  read-write
        STATUS mandatory
        DESCRIPTION
        "Reset performance monitoring."
        DEFVAL { noAction }
        ::= { gnGenCarrierXEntry 2 }

gnGenCarrierXSyncIdcDataBase OBJECT-TYPE
        SYNTAX  INTEGER {
                        noOperation(2),
                        idcToDrawer(3),
                        drawerToIdc(4)
        }
        ACCESS  read-write
        STATUS mandatory
        DESCRIPTION
        "idcToDrawer - copy configuration from the IDC disk to the HW (this operation istraffic effected).
         drawerToIdc - copy configuration from HW to IDC disk.
         this operation used to clear User Configuration Mismatch alarm."
        DEFVAL { noOperation }
        ::= { gnGenCarrierXEntry 3 }

--*******************************************************************


-- This group should contain all the MIB support for
-- Managers table, Trap masks and so on...
gnAgn  OBJECT IDENTIFIER ::= { gnSystem 2}

gnAgnMgrTable  OBJECT-TYPE
        SYNTAX  SEQUENCE OF GnAgnMgrEntry
        ACCESS  not-accessible
        STATUS mandatory
        DESCRIPTION
        "This table indicates the managers list that will receive traps."
        ::= { gnAgn 1 }

gnAgnMgrEntry OBJECT-TYPE
        SYNTAX GnAgnMgrEntry
        ACCESS  not-accessible
        STATUS mandatory
          DESCRIPTION
          "Entry containing the managers IP addresses and the trap filter options."
        INDEX { gnAgnMgrId}
        ::= { gnAgnMgrTable 1 }

GnAgnMgrEntry ::=
            SEQUENCE {
        gnAgnMgrId
             INTEGER,
               gnAgnMgrIP
                    IpAddress,
        gnAgnMgrAlarmGroupMask
             OCTET STRING,
        gnAgnMgrSeverityFilter
             OCTET STRING,
        gnAgnMgrTrapPort
                 INTEGER
    }

gnAgnMgrId OBJECT-TYPE
        SYNTAX  INTEGER
        ACCESS  read-only
           STATUS mandatory
        DESCRIPTION
              "This value indicates an index of a specific manager"
        ::= { gnAgnMgrEntry 1 }

gnAgnMgrIP OBJECT-TYPE
        SYNTAX  IpAddress
        ACCESS  read-write
        STATUS mandatory
        DESCRIPTION
        "This value indicates the  managers IP address.
           WRITE an IP address of all zeroes (0.0.0.0) will remove the entry. "
        ::= { gnAgnMgrEntry 2 }


gnAgnMgrAlarmGroupMask OBJECT-TYPE
        SYNTAX  OCTET STRING (SIZE(2))
        ACCESS  read-write
        STATUS mandatory
        DESCRIPTION
              "bit mask .1 is 'send a trap' 0 is 'dont send a trap'.
         The list of alarms from MSB to LSB is:
         bit 1 = Power Supply Alarm
               bit 2 = Cable Alarm
                 bit 3 = Temperature Alarm
                 bit 4 = External Alarm
                 bit 5 = Radio Alarm
                 bit 6 = Modem Alarm
                 bit 7 = Line Alarm
                 bit 8 = SDH Alarm
                 bit 9 = BER Alarm
                 bit 10 = System fault Alarm
                 bit 11 = Maintenance Alarm
                 If this field is 0, only standard traps will be sent to the manager"
        ::= { gnAgnMgrEntry 3 }

gnAgnMgrSeverityFilter OBJECT-TYPE
        SYNTAX  OCTET STRING (SIZE(1))
        ACCESS  read-write
        STATUS mandatory
        DESCRIPTION
              "This is a bit mask value for masking traps according to its severity.
               There is a bit for each severity. If the relevant bit is on (1), then
                 the Agent will send traps with this severity, and it won't send if the
                 bit is off (0).
         The list of bits from LSB to MSB:
         bit 1 (LSB) = Event.
         bit 2       = Warning.
         bit 3       = Minor.
                 bit 4       = Major.
                 bit 5 (MSB) = Critical."
        ::= { gnAgnMgrEntry 4 }


gnAgnMgrTrapPort        OBJECT-TYPE
        SYNTAX  INTEGER (70..65535)
        ACCESS  read-write
        STATUS mandatory
        DESCRIPTION
              "The Port for sending the trap for each manager (possible values: 70-65535)"
                DEFVAL { 162 }
        ::= { gnAgnMgrEntry 5 }


gnAgnLogFileData  OBJECT IDENTIFIER  ::= { gnAgn 2 }

gnAgnLogFileMaxEntries OBJECT-TYPE
        SYNTAX  INTEGER
        ACCESS  read-only
           STATUS mandatory
        DESCRIPTION
              "The maximum number of entries. "
        ::= { gnAgnLogFileData 1 }

gnAgnLogFileValidEntries OBJECT-TYPE
        SYNTAX  INTEGER
        ACCESS  read-only
           STATUS mandatory
        DESCRIPTION
              "This is the number of valid entries in the current logfile.
               When this value exceeds 70% of capacity (100 entries),
               the management station should store the file in its hard
disk.
                           If the management station is not active, the MIB will display up to
100
                           recent logfile events"
        ::= { gnAgnLogFileData 2 }

gnAgnLogFileAction OBJECT-TYPE
        SYNTAX  INTEGER {
                clear(2),
                save(3),
                saveAndClear(4),
                noAction(5)
        }
        ACCESS  read-write
        STATUS mandatory
        DESCRIPTION
        "This attribute allows for logfile actions,
        CLEARing the logfile and/or SAVING the logfile."
        DEFVAL { noAction }
        ::= { gnAgnLogFileData 3 }


gnAgnLogFileTable  OBJECT-TYPE
        SYNTAX  SEQUENCE OF GnAgnLogFileEntry
        ACCESS  not-accessible
        STATUS mandatory
        DESCRIPTION
        "This table is the agents alarm and event log file."
        ::= { gnAgnLogFileData 4 }

gnAgnLogFileEntry OBJECT-TYPE
        SYNTAX GnAgnLogFileEntry
        ACCESS  not-accessible
        STATUS mandatory
          DESCRIPTION
          "Entry containing the agents alarm and event log file."
        INDEX { gnAgnLogFileId}
        ::= { gnAgnLogFileTable 1 }

GnAgnLogFileEntry ::=
            SEQUENCE {
        gnAgnLogFileId
             INTEGER,
        gnAgnLogFileValid
             INTEGER,
               gnAgnLogFileDate
                    DisplayString,
        gnAgnLogFileTime
                    DisplayString,
        gnAgnLogFileSeverity
              INTEGER,
        gnAgnLogFileText
             DisplayString,
        gnAgnLogFileDeviceCelsiusTemp
             INTEGER,
        gnAgnLogFileDevicePowerSupply
             OCTET STRING,
        gnAgnLogFileInternalCommunication
             OCTET STRING,
        gnAgnLogFileDeviceFanStatus
             OCTET STRING,
        gnAgnLogFileDeviceODUStatus
             OCTET STRING,
        gnAgnLogFileDeviceIDUStatus
             OCTET STRING,
        gnAgnLogFileOduCelsiusTemp
          INTEGER,
            gnAgnLogFileOduReceiveLevel
                 INTEGER,
        gnAgnLogFileOduSynthesizerVCOLock
             OCTET STRING,
        gnAgnLogFileOduPowerSupply
             OCTET STRING,
        gnAgnLogFileLineBERCur
             INTEGER,
        gnAgnLogFileRadioBERCur
             INTEGER,
        gnAgnLogFileModStatus
             INTEGER,
        gnAgnLogFileDemodStatus
             INTEGER,
        gnAgnLogFileLastDemodDefectBlocks
             INTEGER,
        gnAgnLogFileLastDemodBytesCorrected
             INTEGER,
        gnAgnLogFileLastDemodBlocksCorrected
             INTEGER,
        gnAgnLogFileUniqueId
             INTEGER,
        gnAgnLogFileSource
             INTEGER,
        gnAgnLogFileTimeT
                INTEGER
    }

gnAgnLogFileId OBJECT-TYPE
        SYNTAX  INTEGER
        ACCESS  read-only
           STATUS mandatory
        DESCRIPTION
              "This value indicates the index of an alarm logfile entry.
Entry 1 is the most recent logfile
                          event"
        ::= { gnAgnLogFileEntry 1 }

gnAgnLogFileValid OBJECT-TYPE
        SYNTAX  INTEGER { valid(2), notvalid(3) }
        ACCESS  read-only
           STATUS mandatory
        DESCRIPTION
              "This value indicates the validity of the indexed alarm logfile entry.
                           a VALID log entry is (2) and an INVALID entry is (3)."
        ::= { gnAgnLogFileEntry 2 }

gnAgnLogFileDate OBJECT-TYPE
        SYNTAX  DisplayString
        ACCESS  read-only
        STATUS mandatory
        DESCRIPTION
        "This field is the date the alarm occurred, formatted as YYYY-MM-DD.
           YYYY represents the year, MM the month and DD -the day. "
        ::= { gnAgnLogFileEntry 3 }


gnAgnLogFileTime OBJECT-TYPE
        SYNTAX  DisplayString
        ACCESS  read-only
        STATUS mandatory
        DESCRIPTION
        "This field is the hour the alarm occurred - format HH:MM.
         HH - Hour, MM - minute"
        ::= { gnAgnLogFileEntry 4 }

gnAgnLogFileSeverity OBJECT-TYPE
       SYNTAX INTEGER {
                event(1),
                warning(3),
                minor(7),
                major(15),
                critical(31)
                }
       ACCESS  read-only
       STATUS  mandatory
       DESCRIPTION
              "This value indicates the severity of the alarm,
                31 for CRITICAL, 15 for MAJOR, 7 for MINOR, 3 for WARNING and 1 for EVENT. "
        ::= { gnAgnLogFileEntry 5 }

gnAgnLogFileText OBJECT-TYPE
        SYNTAX  DisplayString
        ACCESS  read-only
        STATUS mandatory
        DESCRIPTION
        "This field describes the alarm that occurred. Max length 40
characters."
        ::= { gnAgnLogFileEntry 6 }

gnAgnLogFileDeviceCelsiusTemp OBJECT-TYPE
        SYNTAX  INTEGER
        ACCESS  read-only
        STATUS mandatory
        DESCRIPTION
        "This is the temperature of the IDU in degrees Celsius,
        during the alarm acceptance. "
        ::= {gnAgnLogFileEntry 7 }


gnAgnLogFileDevicePowerSupply OBJECT-TYPE
        SYNTAX OCTET STRING(SIZE(1))
        ACCESS  read-only
        STATUS mandatory
        DESCRIPTION
        "This is the Power supply status of the IDU, during the alarm
acceptance
        bit 1 on = 3.3V faulty
        bit 2 on = -5V faulty
        bit 3 on = 5V faulty.
        bit 4 on = +8V faulty "
        ::= {gnAgnLogFileEntry 8 }



gnAgnLogFileInternalCommunication OBJECT-TYPE
        SYNTAX  OCTET STRING (SIZE(1))
        ACCESS  read-only
        STATUS mandatory
        DESCRIPTION
        "This is the internal communication status of the IDU, during the alarm
acceptance
         bit 1 = 1: between main CPU and ODU CPU.
         bit 2 = 1: between main CPU and MUX CPU.
         bit 3 = 1: between master main CPU and slave main CPU."
        ::= {gnAgnLogFileEntry 9 }

gnAgnLogFileDeviceFanStatus OBJECT-TYPE
        SYNTAX  OCTET STRING (SIZE(1))
        ACCESS  read-only
        STATUS mandatory
        DESCRIPTION
        "This is the Fan status of the IDU, during the alarm acceptance
         bit 1 = Fan1 is faulty.
         bit 2 = Fan 2 is faulty."
        ::= {gnAgnLogFileEntry 10 }

gnAgnLogFileDeviceODUStatus OBJECT-TYPE
        SYNTAX  OCTET STRING (SIZE(2))
        ACCESS  read-only
        STATUS mandatory
        DESCRIPTION
        "This is the ODU status during the alarm acceptance
         bit 1 MSB
         bit 1 = Power Supply status
         bit 2 = Synthesizer lock status
         bit 3 = Tx level status
         bit 4 = ATPC status
         bit 5 = Rx level status
         bit 6 = Not currently used
         bit 7 = Temperature status
         bit 8 = Not currently used.
         bit 9 = Not currently used"
        ::= {gnAgnLogFileEntry 11 }

gnAgnLogFileDeviceIDUStatus OBJECT-TYPE
        SYNTAX  OCTET STRING (SIZE(3))
        ACCESS  read-only
        STATUS mandatory
        DESCRIPTION
        "This is the IDU status during the alarm acceptance
         bit 1 MSB
         bit 1  = Power status -
         bit 2  = Cable open status -
         bit 3  = Cable short status -
         bit 4  = Modem Lock status
         bit 5  = Temperature status
         bit 6  = Not currently used.
         bit 7  = loopback status
         bit 8  = External alarm 1 status
         bit 9  = External alarm 2 status
         bit 10 = External alarm 3 status
         bit 11 = External alarm 4 status
         bit 12 = External alarm 5 status
         bit 13 = External alarm 6 status
         bit 14 = External alarm 7 status
         bit 15 = External alarm 8 status
         bit 16 = Remote connectivity status.
         bit 17 = Inner communication status.
         "
        ::= {gnAgnLogFileEntry 12 }



gnAgnLogFileOduCelsiusTemp OBJECT-TYPE
        SYNTAX  INTEGER
        ACCESS  read-only
        STATUS mandatory
        DESCRIPTION
        "This is the temperature of the ODU in degrees Celsius,
        during the alarm acceptance."
        ::= {gnAgnLogFileEntry 13 }

gnAgnLogFileOduReceiveLevel OBJECT-TYPE
        SYNTAX  INTEGER
        ACCESS  read-only
        STATUS mandatory
        DESCRIPTION
        "This is the received signal level in DBM, during the alarm acceptance "
        ::= {gnAgnLogFileEntry 14 }

gnAgnLogFileOduSynthesizerVCOLock OBJECT-TYPE
        SYNTAX  OCTET STRING (SIZE(1))
        ACCESS  read-only
        STATUS mandatory
        DESCRIPTION
        "This is the Synthesizer status, during the alarm acceptance
        bit 1 on = TX IF synthesizer fault
        bit 2 on = RX IF synthesizer fault
        bit 3 on = Xband synthesizer fault
        bit 4 on = History TX IF synthesizer fault
        bit 5 on = History RX IF synthesizer fault
        bit 6 on = History Xband synthesizer fault "
        ::= {gnAgnLogFileEntry 15 }

gnAgnLogFileOduPowerSupply OBJECT-TYPE
        SYNTAX  OCTET STRING (SIZE(1))
        ACCESS  read-only
        STATUS mandatory
        DESCRIPTION
        "This is the ODU power supply status, during the alarm acceptance
        bit 1 on = +5V faulty
        bit 2 on = +8V faulty
        bit 3 on = +12V faulty
        bit 4 on = -12V faulty."
        ::= {gnAgnLogFileEntry 16 }

gnAgnLogFileLineBERCur OBJECT-TYPE
        SYNTAX  INTEGER
        ACCESS  read-only
        STATUS mandatory
        DESCRIPTION
        "This is the Line BER (Bit Error Rate), during the alarm acceptance.
        Included for future development, not currently supported."
        ::= {gnAgnLogFileEntry 17 }

gnAgnLogFileRadioBERCur OBJECT-TYPE
        SYNTAX  INTEGER
        ACCESS  read-only
        STATUS mandatory
        DESCRIPTION
        "This is the Radio BER (Bit Error Rate), during the alarm acceptance.
         Included for future development, not currently supported."
        ::= {gnAgnLogFileEntry 18 }


gnAgnLogFileModStatus OBJECT-TYPE
        SYNTAX  INTEGER
        ACCESS  read-only
        STATUS mandatory
        DESCRIPTION
        "This is the Modulator status, during the alarm acceptance
                ok(2),
                modulatorFault(3)"
        ::= {gnAgnLogFileEntry 19 }


gnAgnLogFileDemodStatus OBJECT-TYPE
        SYNTAX  INTEGER
        ACCESS  read-only
        STATUS mandatory
        DESCRIPTION
        "This is the Demodulator status, during the alarm acceptance . This field
is for Ceragon
         internal debugging "
        ::= {gnAgnLogFileEntry 20 }


gnAgnLogFileLastDemodDefectBlocks OBJECT-TYPE
        SYNTAX  INTEGER
        ACCESS  read-only
        STATUS mandatory
        DESCRIPTION
        "This is the number of the Defected blocks (blocks that couldn't be
corrected)
         by the FEC, during the alarm acceptance last second."
        ::= {gnAgnLogFileEntry 21 }

gnAgnLogFileLastDemodBytesCorrected OBJECT-TYPE
        SYNTAX  INTEGER
        ACCESS  read-only
        STATUS mandatory
        DESCRIPTION
        "This is the number of the bytes that were corrected by the FEC,
        during the alarm acceptance last second."
        ::= {gnAgnLogFileEntry 22 }

gnAgnLogFileLastDemodBlocksCorrected OBJECT-TYPE
        SYNTAX  INTEGER
        ACCESS  read-only
        STATUS mandatory
        DESCRIPTION
        "This is the number of the blocks that were corrected by the FEC
         , during the alarm acceptance last second."
        ::= {gnAgnLogFileEntry 23 }

gnAgnLogFileUniqueId OBJECT-TYPE
        SYNTAX  INTEGER
        ACCESS  read-only
        STATUS mandatory
        DESCRIPTION
        "Unique Id for each log from 1 to 2,147,483,647 ( = 0x7FFFFFFF)."
        ::= {gnAgnLogFileEntry 24 }

gnAgnLogFileSource OBJECT-TYPE
        SYNTAX  INTEGER {
                interfaces(1),
                idc(2),
                drawer1(3),
                drawer2(4),
                tIdc1(257),
                tIdc2(258),
                tIdc3(259),
                tIdc4(260),
                tIdc5(261),
                tIdc6(262),
                tIdc7(263),
                tIdc8(264),
                tIdc9(265),
                tDrawer1(513),
                tDrawer2(514),
                tDrawer3(515),
                tDrawer4(516),
                tDrawer5(517),
                tDrawer6(518),
                tDrawer7(519),
                tDrawer8(520),
                tDrawer9(521),
                tDrawer10(522),
                tDrawer11(523),
                tDrawer12(524),
                tDrawer13(525),
                tDrawer14(526),
                tDrawer15(527),
                tXC1(769),
                tXC2(770),
                tXC3(771),
                tXC4(772),
                tXC5(773),
                tXC6(774)
        }

        ACCESS  read-only
        STATUS mandatory
        DESCRIPTION
        "The soure drawer of the alarm."
        ::= {gnAgnLogFileEntry 25 }

gnAgnLogFileTimeT  OBJECT-TYPE
        SYNTAX  INTEGER
        ACCESS  read-only
        STATUS mandatory
        DESCRIPTION
        "The time of the alarm represented by the number of seconds from 1.1.1970."
        ::= {gnAgnLogFileEntry 26 }

gnAgnLogFileHitlessSwitchLogAdmin OBJECT-TYPE
        SYNTAX  INTEGER {
                        enable(2),
                        disable(3)
        }
        ACCESS  read-write
        STATUS mandatory
        DESCRIPTION
        "This attribute allows for hitless logfile actions."
        DEFVAL { disable }
        ::= { gnAgnLogFileData 5 }

gnAgnLogFileXCSwitchLogAdmin OBJECT-TYPE
        SYNTAX  INTEGER {
                        enable(2),
                        disable(3)
        }
        ACCESS  read-write
        STATUS mandatory
        DESCRIPTION
        "This attribute allows for XC logfile actions."
        DEFVAL { disable }
        ::= { gnAgnLogFileData 6 }

gnAgnExternAlarm  OBJECT IDENTIFIER  ::= { gnAgn 3 }
gnAgnInExternAlarmTable   OBJECT-TYPE
        SYNTAX  SEQUENCE OF GnAgnInExternAlarmEntry
        ACCESS  not-accessible
        STATUS mandatory
        DESCRIPTION
        "This table is the input external alarm table. "
        ::= { gnAgnExternAlarm 1 }

gnAgnInExternAlarmEntry OBJECT-TYPE
        SYNTAX GnAgnInExternAlarmEntry
        ACCESS  not-accessible
        STATUS mandatory
          DESCRIPTION
          "Entry containing the external alarm inputs."

        INDEX { gnAgnInExternAlarmDevId,gnAgnInExternAlarmIndex}
        ::= { gnAgnInExternAlarmTable   1 }

GnAgnInExternAlarmEntry ::=
            SEQUENCE {
        gnAgnInExternAlarmDevId
             INTEGER,
        gnAgnInExternAlarmIndex
             INTEGER,
        gnAgnInExternAlarmEnable
             INTEGER,
        gnAgnInExternAlarmText
                    DisplayString,
        gnAgnInExternAlarmSeverity
                    INTEGER
    }

gnAgnInExternAlarmDevId OBJECT-TYPE
        SYNTAX  INTEGER
        {
                local(1),
                remote(2)
        }
        ACCESS  read-only
           STATUS mandatory
        DESCRIPTION
              "This value indicates device to which the external alarm
                is connected - 1 Local, 2 Remote"
        ::= { gnAgnInExternAlarmEntry 1 }

gnAgnInExternAlarmIndex OBJECT-TYPE
        SYNTAX INTEGER(1..8)
        ACCESS  read-only
           STATUS mandatory
        DESCRIPTION
              "This value indicates the index of the input external alarm
                1 to 8"
        ::= { gnAgnInExternAlarmEntry 2 }

gnAgnInExternAlarmEnable OBJECT-TYPE
        SYNTAX  INTEGER {
                disabled(2),
                enabled(3)
        }
        ACCESS  read-write
           STATUS mandatory
        DESCRIPTION
              "This value indicates if this Input alarm is enabled."
        DEFVAL { disabled }
        ::= { gnAgnInExternAlarmEntry 3 }


gnAgnInExternAlarmText OBJECT-TYPE
        SYNTAX  DisplayString (SIZE(0..20))
        ACCESS  read-write
        STATUS mandatory
        DESCRIPTION
        "This field describes the external alarm. Max string 20 characters"
        DEFVAL {"Alarm Description"}
        ::= { gnAgnInExternAlarmEntry 4 }

gnAgnInExternAlarmSeverity   OBJECT-TYPE
        SYNTAX INTEGER {
                        event(1),
                        warning(3),
                        minor(7),
                        major(15),
                        critical(31)
                }
       ACCESS  read-write
       STATUS  mandatory
       DESCRIPTION
              "This value indicates the severity of the external alarm
                31 CRITICAL ,15 MAJOR, 7 MINOR, 3 WARNING and 1 EVENT. "
       DEFVAL { 1}
        ::= { gnAgnInExternAlarmEntry 5 }



gnAgnOutRelayAlarmTable   OBJECT-TYPE
        SYNTAX  SEQUENCE OF GnAgnOutRelayAlarmEntry
        ACCESS  not-accessible
        STATUS mandatory
        DESCRIPTION
        "This table is the output relay alarm table. "
        ::= { gnAgnExternAlarm 2 }

gnAgnOutRelayAlarmEntry OBJECT-TYPE
        SYNTAX GnAgnOutRelayAlarmEntry
        ACCESS  not-accessible
        STATUS mandatory
          DESCRIPTION
          "Entry containing the output relay alarms."
        INDEX { gnAgnOutRelayAlarmDevId,gnAgnOutRelayAlarmIndex}
        ::= { gnAgnOutRelayAlarmTable   1 }

GnAgnOutRelayAlarmEntry ::=
            SEQUENCE {
        gnAgnOutRelayAlarmDevId
             INTEGER,
        gnAgnOutRelayAlarmIndex
             INTEGER,
        gnAgnOutRelayAlarmType
                    INTEGER
    }

gnAgnOutRelayAlarmDevId OBJECT-TYPE
        SYNTAX  INTEGER
        {
                local(1),
                remote(2)
        }
        ACCESS  read-only
           STATUS mandatory
        DESCRIPTION
              "This value indicates device from which the relay is sent
                from - 1 Local, 2 Remote"
        ::= { gnAgnOutRelayAlarmEntry 1 }

gnAgnOutRelayAlarmIndex OBJECT-TYPE
        SYNTAX INTEGER(1..5)
        ACCESS  read-only
           STATUS mandatory
        DESCRIPTION
              "This value indicates the index of the Output Relay alarm
                1 to 5"
        ::= { gnAgnOutRelayAlarmEntry 2 }


gnAgnOutRelayAlarmType   OBJECT-TYPE
        SYNTAX  INTEGER {
                                major(2),
                minor(3),
                      warning(4),
                external(5),
                      power(6),
                ber(7),
                      line(8),
                loopback(9),
                lof(10),
                                idu(11),
                                odu(12),
                cable(13),
                      remote(14),
                                critical(15),
                                testOn(16),
                                off(17),
								xc(18)
        }
       ACCESS  read-write
       STATUS  mandatory
       DESCRIPTION
              "This value indicates the alarm/led that causes
                the relay to change its state"
       DEFVAL { major}
        ::= { gnAgnOutRelayAlarmEntry 3 }

-- *******************************************************************

gnAgnFileTransfer  OBJECT IDENTIFIER  ::= { gnAgn 4 }

gnAgnFileTransferDestination  OBJECT-TYPE
        SYNTAX  INTEGER {
                         gnLocal                                       (1)}
--                         gnRemote                                      (2)
--                                        }
        ACCESS  read-write
        STATUS  mandatory
        DESCRIPTION
        "The file destination. The file transfer destination will always be set to
1, LOCAL. "
        ::= { gnAgnFileTransfer 1 }

gnAgnFileTransferServerIP  OBJECT-TYPE
        SYNTAX  IpAddress
        ACCESS  read-write
        STATUS  mandatory
        DESCRIPTION
        "The IP address of the server from which the file is loaded "
        ::= { gnAgnFileTransfer 2 }

gnAgnFileTransferFileName  OBJECT-TYPE
        SYNTAX  DisplayString
        ACCESS  read-write
        STATUS  mandatory
        DESCRIPTION
        "The name of the file to be loaded, format 8.3. "
        ::= { gnAgnFileTransfer 3 }

gnAgnFileTransferTftpTotalTimeOut OBJECT-TYPE
    SYNTAX  INTEGER
    ACCESS  read-write
    STATUS  mandatory
    DESCRIPTION
        "Receiving time-out value (seconds)."
    -- DEFVAL  { 20 }
    ::= { gnAgnFileTransfer 4 }


gnAgnFileTransferTransCmd  OBJECT-TYPE
        SYNTAX  INTEGER {
                         gnStartMUXSoftwareDownLoad     (1),
                         gnStartODUSoftwareDownLoad     (2),
                         gnStartMainManagerSoftwareDownLoad   (3),
                                         gnCancel                                        (4),
--                         gnStartMUXSoftwareUpLoad     (4),
--                         gnStartODUSoftwareUpLoad     (5),
                         gnNoOperation          (255)
                                        }
        ACCESS  read-write
        STATUS  mandatory
        DESCRIPTION
        "The command to be executed on fileName at fileServerIP."
        ::= { gnAgnFileTransfer 5 }


gnAgnFileTransfertFtpStatus OBJECT-TYPE
    SYNTAX  INTEGER {
                         gnTftpSessionPreStartSession   (1),
                         gnTftpSessionFileError    (2),
                         gnTftpSessionRcvBlock     (3),
                         gnTftpSessionRcvtimeout    (4),
                         gnTftpSessionRcvError     (5),
                                         gnTftpSessionDone          (6),
                         gnNoTftpSession     (255)
                                        }
    ACCESS  read-only
    STATUS  mandatory
    DESCRIPTION
        "Tftp session status "
    ::= { gnAgnFileTransfer 6 }

gnAgnFileTransfertftpBlockCount OBJECT-TYPE
    SYNTAX  INTEGER
    ACCESS  read-only
    STATUS  mandatory
    DESCRIPTION
        "The total number of blocks received in the current tFtp session "
    ::= { gnAgnFileTransfer 7 }

gnAgnFileTransferProtocol  OBJECT-TYPE
        SYNTAX  INTEGER {
                         tftp (2),
                         ftp (3)
                                        }
        ACCESS  read-write
        STATUS  mandatory
        DESCRIPTION
        "File transfer protocol: tftp or ftp."
        ::= { gnAgnFileTransfer 8 }

gnAgnFileTransferUserName  OBJECT-TYPE
        SYNTAX  DisplayString (SIZE(0..20))
        ACCESS  read-write
        STATUS  mandatory
        DESCRIPTION
        "User name - only for ftp protocol."
        ::= { gnAgnFileTransfer 9 }

gnAgnFileTransferPassword  OBJECT-TYPE
        SYNTAX  DisplayString (SIZE(0..20))
        ACCESS  read-write
        STATUS  mandatory
        DESCRIPTION
        "Password - only for ftp protocol."
        ::= { gnAgnFileTransfer 10 }

gnAgnFileTransferIDCVersionControl OBJECT-TYPE
        SYNTAX  INTEGER {
                version1(1),
        version2(2)
        }
        ACCESS  read-only
        STATUS mandatory
        DESCRIPTION
        "Points to the IDC software version to be downloaded"
        ::= { gnAgnFileTransfer 11 }

gnAgnFileTransferODCVersionControl OBJECT-TYPE
        SYNTAX  INTEGER {
                version1(1),
        version2(2)
        }
        ACCESS  read-only
        STATUS mandatory
        DESCRIPTION
        "Points to the ODC software version to be downloaded"
        ::= { gnAgnFileTransfer 12 }

--//////////////////////////////////////

gnAgnInternalDownloadTable  OBJECT-TYPE
        SYNTAX  SEQUENCE OF GnAgnInternalDownloadEntry
        ACCESS  not-accessible
        STATUS mandatory
        DESCRIPTION
        "This table controls the Internal Download process
           from manager to MUX and ODU (local and remote)."
        ::= { gnAgn 5 }

gnAgnInternalDownloadEntry OBJECT-TYPE
        SYNTAX GnAgnInternalDownloadEntry
        ACCESS  not-accessible
        STATUS mandatory
          DESCRIPTION
          "Entry containing the internal download process controls, for local and
remote."
        INDEX { gnAgnInternalDownloadId}
        ::= { gnAgnInternalDownloadTable 1 }

GnAgnInternalDownloadEntry ::=
            SEQUENCE {
        gnAgnInternalDownloadId
             INTEGER,
    gnAgnInternalDownloadOperation
                    INTEGER,
    gnAgnInternalDownloadAction
                    INTEGER,
        gnAgnInternalDownloadStatus
                     INTEGER,
    gnAgnInternalDownloadBlockCount
                    INTEGER,
        gnAgnInternalDownloadVersionControl
            INTEGER,
        gnAgnInternalDownloadFileSizeInBytes
            INTEGER,
        gnAgnInternalDownloadBytesCount
            INTEGER

    }

gnAgnInternalDownloadId OBJECT-TYPE
        SYNTAX  INTEGER
    ACCESS  read-only
           STATUS mandatory
        DESCRIPTION
              "This value indicates an index of a specific Internal Download
operation."
        ::= { gnAgnInternalDownloadEntry 1 }


gnAgnInternalDownloadOperation OBJECT-TYPE
        SYNTAX  INTEGER {
                localMUX(2),
                localODU(3),
                remoteMUX(4),
                remoteODU(5),
                leftShelfODU(6),
        rightShelfODU(7)
        }
        ACCESS  read-only
        STATUS mandatory
        DESCRIPTION
        "The Operation Description"
        ::= { gnAgnInternalDownloadEntry 2 }

gnAgnInternalDownloadAction OBJECT-TYPE
        SYNTAX  INTEGER {         start(2),
                                                cancel(3),
                                                clear(4),
                                                noAction(5),
                                                upLoadFpga(6) }
        ACCESS  read-write
        STATUS mandatory
        DESCRIPTION
        "This parameter controls the download action operation. "
        DEFVAL { noAction}
        ::= { gnAgnInternalDownloadEntry 3 }

gnAgnInternalDownloadStatus OBJECT-TYPE
    SYNTAX  INTEGER {

                         gnInternalDownloadSessionError                    (1),
                          gnInternalDownloadSessionClearing             (2),
             gnInternalDownloadSessionSendBlock     (3),
             gnInternalDownloadSessiontimeout           (4),
                          gnInternalDownloadSessionDone                     (5),
                         gnInternalDownloadSessionWaitForRetransmit (6),        --phos odu
                         gnNoInternalDownloadSession                    (255)

                                                    }
    ACCESS  read-only
    STATUS  mandatory
    DESCRIPTION
        " Internal download session status "
        ::= { gnAgnInternalDownloadEntry 4 }

gnAgnInternalDownloadBlockCount OBJECT-TYPE
    SYNTAX  INTEGER
    ACCESS  read-only
    STATUS  mandatory
    DESCRIPTION
        "The total number of blocks sent in the current session."
        ::= { gnAgnInternalDownloadEntry 5 }

gnAgnInternalDownloadVersionControl OBJECT-TYPE
        SYNTAX  INTEGER {
                version1(1),
        version2(2)
        }
        ACCESS  read-write
        STATUS mandatory
        DESCRIPTION
        "Points to the software version to be uploaded"
        ::= { gnAgnInternalDownloadEntry 6 }

gnAgnInternalDownloadFileSizeInBytes OBJECT-TYPE
        SYNTAX  INTEGER
        ACCESS  read-only
        STATUS mandatory
        DESCRIPTION
        "The total number of blocks in the current file"
        ::= { gnAgnInternalDownloadEntry 7 }

gnAgnInternalDownloadBytesCount OBJECT-TYPE
        SYNTAX  INTEGER
        ACCESS  read-only
        STATUS mandatory
        DESCRIPTION
        "The number of bytes sent in the current session"
        ::= { gnAgnInternalDownloadEntry 8 }


--//////////////////////////////////////


--//////////////////////////////////////

gnAgnInterLinkTable  OBJECT-TYPE
        SYNTAX  SEQUENCE OF GnAgnInterLinkEntry
        ACCESS  not-accessible
        STATUS mandatory
        DESCRIPTION
        "This table controls the Inter Link Download process
           between local and remote masters and between master and slave (local or
remote).
                 Each session transfers MUX, ODU or manager (IDC) software."
        ::= { gnAgn 6 }

gnAgnInterLinkEntry OBJECT-TYPE
        SYNTAX GnAgnInterLinkEntry
        ACCESS  not-accessible
        STATUS mandatory
          DESCRIPTION
          "Entry containing the process controls for the interlink download
process, for local and remote."
        INDEX { gnAgnInterLinkId}
        ::= { gnAgnInterLinkTable 1 }

        GnAgnInterLinkEntry ::=
            SEQUENCE {
        gnAgnInterLinkId
             INTEGER,
        gnAgnInterLinkSide
                         INTEGER,
    gnAgnInterLinkSource
                    INTEGER,
    gnAgnInterLinkDestination
                    INTEGER,
    gnAgnInterLinkSoftware
                    INTEGER,
    gnAgnInterLinkAction
                    INTEGER,
        gnAgnInterLinkStatus
                     INTEGER,
    gnAgnInterLinkBlockCount
                    INTEGER
    }

gnAgnInterLinkId OBJECT-TYPE
        SYNTAX  INTEGER
    ACCESS  read-only
           STATUS mandatory
        DESCRIPTION
              "This value indicates the index of a specific InterLink
operation."
        ::= { gnAgnInterLinkEntry 1 }

gnAgnInterLinkSide OBJECT-TYPE
        SYNTAX  INTEGER {
                local(2),
                remote(3)
        }
        ACCESS  read-only
        STATUS mandatory
        DESCRIPTION
        "The Link Side "
        ::= { gnAgnInterLinkEntry 2 }


gnAgnInterLinkSource OBJECT-TYPE
        SYNTAX  INTEGER {
                me(2),
                mate(3)
        }
        ACCESS  read-write
        STATUS mandatory
        DESCRIPTION
        "The source distribution center."
        ::= { gnAgnInterLinkEntry 3 }

gnAgnInterLinkDestination OBJECT-TYPE
        SYNTAX  INTEGER {
                me(2),
                mate(3),
                remote(4)
        }
        ACCESS  read-write
        STATUS mandatory
        DESCRIPTION
        "The destination distribution center.
         The destination may be selected as the local IDU being contacted (me),
         the collocated local IDU, in a protected configuration (mate) or
         it may be selected to be the remote IDU."
        ::= { gnAgnInterLinkEntry 4 }

gnAgnInterLinkSoftware OBJECT-TYPE
        SYNTAX  INTEGER {
                manager(2),
                mux(3),
                odu(4)
        }
        ACCESS  read-write
        STATUS mandatory
        DESCRIPTION
        "The software type to be transferred. MUX, ODU or IDU (referred to as
manager)."
        ::= { gnAgnInterLinkEntry 5 }



gnAgnInterLinkAction OBJECT-TYPE
        SYNTAX  INTEGER { start(2), cancel(3), noAction(4) }
        ACCESS  read-write
        STATUS mandatory
        DESCRIPTION
        "This parameter controls the interlink action operation. "
        DEFVAL { noAction}
        ::= { gnAgnInterLinkEntry 6 }

gnAgnInterLinkStatus OBJECT-TYPE
    SYNTAX  INTEGER {

                         gnInterLinkSessionError                    (1),
                          gnInterLinkSessionClearing             (2),
             gnInterLinkSessionSendBlock     (3),
             gnInterLinkSessiontimeout           (4),
                          gnInterLinkSessionDone                     (5),
                         gnNoInterLinkSession                    (255)

                                                    }
    ACCESS  read-only
    STATUS  mandatory
    DESCRIPTION
        " Inter-link session status "
        ::= { gnAgnInterLinkEntry 7 }

gnAgnInterLinkBlockCount OBJECT-TYPE
    SYNTAX  INTEGER
    ACCESS  read-only
    STATUS  mandatory
    DESCRIPTION
        "The total number of blocks sent in the current session."
        ::= { gnAgnInterLinkEntry 8 }

--//////////////////////////////////////

gnSoftwareVersionTable  OBJECT-TYPE
        SYNTAX  SEQUENCE OF GnSoftwareVersionEntry
        ACCESS  not-accessible
        STATUS mandatory
        DESCRIPTION
        "This table contains the IDU, MUX, ODU & WS software versions;
         local and remote."
        ::= { gnAgn 7 }

gnSoftwareVersionEntry OBJECT-TYPE
        SYNTAX GnSoftwareVersionEntry
        ACCESS  not-accessible
        STATUS mandatory
          DESCRIPTION
          "Entry containing the currently operating IDU, ODU and MUX software
versions."
        INDEX { gnSoftwareVersionId }
        ::= { gnSoftwareVersionTable 1 }

GnSoftwareVersionEntry ::=
         SEQUENCE {
        gnSoftwareVersionId
      INTEGER,
        gnSoftwareVersionIDU
          DisplayString,
        gnSoftwareVersionMUX
          DisplayString,
        gnSoftwareVersionODU
          DisplayString,
        gnSoftwareVersionIDUPostResetVersion
          DisplayString,
        gnSoftwareVersionMUXPostResetVersion
          DisplayString,
        gnSoftwareVersionODUPostResetVersion
          DisplayString,
        gnSoftwareVersionMuxAlteraVer
          DisplayString,
        gnSoftwareIDCVersionControl
      INTEGER,
        gnSoftwareVersionWSAlteraVer
          DisplayString,
        gnSoftwareVersionWSPostResetVersion
          DisplayString,
        gnSoftwareVersionMrmcVer
          DisplayString,
        gnSoftwareVersionMrmcPostResetVer
          DisplayString,
        gnSoftwareVersionBootSoftVer
          DisplayString,
        gnSoftwareVersionBootFlashVer
          DisplayString
        }

gnSoftwareVersionId OBJECT-TYPE
        SYNTAX  INTEGER
        {
                local(1),
                remote(2)
        }
    ACCESS  read-only
           STATUS mandatory
    DESCRIPTION
    "The ID indicates which device is involved
        in the specific row. The software table includes two rows,
        one for the local radio and one for the remote radio."
        ::= { gnSoftwareVersionEntry 1 }

gnSoftwareVersionIDU OBJECT-TYPE
        SYNTAX  DisplayString (SIZE(0..15))
        ACCESS  read-only
        STATUS mandatory
        DESCRIPTION
        "This is the IDU software version."
        ::= { gnSoftwareVersionEntry 2 }

gnSoftwareVersionMUX OBJECT-TYPE
        SYNTAX  DisplayString (SIZE(0..15))
        ACCESS  read-only
        STATUS mandatory
        DESCRIPTION
        "This is the MUX software version."
        ::= { gnSoftwareVersionEntry 3 }

gnSoftwareVersionODU OBJECT-TYPE
        SYNTAX  DisplayString (SIZE(0..15))
        ACCESS  read-only
        STATUS mandatory
        DESCRIPTION
        "This is the ODU software version."
        ::= { gnSoftwareVersionEntry 4 }

gnSoftwareVersionIDUPostResetVersion OBJECT-TYPE
        SYNTAX  DisplayString (SIZE(0..15))
        ACCESS  read-only
        STATUS mandatory
        DESCRIPTION
        "This is the IDU post reset software version."
        ::= { gnSoftwareVersionEntry 5 }

gnSoftwareVersionMUXPostResetVersion OBJECT-TYPE
        SYNTAX  DisplayString (SIZE(0..15))
        ACCESS  read-only
        STATUS mandatory
        DESCRIPTION
        "This is the MUX post reset software version."
        ::= { gnSoftwareVersionEntry 6 }

gnSoftwareVersionODUPostResetVersion OBJECT-TYPE
        SYNTAX  DisplayString (SIZE(0..15))
        ACCESS  read-only
        STATUS mandatory
        DESCRIPTION
        "This is the ODU post reset software version."
        ::= { gnSoftwareVersionEntry 7 }

gnSoftwareVersionMuxAlteraVer OBJECT-TYPE
        SYNTAX  DisplayString (SIZE(0..15))
        ACCESS  read-only
        STATUS mandatory
        DESCRIPTION
        "This string contains the MUX altera versions"
        ::= { gnSoftwareVersionEntry 8 }

gnSoftwareIDCVersionControl OBJECT-TYPE
        SYNTAX  INTEGER {
                version1(1),
        version2(2)
        }
        ACCESS  read-write
        STATUS mandatory
        DESCRIPTION
        "Points to the software version that will run on the next reset"
        ::= { gnSoftwareVersionEntry 9 }

gnSoftwareVersionWSAlteraVer OBJECT-TYPE
        SYNTAX  DisplayString (SIZE(0..15))
        ACCESS  read-only
        STATUS mandatory
        DESCRIPTION
        "This is the WS software version"
        ::= { gnSoftwareVersionEntry 10 }

gnSoftwareVersionWSPostResetVersion OBJECT-TYPE
        SYNTAX  DisplayString (SIZE(0..15))
        ACCESS  read-only
        STATUS mandatory
        DESCRIPTION
        "This is the WS post reset software version"
        ::= { gnSoftwareVersionEntry 11 }

gnSoftwareVersionMrmcVer OBJECT-TYPE
        SYNTAX  DisplayString (SIZE(0..15))
        ACCESS  read-only
        STATUS mandatory
        DESCRIPTION
        "This is the MRMC filter table software version"
        ::= { gnSoftwareVersionEntry 12 }

gnSoftwareVersionMrmcPostResetVer OBJECT-TYPE
        SYNTAX  DisplayString (SIZE(0..15))
        ACCESS  read-only
        STATUS mandatory
        DESCRIPTION
        "This is the MRMC  filter table post reset software version"
        ::= { gnSoftwareVersionEntry 13 }

gnSoftwareVersionBootSoftVer OBJECT-TYPE
        SYNTAX  DisplayString (SIZE(0..15))
        ACCESS  read-only
        STATUS mandatory
        DESCRIPTION
        "This is the BOOT software version"
        ::= { gnSoftwareVersionEntry 14 }

gnSoftwareVersionBootFlashVer OBJECT-TYPE
        SYNTAX  DisplayString (SIZE(0..15))
        ACCESS  read-only
        STATUS mandatory
        DESCRIPTION
        "This is the BOOT FLASH version"
        ::= { gnSoftwareVersionEntry 15 }

--//////////////////////////////////////

gnAgnNTPCfg  OBJECT IDENTIFIER  ::= { gnAgn 8 }

gnAgnNTPCfgServerIP  OBJECT-TYPE
         SYNTAX  IpAddress
        ACCESS  read-write
        STATUS  mandatory
        DESCRIPTION
        " The IP address of the server from which
        the current time is loaded."
        ::= { gnAgnNTPCfg 1 }

gnAgnNTPCfgOffsetFromUTC  OBJECT-TYPE
         SYNTAX  INTEGER (-1439..1439)
        ACCESS  read-write
        STATUS  mandatory
        DESCRIPTION
        " The offset from Coordinated Universal Time (minutes).
        Possible values: -1439..1439. "
        DEFVAL        {0}
        ::= { gnAgnNTPCfg 2 }

gnAgnNTPCfgSummerAdjOffset  OBJECT-TYPE
        SYNTAX  INTEGER (-1439..1439)
        ACCESS  read-write
        STATUS  mandatory
        DESCRIPTION
        " The summer adjustment offset (minutes).
        Possible values: -1439..1439. "
        DEFVAL        {0}
        ::= { gnAgnNTPCfg 3 }

gnAgnNTPCfgSummerAdjStart OBJECT-TYPE
    SYNTAX  INTEGER
    ACCESS  read-write
    STATUS  mandatory
    DESCRIPTION
    " The summertime adjustment start.
        In order to set this value:
        1.Turn every parameter (month, day, hour, minute)
          to hexadecimal.
        2.Write them all together - from left to right.
        3.Turn the accepted number to decimal basis.
        For example:
        in order to set 11:27:1:55 --> 11 = 0x0b, 27 = 0x1b,
        1 = 0x01, 55 = 0x37 --> the 4 parameters together:
        0x0b1b0137 = 186319159 (the last number is the one to set)."
    ::= { gnAgnNTPCfg 4 }


gnAgnNTPCfgSummerAdjEnd  OBJECT-TYPE
        SYNTAX  INTEGER
        ACCESS  read-write
        STATUS  mandatory
        DESCRIPTION
    " The summertime adjustment end.
        In order to set this value:
        1.Turn every parameter (month, day, hour, minute)
          to hexadecimal.
        2.Write them all together - from left to right.
        3.Turn the accepted number to decimal basis.
        For example:
        in order to set 11:27:1:55 --> 11 = 0x0b, 27 = 0x1b,
        1 = 0x01, 55 = 0x37 --> the 4 parameters together:
        0x0b1b0137 = 186319159 (the last number is the one to set)."
        ::= { gnAgnNTPCfg 5 }

gnAgnNTPCfgEnableAuth OBJECT-TYPE
    SYNTAX  INTEGER {
                disabled(2),
                des(3)
                                        }
    ACCESS  read-write
    STATUS  mandatory
    DESCRIPTION
    " This value indicates if the Authentication is enabled. "
        DEFVAL        {disabled}
    ::= { gnAgnNTPCfg 6 }

gnAgnNTPCfgAuthSecretKey OBJECT-TYPE
        SYNTAX  OCTET STRING (SIZE(8))
    ACCESS  read-write
    STATUS  mandatory
    DESCRIPTION
    " The authentication secret key (HEX).
        Not relevant when authentication is disable. "
    ::= { gnAgnNTPCfg 7 }

gnAgnNTPCfgAuthPublicKey OBJECT-TYPE
    SYNTAX  Gauge
    ACCESS  read-write
    STATUS  mandatory
    DESCRIPTION
    " The authentication public key is an integer number.
        The valid values: 1-4294967295.
        Not relevant when authentication is disable. "
    ::= { gnAgnNTPCfg 8 }

gnAgnNTPCfgUpdateInterval  OBJECT-TYPE
        SYNTAX  INTEGER (1..65535)
        ACCESS  read-write
        STATUS  mandatory
        DESCRIPTION
        " The time interval between sending NTP requests
        to the NTP server (minutes). Possible values: 1-65535. "
        DEFVAL        {10}
        ::= { gnAgnNTPCfg 9 }

gnAgnNTPCfgProtocolType OBJECT-TYPE
    SYNTAX  INTEGER {
                ntp(2),
                sntp(3)
                                        }
    ACCESS  read-write
    STATUS  mandatory
    DESCRIPTION
    "  "
        DEFVAL        {ntp}
    ::= { gnAgnNTPCfg 10 }


gnAgnInBandMng  OBJECT IDENTIFIER  ::= { gnAgn 9 }

gnAgnInBandMngEthernetIp  OBJECT-TYPE
         SYNTAX  IpAddress
        ACCESS  read-only
        STATUS  mandatory
        DESCRIPTION
        " The ethernet IP of the gateway network element."
        ::= { gnAgnInBandMng 1 }

gnAgnInBandMngEthernetMask  OBJECT-TYPE
         SYNTAX  IpAddress
        ACCESS  read-write
        STATUS  mandatory
        DESCRIPTION
        " The IP mask of the gateway network element."
        ::= { gnAgnInBandMng 2 }

gnAgnInBandMngPppIp  OBJECT-TYPE
         SYNTAX  IpAddress
        ACCESS  read-only
        STATUS  mandatory
        DESCRIPTION
        " The PPP IP address of the gateway network element."
        ::= { gnAgnInBandMng 3 }

gnAgnInBandMngPppMask  OBJECT-TYPE
         SYNTAX  IpAddress
        ACCESS  read-write
        STATUS  mandatory
        DESCRIPTION
        " The PPP IP mask of the gateway network element."
        ::= { gnAgnInBandMng 4 }

gnAgnInBandMngDefRoute  OBJECT-TYPE
         SYNTAX  IpAddress
        ACCESS  read-write
        STATUS  mandatory
        DESCRIPTION
    " The IP address of the default gateway/router
        to the internet. "
        ::= { gnAgnInBandMng 5 }

gnAgnInBandMngEnable  OBJECT-TYPE
        SYNTAX  INTEGER {
                        enable(2),
                        disable(3)
        }
        ACCESS  read-write
        STATUS  mandatory
        DESCRIPTION
        " Enable/Disable in-band management."
        ::= { gnAgnInBandMng 6 }

gnAgnInBandMngNetworkElementType  OBJECT-TYPE
        SYNTAX  INTEGER {
                        networkElement(2),
                        gateway(3)
        }
        ACCESS  read-write
        STATUS  mandatory
        DESCRIPTION
        " The element type of a single unit on the
        inband network (Gateway or Network Element). "
        ::= { gnAgnInBandMng 7 }

gnAgnInBandMngRadioChannel  OBJECT-TYPE
        SYNTAX  INTEGER {
                        dccr(2),
                        dccm(3),
                        mediaSpecific128k(4),
                        proprietary(5),
                        userChannel(6)
        }
        ACCESS  read-write
        STATUS  mandatory
        DESCRIPTION
        " The channel the in-band-management goes over
        (DCCR\DCCM\etc.). "
        ::= { gnAgnInBandMng 8 }

gnAgnInBandMngUnknownPackets  OBJECT-TYPE
        SYNTAX  INTEGER {
                        transparent(2),
                        discard(3)
        }
        ACCESS  read-write
        STATUS  mandatory
        DESCRIPTION
        " Select if unknown packets will be transparently
        transmitted over the RING or discarded and dropped."
        ::= { gnAgnInBandMng 9 }

gnAgnInBandMngTTL  OBJECT-TYPE
        SYNTAX  INTEGER  (5..64)
        ACCESS  read-write
        STATUS  mandatory
        DESCRIPTION
        " Time To Live."
        ::= { gnAgnInBandMng 10 }

gnAgnInBandMngRingIpSubnet  OBJECT-TYPE
         SYNTAX  IpAddress
        ACCESS  read-write
        STATUS  mandatory
        DESCRIPTION
        " The IP subnet address of the ring."
        ::= { gnAgnInBandMng 11 }

gnAgnInBandMngRingIpMask  OBJECT-TYPE
         SYNTAX  IpAddress
        ACCESS  read-write
        STATUS  mandatory
        DESCRIPTION
        " The IP mask of the ring subnet address."
        ::= { gnAgnInBandMng 12 }

gnAgnInBandMngNetworkId  OBJECT-TYPE
         SYNTAX  INTEGER  (1..255)
        ACCESS  read-write
        STATUS  mandatory
        DESCRIPTION
        " Identification for single link path of
        PPPoE over cross-networks. "
        ::= { gnAgnInBandMng 13 }

gnAgnInBandMngLineMode  OBJECT-TYPE
        SYNTAX  INTEGER {
                        inbandFiber(2),
                        forcePPPoE(3)
        }
        ACCESS  read-write
        STATUS  mandatory
        DESCRIPTION
        " Enable the user to force PPPoE mode
        instead of DCCR line communication. "
        ::= { gnAgnInBandMng 14 }

gnAgnInBandMngFiberChannel  OBJECT-TYPE
        SYNTAX  INTEGER {
                        dccr(2),
                        dccm(3),
--                        mediaSpecific128k(4),
                        userChannel(5)
        }
        ACCESS  read-write
        STATUS  mandatory
        DESCRIPTION
                " "
        DEFVAL { dccr}
        ::= { gnAgnInBandMng 15 }

gnAgnInBandMngTribChannel  OBJECT-TYPE
        SYNTAX  INTEGER {
                        disable(2),
                        dccr(3),
                        dccm(4)
        }
        ACCESS  read-write
        STATUS  mandatory
        DESCRIPTION
                " "
        DEFVAL { dccr}
        ::= { gnAgnInBandMng 16 }

gnAgnInBandMngXChannelTable OBJECT-TYPE
        SYNTAX SEQUENCE OF GnAgnInBandMngXChannelEntry
        ACCESS not-accessible
        STATUS mandatory
        DESCRIPTION
        "This table defines the inband channels mapping."
        ::= { gnAgnInBandMng 17 }

gnAgnInBandMngXChannelEntry OBJECT-TYPE
        SYNTAX GnAgnInBandMngXChannelEntry
        ACCESS not-accessible
        STATUS mandatory
        DESCRIPTION
        "This is an entry in the inband channel table.
        This table contains a row for every channel (1..4).
        First 3 physical channels are available in the 8 possible mapping options (on both carrier drawers).
        An additional channel (4) is available on the IDC (PPPoE))."
        INDEX { gnAgnInBandMngXChannelId }
        ::= { gnAgnInBandMngXChannelTable 1 }

GnAgnInBandMngXChannelEntry ::=
        SEQUENCE {
        gnAgnInBandMngXChannelId
                INTEGER,
        gnAgnInBandMngXChannelIfIndex
                INTEGER,
        gnAgnInBandMngXChannelType
                INTEGER,
    gnAgnInBandMngXChannelState
                 INTEGER,
        gnAgnInBandMngXChannelNeighborIP
             IpAddress,
    gnAgnInBandMngXChannelStatus
                INTEGER
    }

gnAgnInBandMngXChannelId OBJECT-TYPE
        SYNTAX  INTEGER
        {
                channel1(1),
                channel2(2),
                channel3(3),
                channel4(4)
        }
    ACCESS  read-only
           STATUS mandatory
    DESCRIPTION
    "The channel Id"
    ::= { gnAgnInBandMngXChannelEntry 1 }

gnAgnInBandMngXChannelIfIndex OBJECT-TYPE
    SYNTAX  INTEGER
    ACCESS  read-write
    STATUS mandatory
    DESCRIPTION
    "The ifIndex of the interface that is mapped to this channel"
    ::= { gnAgnInBandMngXChannelEntry 2 }

gnAgnInBandMngXChannelType OBJECT-TYPE
    SYNTAX  INTEGER
    {
                proprietary(2),
                dccr(3),
                dccm(4),
                mediaspecific(5),
                pppoe(6)
    }
    ACCESS  read-write
    STATUS mandatory
    DESCRIPTION
            "The type of channel the in-band-management goes over.
         Default value for channels 1 and 3 in the carrier drawers is Proprietary.
         Channel 2 not allowed to be Proprietary.
                 In protection the ch_type of ch#3 can not be modified
         Channel 4 must be PPPoE"
    ::= { gnAgnInBandMngXChannelEntry 3 }

gnAgnInBandMngXChannelState OBJECT-TYPE
    SYNTAX  INTEGER
    {
                enable(2),
                disable(3)
    }
    ACCESS  read-write
    STATUS mandatory
    DESCRIPTION
            "Enable/Disable the in band channel"
    ::= { gnAgnInBandMngXChannelEntry 4 }

gnAgnInBandMngXChannelNeighborIP  OBJECT-TYPE
         SYNTAX  IpAddress
        ACCESS  read-write
        STATUS  mandatory
        DESCRIPTION
        " The PPP IP address of the gateway network element."
        ::= { gnAgnInBandMngXChannelEntry 5 }

gnAgnInBandMngXChannelStatus OBJECT-TYPE
        SYNTAX  INTEGER {
                up(2),
                down(3),
                closed(4)
        }
           ACCESS  read-only
           STATUS mandatory
           DESCRIPTION
    " This MIB parameter defines the In-band PPP connection status.
      If the MIB value is up the PPP connection is up and running
      If the MIB value is down the PPP connection is down and is in initialization state.
          (Trying to establish a connection)
      If the MIB value is closed the PPP connection is down and is not trying open a connection."
    ::= { gnAgnInBandMngXChannelEntry 6 }

gnAgnInBandMngXEnableInbandChannels  OBJECT-TYPE
        SYNTAX  INTEGER (0..15)
        ACCESS  read-write
        STATUS  mandatory
        DESCRIPTION
                "This configuration enables/disables the in-band channels: 1-4.
                The LSB represent channel 1, the 2nd bit channel 2, etc.
                If a bit is on (1) it's channel is enabled.
                Example: if channels 2 & 4 are enabled and channels 1 & 3 are disabled, then
                                 the binary value is 1010, so the MIB value (decimal integer) will be 10."
        DEFVAL { 0 }
        ::= { gnAgnInBandMng 18 }

gnAgnInBandMngMainGNEInterface  OBJECT-TYPE
        SYNTAX  INTEGER {
                default(2),
                channel1(3),
                channel2(4),
                channel3(5),
                channel4(6)
        }
        ACCESS  read-write
        STATUS  mandatory
        DESCRIPTION
                "determines the primary GNE channel.
                 Default means fixed channel prioritizing, in the following order (from first to last):
                 Right Carrier Radio interface, [STM-1] Line interface on either Left or Right Carrier,
                 Left Carrier Radio interface and PPPoE interface."
        DEFVAL { 2 }
        ::= { gnAgnInBandMng 19 }

--//////////////////////////////////////

gnNeighborIP  OBJECT IDENTIFIER  ::= { gnAgn 10 }
gnNeighborInBandTable OBJECT-TYPE
        SYNTAX  SEQUENCE OF GnNeighborInBandEntry
        ACCESS  not-accessible
        STATUS mandatory
        DESCRIPTION
        "This table defines the IP addresses of the units that are connected Inband."
        ::= { gnNeighborIP 1 }

gnNeighborInBandEntry OBJECT-TYPE
        SYNTAX GnNeighborInBandEntry
        ACCESS  not-accessible
        STATUS mandatory
        DESCRIPTION
        "This is an entry in the IP addresses of the units that are connected Inband.
        This table contains a row for every interface which type is logically connected.
        for example regenerator which is connected in band has two neighbors: the first (index 1)
      the remote radio unit and the second the remote fiber neighbor (index 2)."
        INDEX {  ifIndex }
        ::= { gnNeighborInBandTable 1 }

GnNeighborInBandEntry ::=
            SEQUENCE {
              gnNeighborInBandIP
               IpAddress,
        gnNeighborInBandStatus
                        INTEGER
    }

gnNeighborInBandIP  OBJECT-TYPE
         SYNTAX  IpAddress
        ACCESS  read-write
        STATUS  mandatory
        DESCRIPTION
        " The PPP IP address of the gateway network element."
        ::= { gnNeighborInBandEntry 1 }

gnNeighborInBandStatus OBJECT-TYPE
        SYNTAX  INTEGER {
                up(2),
                down(3),
                closed(4)
        }
           ACCESS  read-only
           STATUS mandatory
           DESCRIPTION
    " This MIB parameter defines the In-band PPP connection status.
      If the MIB value is up the PPP connection is up and running
      If the MIB value is down the PPP connection is down and is in initialization state.
          (Trying to establish a connection)
      If the MIB value is closed the PPP connection is down and is not trying open a connection."
    ::= { gnNeighborInBandEntry 2 }



gnNeighborMateIP OBJECT-TYPE
        SYNTAX  IpAddress
        ACCESS  read-only
        STATUS  mandatory
        DESCRIPTION
        " The Protection Mate IP address."
        ::= { gnNeighborIP 2 }


gnNeighborRemoteRadioIP OBJECT-TYPE
        SYNTAX  IpAddress
        ACCESS  read-only
        STATUS  mandatory
        DESCRIPTION
        " The IP address of the Radio Remote IDU."
        ::= { gnNeighborIP 3 }


gnNeighborInBandXTable OBJECT-TYPE
        SYNTAX  SEQUENCE OF GnNeighborInBandXEntry
        ACCESS  not-accessible
        STATUS mandatory
        DESCRIPTION
        "This table defines the IP addresses of the units that are connected Inband."
        ::= { gnNeighborIP 4 }

gnNeighborInBandXEntry OBJECT-TYPE
        SYNTAX GnNeighborInBandXEntry
        ACCESS  not-accessible
        STATUS mandatory
        DESCRIPTION
        "This is an entry in the IP addresses of the units that are connected Inband.
        This table contains a row for every interface which type is logically connected.
        for example regenerator which is connected in band has two neighbors: the first (index 1)
      the remote radio unit and the second the remote fiber neighbor (index 2)."
        INDEX {  gnNeighborInBandXId }
        ::= { gnNeighborInBandXTable 1 }

GnNeighborInBandXEntry ::=
            SEQUENCE {
                gnNeighborInBandXId
                        INTEGER,
              gnNeighborInBandXIP
               IpAddress
    }

gnNeighborInBandXId OBJECT-TYPE
        SYNTAX  INTEGER
        {
                drawer1(3),
                drawer2(4)
        }
    ACCESS  read-only
           STATUS mandatory
    DESCRIPTION
    " "
    ::= { gnNeighborInBandXEntry 1 }

gnNeighborInBandXIP  OBJECT-TYPE
         SYNTAX  IpAddress
        ACCESS  read-write
        STATUS  mandatory
        DESCRIPTION
        " The PPP IP address of the gateway network element."
        ::= { gnNeighborInBandXEntry 2 }


gnNeighborIpTable OBJECT-TYPE
        SYNTAX  SEQUENCE OF GnNeighborIpEntry
        ACCESS  not-accessible
        STATUS mandatory
        DESCRIPTION
        "This table shows the Neighbor IP for each STM connection."
        ::= { gnNeighborIP 5 }

gnNeighborIpEntry OBJECT-TYPE
        SYNTAX GnNeighborIpEntry
        ACCESS  not-accessible
        STATUS mandatory
        DESCRIPTION
        "."
        INDEX { ifIndex }
        ::= { gnNeighborIpTable 1 }

GnNeighborIpEntry ::=
            SEQUENCE {
        gnNeighborIpDetectMode
                        INTEGER,
              gnNeighborIpAddress
               IpAddress,
        gnNeighborIpRemoteIfIndex
                        INTEGER,
                gnNeighborIpRemoteType
                        INTEGER
    }

gnNeighborIpDetectMode OBJECT-TYPE
        SYNTAX  INTEGER {
                disable(2),
                manual(3),
                auto(4)
        }
           ACCESS  read-write
           STATUS mandatory
           DESCRIPTION
    "The Neighbor detect can be done automatically or to be manually insreted.
    Disable marks that the IP Detect is not used."
    ::= { gnNeighborIpEntry 1 }

gnNeighborIpAddress OBJECT-TYPE
         SYNTAX  IpAddress
        ACCESS  read-write
        STATUS  mandatory
        DESCRIPTION
        "The neighbor IP address."
        ::= { gnNeighborIpEntry 2 }

gnNeighborIpRemoteIfIndex OBJECT-TYPE
        SYNTAX  INTEGER
           ACCESS  read-write
           STATUS mandatory
           DESCRIPTION
    "The If index of the neighbor IP address connected to the current If Index."
    ::= { gnNeighborIpEntry 3 }

gnNeighborIpRemoteType OBJECT-TYPE
        SYNTAX  INTEGER {
                regenerator(1),
                access(2),
                adm(3),
                fibeair1500p(4),
                admline2line(5)
        }
           ACCESS  read-write
           STATUS mandatory
           DESCRIPTION
    "The Type of the neighbor."
    ::= { gnNeighborIpEntry 4 }

----------------
gnAgnSNMPCfg  OBJECT IDENTIFIER  ::= { gnAgn 11 }

gnAgnSNMPCfgTrapCommunity  OBJECT-TYPE
        SYNTAX OCTET STRING(SIZE(12))
        ACCESS  read-write
        STATUS  mandatory
        DESCRIPTION
        " "
        ::= { gnAgnSNMPCfg 1 }

gnAgnSNMPCfgReadCommunity  OBJECT-TYPE
        SYNTAX OCTET STRING(SIZE(12))
        ACCESS  read-write
        STATUS  mandatory
        DESCRIPTION
        " "
        ::= { gnAgnSNMPCfg 2 }

gnAgnSNMPCfgWriteCommunity  OBJECT-TYPE
        SYNTAX OCTET STRING(SIZE(12))
        ACCESS  read-write
        STATUS  mandatory
        DESCRIPTION
        " "
        ::= { gnAgnSNMPCfg 3 }


gnAgnPrvt  OBJECT IDENTIFIER  ::= { gnAgn 12 }

gnAgnPrvtCmd  OBJECT-TYPE
        SYNTAX  INTEGER {
                noOperation(2),
        cNV(3),
                cNVBtr(4)
        }
        ACCESS  read-write
        STATUS  mandatory
        DESCRIPTION
        " ."
        DEFVAL { noOperation }
        ::= { gnAgnPrvt 1 }

gnAgnPrvtCmdStat  OBJECT-TYPE
        SYNTAX  INTEGER {
                ready(2),
        cNVPass(3),
                cNVFail(4),
                cNVBtrPass(5),
                cNVBtrFail(6)
        }
        ACCESS  read-only
        STATUS  mandatory
        DESCRIPTION
        " ."
        DEFVAL { ready }
        ::= { gnAgnPrvt 2 }


gnSoftwareDrawerVersionTable  OBJECT-TYPE
        SYNTAX  SEQUENCE OF GnSoftwareDrawerVersionEntry
        ACCESS  not-accessible
        STATUS mandatory
        DESCRIPTION
        "This table contains the IDU, MUX & ODU software versions;
         local and remote."
        ::= { gnAgn 13 }

gnSoftwareDrawerVersionEntry OBJECT-TYPE
        SYNTAX GnSoftwareDrawerVersionEntry
        ACCESS  not-accessible
        STATUS mandatory
          DESCRIPTION
          "Entry containing the currently operating IDU, ODU and MUX software
versions."
        INDEX { gnSoftwareDrawerId }
        ::= { gnSoftwareDrawerVersionTable 1 }

GnSoftwareDrawerVersionEntry ::=
         SEQUENCE {
        gnSoftwareDrawerId
      INTEGER,
        gnSoftwareDrawerVersionMUX
          DisplayString,
         gnSoftwareDrawerVersionMUXPostResetVersion
          DisplayString,
        gnSoftwareDrawerVersionODU
          DisplayString,
        gnSoftwareDrawerVersionODUPostResetVersion
          DisplayString,
        gnSoftwareDrawerVersionModemFile
          DisplayString,
        gnSoftwareDrawerVersionModemFilePostResetVersion
          DisplayString,
        gnSoftwareDrawerVersionModemScript
          DisplayString,
        gnSoftwareDrawerVersionModemScriptPostResetVersion
          DisplayString,
        gnSoftwareDrawerVersionRfuFpgaVersion
          DisplayString
        }

gnSoftwareDrawerId OBJECT-TYPE
        SYNTAX  INTEGER
        {
                drawer1(3),
                drawer2(4)
        }
    ACCESS  read-only
           STATUS mandatory
    DESCRIPTION
    "The ID indicates which Drawer is involved
        in the specific row. "
        ::= { gnSoftwareDrawerVersionEntry 1 }


gnSoftwareDrawerVersionMUX OBJECT-TYPE
        SYNTAX  DisplayString (SIZE(0..15))
        ACCESS  read-only
        STATUS mandatory
        DESCRIPTION
        "This is the MUX software version."
        ::= { gnSoftwareDrawerVersionEntry 2 }

gnSoftwareDrawerVersionMUXPostResetVersion OBJECT-TYPE
        SYNTAX  DisplayString (SIZE(0..15))
        ACCESS  read-only
        STATUS mandatory
        DESCRIPTION
        "This is the ODU software version."
        ::= { gnSoftwareDrawerVersionEntry 3 }


gnSoftwareDrawerVersionODU OBJECT-TYPE
        SYNTAX  DisplayString (SIZE(0..15))
        ACCESS  read-only
        STATUS mandatory
        DESCRIPTION
        "This is the MUX post reset software version."
        ::= { gnSoftwareDrawerVersionEntry 4 }


gnSoftwareDrawerVersionODUPostResetVersion OBJECT-TYPE
        SYNTAX  DisplayString (SIZE(0..15))
        ACCESS  read-only
        STATUS mandatory
        DESCRIPTION
        "This is the MUX post reset software version."
        ::= { gnSoftwareDrawerVersionEntry 5 }

gnSoftwareDrawerVersionModemFile OBJECT-TYPE
        SYNTAX  DisplayString (SIZE(0..15))
        ACCESS  read-only
        STATUS mandatory
        DESCRIPTION
        "This is the Modem software version."
        ::= { gnSoftwareDrawerVersionEntry 6 }

gnSoftwareDrawerVersionModemFilePostResetVersion OBJECT-TYPE
        SYNTAX  DisplayString (SIZE(0..15))
        ACCESS  read-only
        STATUS mandatory
        DESCRIPTION
        "This is the Modem post reset software version."
        ::= { gnSoftwareDrawerVersionEntry 7 }

gnSoftwareDrawerVersionModemScript OBJECT-TYPE
        SYNTAX  DisplayString (SIZE(0..15))
        ACCESS  read-only
        STATUS mandatory
        DESCRIPTION
        "This is the Modem software version."
        ::= { gnSoftwareDrawerVersionEntry 8 }

gnSoftwareDrawerVersionModemScriptPostResetVersion OBJECT-TYPE
        SYNTAX  DisplayString (SIZE(0..15))
        ACCESS  read-only
        STATUS mandatory
        DESCRIPTION
        "This is the Modem post reset software version."
        ::= { gnSoftwareDrawerVersionEntry 9 }

gnSoftwareDrawerVersionRfuFpgaVersion OBJECT-TYPE
        SYNTAX  DisplayString (SIZE(0..15))
        ACCESS  read-only
        STATUS mandatory
        DESCRIPTION
        "This is the Rfu Fpga software version."
        ::= { gnSoftwareDrawerVersionEntry 10 }
-- @@@@@@@@@@@@@@@@@@@@@@@@@@@@@@@@@@@@@@@@@@@@@@@@@@@@@@@@@@@@@@@@@

gnAgnCurrentAlarm OBJECT IDENTIFIER  ::= { gnAgn 14 }

gnAgnCurrentAlarmLastChange OBJECT-TYPE
        SYNTAX INTEGER
        ACCESS  read-only
        STATUS mandatory
                DESCRIPTION
                "This counter initialized with random number after resest, and incremented on each change in the gnAgnCurrentAlarmTable
                (either add or remove of an entery)."
        ::= { gnAgnCurrentAlarm 1 }

gnAgnCurrentAlarmTable  OBJECT-TYPE
        SYNTAX  SEQUENCE OF GnCurrentAlarmEntry
        ACCESS  not-accessible
        STATUS mandatory
        DESCRIPTION
        "This table includes the currently open alarm (when a RAISED trap is
          sent, an alarm is added to the table, when a CLEAR trap is sent,
          the alarm is removed."
        ::= { gnAgnCurrentAlarm 2 }

gnCurrentAlarmEntry OBJECT-TYPE
        SYNTAX GnCurrentAlarmEntry
        ACCESS  not-accessible
        STATUS mandatory
          DESCRIPTION
          "Entry containing the info of a currently RAISED trap."
        INDEX { gnAgnCurrentAlarmCounter }
        ::= { gnAgnCurrentAlarmTable  1 }

GnCurrentAlarmEntry ::=
            SEQUENCE {
           gnAgnCurrentAlarmCounter
              INTEGER,
        gnAgnCurrentAlarmSeverity
              INTEGER,
        gnAgnCurrentAlarmId
              INTEGER,
           gnAgnCurrentAlarmIfIndex
              INTEGER,
           gnAgnCurrentAlarmOrigin
              INTEGER,
           gnAgnCurrentAlarmUnit
              INTEGER,
           gnAgnCurrentAlarmTrapID
              INTEGER,
        gnAgnCurrentAlarmTimeT
          INTEGER,
        gnAgnCurrentAlarmText
                  DisplayString
}

  gnAgnCurrentAlarmCounter OBJECT-TYPE
        SYNTAX INTEGER
        ACCESS  read-only
        STATUS mandatory
                DESCRIPTION
                "A running counter of open alarm, the counter is incremented on every new RAISED trap.
                It is cleared after reset. This counter is (optionaly) attached to each trap."
        ::= { gnCurrentAlarmEntry 1 }


gnAgnCurrentAlarmSeverity OBJECT-TYPE
        SYNTAX  INTEGER
        {
                event                (1),
                warning                (3),
                minor                (7),
                major                (15),
                critical        (31)
        }
        ACCESS  read-only
        STATUS  mandatory
        DESCRIPTION
        "The current Alarm severity"
         ::= { gnCurrentAlarmEntry 2 }

  gnAgnCurrentAlarmId OBJECT-TYPE
        SYNTAX INTEGER
        ACCESS  read-only
        STATUS mandatory
                DESCRIPTION
                "Alarm Identifier (contains alarm type and interface). Same AlarmId for rasie and clear alarms."
        ::= { gnCurrentAlarmEntry 3 }

  gnAgnCurrentAlarmIfIndex OBJECT-TYPE
        SYNTAX INTEGER
        ACCESS  read-only
        STATUS mandatory
                DESCRIPTION
                "Interface Index where the alarm occurred, alarms that are
                   not associated with specific interface will have the following value:
                        For IDC related alarms the value is:          65001
                        For drawer1 related alarms the value is:  65003
                        For drawer2 related alarms the value is:  65004				
						If Alarm's origin is bigger than 256, it will be 65000 + the origin"
        ::= { gnCurrentAlarmEntry 4 }

gnAgnCurrentAlarmOrigin OBJECT-TYPE
        SYNTAX  INTEGER {
                interfaces(1),
                idc(2),
                drawer1(3),
                drawer2(4),
                unKnown(5),
                tIdc1(257),
                tIdc2(258),
                tIdc3(259),
                tIdc4(260),
                tIdc5(261),
                tIdc6(262),
                tIdc7(263),
                tIdc8(264),
                tIdc9(265),
                tDrawer1(513),
                tDrawer2(514),
                tDrawer3(515),
                tDrawer4(516),
                tDrawer5(517),
                tDrawer6(518),
                tDrawer7(519),
                tDrawer8(520),
                tDrawer9(521),
                tDrawer10(522),
                tDrawer11(523),
                tDrawer12(524),
                tDrawer13(525),
                tDrawer14(526),
                tDrawer15(527),
                tXC1(769),
                tXC2(770),
                tXC3(771),
                tXC4(772),
                tXC5(773),
                tXC6(774)
        }
        ACCESS  read-only
        STATUS mandatory
                DESCRIPTION
                "The origin drawer of the alarm (if applicable, otherwise it will be idc(2))."
        ::= {gnCurrentAlarmEntry 5}

gnAgnCurrentAlarmUnit OBJECT-TYPE
        SYNTAX  INTEGER {
                idc(2),
                odu(3),
                mux(4),
                modem(5),
                drawer(6),
                unKnown(7),
                xc(9)
        }
        ACCESS  read-only
        STATUS mandatory
                DESCRIPTION
                "The unit of the alarm."
        ::= {gnCurrentAlarmEntry 6}

gnAgnCurrentAlarmTrapID OBJECT-TYPE
        SYNTAX INTEGER
        ACCESS  read-only
        STATUS mandatory
                DESCRIPTION
                "The ID of the RAISED trap that was sent when this alarm was raised."
        ::= { gnCurrentAlarmEntry 7 }

gnAgnCurrentAlarmTimeT OBJECT-TYPE
        SYNTAX  INTEGER
        ACCESS  read-only
        STATUS mandatory
        DESCRIPTION
        "Timestamp of this alarm, this number is the seconds from midnight 1.1.1970."
        ::= { gnCurrentAlarmEntry 8 }

gnAgnCurrentAlarmText OBJECT-TYPE
        SYNTAX  DisplayString
        ACCESS  read-only
        STATUS mandatory
        DESCRIPTION
        "The alarm display text (same as the text in the sent trap)."
        ::= { gnCurrentAlarmEntry 9}


gnNMS OBJECT IDENTIFIER  ::= { gnAgn 15 }
--//////////////////////////////////////
gnApplicFileTable  OBJECT-TYPE
        SYNTAX  SEQUENCE OF GnApplicFileEntry
        ACCESS  not-accessible
        STATUS mandatory
        DESCRIPTION
        "This table contains the application file list."
        ::= { gnAgn 16 }

gnApplicFileEntry OBJECT-TYPE
        SYNTAX GnApplicFileEntry
        ACCESS  not-accessible
        STATUS mandatory
          DESCRIPTION
          "Entry containing the application file list."
        INDEX { gnApplicFileId }
        ::= { gnApplicFileTable 1 }

GnApplicFileEntry ::=
         SEQUENCE {
        gnApplicFileId
			INTEGER,
        gnApplicFileName
			DisplayString,
        gnApplicFileVersion
			DisplayString,
        gnApplicFileCreateDate
			OCTET STRING,
        gnApplicFileDownloadDate
			OCTET STRING,
        gnApplicFileType
			INTEGER,
        gnApplicFileSubType
			DisplayString,
        gnApplicFileFirmware
			INTEGER,
        gnApplicFileGeneralPurpose
			INTEGER,
        gnApplicFileSize
			INTEGER,		  
        gnApplicFileCompressed
			INTEGER,		  
        gnApplicFileDssSupport
			INTEGER,		  
        gnApplicFileCrcSupport
			INTEGER		  
        }

gnApplicFileId OBJECT-TYPE
        SYNTAX  INTEGER
		ACCESS  read-only
        STATUS mandatory
		DESCRIPTION
		"The ID indicates which device is involved
        in the specific row. The application file table includes two rows,
        one for the local radio and one for the remote radio."
        ::= { gnApplicFileEntry 1 }

gnApplicFileName OBJECT-TYPE
        SYNTAX  DisplayString (SIZE(0..40))
        ACCESS  read-only
        STATUS mandatory
        DESCRIPTION
        "This is the application file name."
        ::= { gnApplicFileEntry 2 }

gnApplicFileVersion OBJECT-TYPE
        SYNTAX  DisplayString (SIZE(0..40))
        ACCESS  read-only
        STATUS mandatory
        DESCRIPTION
        "This is the application file version."
        ::= { gnApplicFileEntry 3 }

gnApplicFileCreateDate OBJECT-TYPE
        SYNTAX OCTET STRING(SIZE(8))
        ACCESS  read-only
        STATUS mandatory
        DESCRIPTION
        "This parameter specifies the application file download date
          Format 'YYYY-MM-DD,HH:MM:SS' (Hexadecimal).
            A date-time specification.

            field  octets  contents                  range
            -----  ------  --------                  -----
              1      1-2   year                      0..65536
              2       3    month                     1..12
              3       4    day                       1..31
              4       5    hour                      0..23
              5       6    minutes                   0..59
                  6       7    seconds                   0..60
                           (use 60 for leap-second)
              7       8    deci-seconds              0..9
              8       9    direction from UTC        '+' / '-'
              9      10    hours from UTC            0..11
             10      11    minutes from UTC          0..59

            For example, Tuesday May 26, 1992 at 1:30:15 PM EDT
            would be displayed as:        07 c8 05 1a 0d 1e 0f 00
                                                                  ( 1992 -5 -26,13:30:15 )

            Note that if only local time is known, then timezone
            information (fields 8-10) is not present."

        ::= { gnApplicFileEntry 4 }


gnApplicFileDownloadDate OBJECT-TYPE
        SYNTAX OCTET STRING(SIZE(8))
        ACCESS  read-only
        STATUS mandatory
        DESCRIPTION
        "This parameter specifies the application file download date
          Format 'YYYY-MM-DD,HH:MM:SS' (Hexadecimal).
            A date-time specification.

            field  octets  contents                  range
            -----  ------  --------                  -----
              1      1-2   year                      0..65536
              2       3    month                     1..12
              3       4    day                       1..31
              4       5    hour                      0..23
              5       6    minutes                   0..59
                  6       7    seconds                   0..60
                           (use 60 for leap-second)
              7       8    deci-seconds              0..9
              8       9    direction from UTC        '+' / '-'
              9      10    hours from UTC            0..11
             10      11    minutes from UTC          0..59

            For example, Tuesday May 26, 1992 at 1:30:15 PM EDT
            would be displayed as:        07 c8 05 1a 0d 1e 0f 00
                                                                  ( 1992 -5 -26,13:30:15 )

            Note that if only local time is known, then timezone
            information (fields 8-10) is not present."

        ::= { gnApplicFileEntry 5 }

gnApplicFileType OBJECT-TYPE
        SYNTAX  INTEGER {
			idc(1),
			mux(2),
			odu(3),
			modem(4),
			boot(5),
			modemConfig(6),
			wayside(7),
			bootRom(8),
			rfuFpga(9),
			rfuConfig(10),
			mrmcTable(11),
			xc(12),
			xcErrorgen(13),
            aAux(14),
            license(15)
        }
        ACCESS  read-only
        STATUS mandatory
        DESCRIPTION
        "This is the application file type."
        ::= { gnApplicFileEntry 6 }

gnApplicFileSubType OBJECT-TYPE
        SYNTAX  DisplayString (SIZE(0..15))
        ACCESS  read-only
        STATUS mandatory
        DESCRIPTION
        "This is the application file sub type."
        ::= { gnApplicFileEntry 7 }

gnApplicFileFirmware OBJECT-TYPE
        SYNTAX  INTEGER
        ACCESS  read-only
        STATUS mandatory
        DESCRIPTION
        "This is the application file firmware."
        ::= { gnApplicFileEntry 8 }

gnApplicFileGeneralPurpose OBJECT-TYPE
        SYNTAX  INTEGER
        ACCESS  read-only
        STATUS mandatory
        DESCRIPTION
        "This is the application file General Purpose."
        ::= { gnApplicFileEntry 9 }

gnApplicFileSize OBJECT-TYPE
        SYNTAX  INTEGER
        ACCESS  read-only
        STATUS mandatory
        DESCRIPTION
        "This is the application file size in bytes."
        ::= { gnApplicFileEntry 10 }

gnApplicFileCompressed OBJECT-TYPE
        SYNTAX  INTEGER
        {
                yes(2),
                no(3)
        }        
		ACCESS  read-only
        STATUS mandatory
        DESCRIPTION
        "This is indicate the application file compress status."
        ::= { gnApplicFileEntry 11 }

gnApplicFileDssSupport OBJECT-TYPE
        SYNTAX  INTEGER
        {
                yes(2),
                no(3)
        }
        ACCESS  read-only
        STATUS mandatory
        DESCRIPTION
        "This is indicate the application file DSS support."
        ::= { gnApplicFileEntry 12 }

gnApplicFileCrcSupport OBJECT-TYPE
        SYNTAX  INTEGER
        {
                yes(2),
                no(3)
        }
        ACCESS  read-only
        STATUS mandatory
        DESCRIPTION
        "This is indicate the application file CRC support."
        ::= { gnApplicFileEntry 13 }

--//////////////////////////////////////
gnDiskCapacityData  OBJECT IDENTIFIER  ::= { gnAgn 17 } 


gnDiskUsedspace OBJECT-TYPE
        SYNTAX  INTEGER
		ACCESS  read-only
        STATUS mandatory
		DESCRIPTION
		"The ID indicates Disk Used space."
        ::= { gnDiskCapacityData 1 }

gnDiskFreespace OBJECT-TYPE
        SYNTAX  INTEGER
		ACCESS  read-only
        STATUS mandatory
		DESCRIPTION
		"The ID indicates Disk Free space."
        ::= { gnDiskCapacityData 2 }

--//////////////////////////////////////

gnUnits OBJECT IDENTIFIER ::= { ceragon 3 }

gnODU OBJECT IDENTIFIER ::=  { gnUnits 1 }

gnOduCfgTable OBJECT-TYPE
        SYNTAX  SEQUENCE OF GnOduCfgEntry
        ACCESS  not-accessible
        STATUS mandatory
        DESCRIPTION
        "This table defines the configuration of the Outdoor part
                of the system."
        ::= { gnODU 1 }

gnOduCfgEntry OBJECT-TYPE
        SYNTAX GnOduCfgEntry
        ACCESS  not-accessible
        STATUS mandatory
        DESCRIPTION
        "This is an entry in the ODU Configuration Table. This table
        contains two rows, indexed by ifIndex= 1 for local ODU and
        ifIndex = 101 for remote ODU."
        INDEX {  ifIndex }
        ::= { gnOduCfgTable 1 }


GnOduCfgEntry ::=
            SEQUENCE {
        gnOduCfgTransmitterFrequency
          INTEGER,
        gnOduCfgRLPerfMonThresh1
           INTEGER,
        gnOduCfgRLPerfMonThresh2
           INTEGER,
        gnOduCfgATPCStatus
            INTEGER,
        gnOduCfgMUTEStatus
            INTEGER,
        gnOduCfgAntennaType
            INTEGER,
        gnOduCfgTransmitLevel
            INTEGER,
        gnOduCfgRealTxFreqNumber
            INTEGER,
        gnOduCfgRealRxFreqNumber
            INTEGER,
        gnOduCfgMinTxFreqNumber
            INTEGER,
        gnOduCfgMaxTxFreqNumber
            INTEGER,
        gnOduCfgMaxTxLevel
            INTEGER,
        gnOduCfgRefRsl
            INTEGER,
        gnOduCfgForceRmtMuteTx
                INTEGER,
        gnOduCfgForceRmtMaxTx
                INTEGER,
        gnOduCfgTLPerfMonThresh1
           INTEGER,
        gnOduCfgMinRxFreqNumber
            INTEGER,
        gnOduCfgMaxRxFreqNumber
            INTEGER,
        gnOduCfgOduLoopSupport
            INTEGER,
        gnOduCfgOduModel
                INTEGER,
        gnOduCfgFreqPlanStandard
            DisplayString,
        gnOduCfgFreqDevider
            INTEGER
    }

gnOduCfgTransmitterFrequency OBJECT-TYPE
        SYNTAX  INTEGER (0..20)
        ACCESS  read-write
        STATUS mandatory
        DESCRIPTION
        "This parameter indicates the radio TX channel number.
        WRITE will change the LOCAL side only.
        Not all radios will support TX frequency change via channel numbers."
        DEFVAL { 1}
        ::= { gnOduCfgEntry 1 }

gnOduCfgRLPerfMonThresh1 OBJECT-TYPE
        SYNTAX  INTEGER (-75..-15)
        ACCESS  read-write
        STATUS mandatory
        DESCRIPTION
        "When the Received Level (RL) exceeds this threshold a
        performance monitoring RL1 counter increments."
        DEFVAL { -50}
        ::= { gnOduCfgEntry 2}

gnOduCfgRLPerfMonThresh2 OBJECT-TYPE
        SYNTAX  INTEGER (-75..-15)
        ACCESS  read-write
        STATUS mandatory
        DESCRIPTION
        "When the Received Level (RL) exceeds this threshold a
        performance monitoring RL2 counter increments."
        DEFVAL { -70}
        ::= { gnOduCfgEntry 3}


gnOduCfgATPCStatus OBJECT-TYPE
        SYNTAX  INTEGER { on(2), off(3) }
        ACCESS  read-write
        STATUS mandatory
        DESCRIPTION
        "This parameter indicates if the ATPC option is enabled or disabled."
        DEFVAL { on}
        ::= { gnOduCfgEntry 4}

gnOduCfgMUTEStatus OBJECT-TYPE
        SYNTAX  INTEGER { on(2), off(3) }
        ACCESS  read-write
        STATUS mandatory
        DESCRIPTION
        "This parameter indicates if transmitter will be in mute state.
            (Mute on -> don't transmit) "
        DEFVAL { off}
        ::= { gnOduCfgEntry 5 }

gnOduCfgAntennaType OBJECT-TYPE
        SYNTAX  INTEGER { oneFoot(2), twoFeet(3), threeFeet(4), fourFeet(5),
sixFeet(6) }
        ACCESS  read-write
        STATUS mandatory
        DESCRIPTION
        "This parameter indicates the size of the antenna used
        in the ODU. This attribute will not auto-detect the antenna size.
        It is used for the unfaded RSL calculation feature included in
CERAGONView."
        DEFVAL { oneFoot }
        ::= { gnOduCfgEntry 6 }

gnOduCfgTransmitLevel OBJECT-TYPE
        SYNTAX  INTEGER (-50..30)
        ACCESS  read-write
        STATUS mandatory
        DESCRIPTION
        "This is the transmitter output power level of the signal
        transmitted by the radios, displayed in DBM. "
        ::= { gnOduCfgEntry 7 }

gnOduCfgRealTxFreqNumber OBJECT-TYPE
        SYNTAX  INTEGER
        ACCESS  read-write
        STATUS mandatory
        DESCRIPTION
        "Identifies the RF Tx frequency. For 6, 7 and 8 bands the Tx frequency
        resolution is in kHz, for other bands the resolution is in 10kHz.
        If the Tx frequency value is over 4000000 than the band is identified
        as 6, 7 or 8G band."
        ::= { gnOduCfgEntry 8 }

gnOduCfgRealRxFreqNumber OBJECT-TYPE
        SYNTAX  INTEGER
        ACCESS  read-write
        STATUS mandatory
        DESCRIPTION
        "Identifies the RF Rx frequency. For 6, 7 and 8 bands the Rx frequency
        resolution is in kHz, for other bands the resolution is in 10kHz.
        If the Rx frequency value is over 4000000 than the band is identified
        as 6, 7 or 8G band."
        ::= { gnOduCfgEntry 9}

gnOduCfgMinTxFreqNumber OBJECT-TYPE
        SYNTAX  INTEGER (0..65535)
        ACCESS  read-only
        STATUS mandatory
        DESCRIPTION
        "This the Minimum TX frequency that the ODU can receive - Used by the
management station."
        ::= { gnOduCfgEntry 10 }

gnOduCfgMaxTxFreqNumber OBJECT-TYPE
        SYNTAX  INTEGER (0..65535)
        ACCESS  read-only
        STATUS mandatory
        DESCRIPTION
        "This the Maximum TX frequency that the ODU can receive - Used by the
management station."
        ::= { gnOduCfgEntry 11}

gnOduCfgMaxTxLevel  OBJECT-TYPE
        SYNTAX  INTEGER (0..99)
        ACCESS  read-only
        STATUS mandatory
        DESCRIPTION
        "This is the theoretical maximum level that this ODU unit
         can transmit."
        ::= { gnOduCfgEntry 12 }

gnOduCfgRefRsl OBJECT-TYPE
        SYNTAX  INTEGER (-70..-30)
        ACCESS  read-write
        STATUS mandatory
        DESCRIPTION
        "This is the received level reference, applicable when utilizing ATPC mode;
         displayed in dBm."
        ::= { gnOduCfgEntry 13 }

gnOduCfgForceRmtMuteTx OBJECT-TYPE
        SYNTAX  INTEGER { on(2), off(3) }
        ACCESS  read-write
        STATUS mandatory
        DESCRIPTION
        "When on, this parameter force the transmitter to be in mute state.
            (Mute on -> don't transmit) "
        DEFVAL { off }
        ::= { gnOduCfgEntry 14 }

gnOduCfgForceRmtMaxTx OBJECT-TYPE
        SYNTAX  INTEGER (-50..30)
        ACCESS  read-write
        STATUS mandatory
        DESCRIPTION
        "This parameter force the transmitter output power level of the signal
        transmitted by the radio. "
        ::= { gnOduCfgEntry 15 }

gnOduCfgTLPerfMonThresh1 OBJECT-TYPE
        SYNTAX  INTEGER (-10..25)
        ACCESS  read-write
        STATUS mandatory
        DESCRIPTION
        "When the Transmitted Level (TL) exceeds this threshold a
        performance monitoring TL1 counter increments."
        DEFVAL { 25 }
        ::= { gnOduCfgEntry 16}

gnOduCfgMinRxFreqNumber OBJECT-TYPE
        SYNTAX  INTEGER
        ACCESS  read-only
        STATUS mandatory
        DESCRIPTION
        "This the Minimum RX frequency that the ODU can receive - Used by the
management station."
        ::= { gnOduCfgEntry 17 }

gnOduCfgMaxRxFreqNumber OBJECT-TYPE
        SYNTAX  INTEGER
        ACCESS  read-only
        STATUS mandatory
        DESCRIPTION
        "This the Maximum RX frequency that the ODU can receive - Used by the
management station."
        ::= { gnOduCfgEntry 18}

gnOduCfgOduLoopSupport OBJECT-TYPE
        SYNTAX  INTEGER {
                notSupported(2),
                supported(3)
        }
        ACCESS  read-only
        STATUS mandatory
        DESCRIPTION
        "Indication for loopback support by the connected ODU."
        ::= { gnOduCfgEntry 19}

gnOduCfgOduModel OBJECT-TYPE
        SYNTAX  INTEGER {
                unknown(2),
                v2(3),        --phos
                v1(4)
        }
        ACCESS  read-only
        STATUS mandatory
        DESCRIPTION
        "."
        ::= { gnOduCfgEntry 20}


gnOduCfgFreqPlanStandard OBJECT-TYPE
        SYNTAX  DisplayString (SIZE(0..45))
        ACCESS  read-write
        STATUS mandatory
        DESCRIPTION
        "For the NMS use."
        ::= { gnOduCfgEntry 21}


gnOduCfgFreqDevider OBJECT-TYPE
        SYNTAX  INTEGER
        ACCESS  read-only
        STATUS mandatory
        DESCRIPTION
        "Indicates the number with which we should divide the MIB Freq value to get to the actual Freq (100 or 1000) "
        ::= { gnOduCfgEntry 22}


-- RO parameters described the state of the ODU.
gnOduStatusTable OBJECT-TYPE
        SYNTAX  SEQUENCE OF GnOduStatusEntry
        ACCESS  not-accessible
        STATUS mandatory
        DESCRIPTION
        "This table defines the status of the Outdoor unit
                of the system."
        ::= { gnODU 2 }

gnOduStatusEntry OBJECT-TYPE
        SYNTAX GnOduStatusEntry
        ACCESS  not-accessible
        STATUS mandatory
        DESCRIPTION
        "This is an entry in the ODU Status Table. This table
        contains two rows, indexed by ifIndex= 1 for local ODU and
        ifIndex = 101 for remote ODU."
        INDEX {  ifIndex }
        ::= { gnOduStatusTable 1 }


GnOduStatusEntry ::=
            SEQUENCE {
        gnOduStatusCelsiusTemp
          INTEGER,
        gnOduStatusFahrenheitTemp
          INTEGER,
        gnOduStatusTransmitLevel
          INTEGER,
            gnOduStatusReceiveLevel
                 INTEGER,
        gnOduStatusSynthesizerVCOLock
           OCTET STRING,
        gnOduStatusPowerSupply
           OCTET STRING,
        gnOduStatusClearLoopTimer
                INTEGER
    }

gnOduStatusCelsiusTemp OBJECT-TYPE
        SYNTAX  INTEGER (-50..80)
        ACCESS  read-only
        STATUS mandatory
        DESCRIPTION
        "This is the temperature of the ODU in degrees Celsius."
        ::= { gnOduStatusEntry 1 }

gnOduStatusFahrenheitTemp OBJECT-TYPE
        SYNTAX  INTEGER  (-58..176)
        ACCESS  read-only
        STATUS mandatory
        DESCRIPTION
        "This is the temperature of the ODU in degrees Fahrenheit."
        ::= { gnOduStatusEntry 2 }

gnOduStatusTransmitLevel OBJECT-TYPE
        SYNTAX  INTEGER (-99..30)
        ACCESS  read-only
        STATUS mandatory
        DESCRIPTION
        "This is the transmit level of the signal transmitted by the radios
         transmitter, displayed in DBM."
        ::= { gnOduStatusEntry 3 }

gnOduStatusReceiveLevel OBJECT-TYPE
        SYNTAX  INTEGER (-99..-15)
        ACCESS  read-only
        STATUS mandatory
        DESCRIPTION
        "This is the receive level of the signal transmitted by the radios
         transmitter, displayed in DBM."
        ::= { gnOduStatusEntry 4}


gnOduStatusSynthesizerVCOLock OBJECT-TYPE
        SYNTAX  OCTET STRING(SIZE(1))
        ACCESS  read-only
        STATUS mandatory
        DESCRIPTION
        "This octet represents the ODU status as follows (bit 1, LSB):
        bit 1 on = TX IF synthesizer
        bit 2 on = RX IF synthesizer
        bit 3 on = Xband synthesizer
        bit 4 on = History TX IF synthesizer
        bit 5 on = History RX IF synthesizer
        bit 6 on = History Xband synthesizer  "
        ::= { gnOduStatusEntry 5}

gnOduStatusPowerSupply OBJECT-TYPE
        SYNTAX OCTET STRING(SIZE(1))
        ACCESS  read-only
        STATUS mandatory
        DESCRIPTION
        "This octet represents the status of the power
        supplies of the ODU:
        bit 1 on = +5V faulty
        bit 2 on = +8V faulty
        bit 3 on = +12V faulty
        bit 4 on = -12V faulty."
        ::= { gnOduStatusEntry 6}

gnOduStatusClearLoopTimer OBJECT-TYPE
        SYNTAX INTEGER (0..1440)
        ACCESS  read-only
        STATUS mandatory
        DESCRIPTION
        "This variable indicates the remaining time (in minutes)
        till the relevant odu loopback timer will be expired.
        when starting a loopback and the value of gnGenCfgClearLoopTimeout is x,
        the gnOduStatusClearLoopTimer will be also x, after one minute it will be x-1, etc."
        ::= { gnOduStatusEntry 7}


-- This part of the MIB deals with the performance monitoring
-- of the ODU part of the system.
gnOduMonitor  OBJECT IDENTIFIER ::= { gnODU 3 }
-- This part is built according the habits in the telcos/datacom community.
-- There are three tables:
-- gnOduMonCurrTable that keeps the counters of the current 15 min interval.
-- gnOduMonIntervalTable that keeps the counters of the past 96 intervals.
-- gnOduMonDayTable that keeps the counters of the past 30 days.

gnOduMonCurrTable OBJECT-TYPE
        SYNTAX  SEQUENCE OF GnOduMonCurrEntry
        ACCESS  not-accessible
        STATUS mandatory
        DESCRIPTION
        "This table defines/keeps the counters of the current 15 min interval."
        ::= { gnOduMonitor 1 }

gnOduMonCurrEntry OBJECT-TYPE
        SYNTAX GnOduMonCurrEntry
        ACCESS  not-accessible
        STATUS mandatory
        DESCRIPTION
        "This is an entry in the Current Interval Table. This table
        contains two rows, indexed by ifIndex= 1 for local ODU and
        ifIndex = 101 for remote ODU."
        INDEX {  ifIndex }
        ::= { gnOduMonCurrTable 1 }

GnOduMonCurrEntry ::=
            SEQUENCE {
        gnOduMonCurrMinRL
          INTEGER,
           gnOduMonCurrMaxRL
          INTEGER,
        gnOduMonCurrTLThresh1Exceed
          Counter,
        gnOduMonCurrRLThresh1Exceed
          Counter,
        gnOduMonCurrRLThresh2Exceed
          Counter,
        gnOduMonCurrDayMinRL
           INTEGER,
        gnOduMonCurrDayMaxRL
           INTEGER,
        gnOduMonCurrDayTLThresh1Exceed
          Counter,
        gnOduMonCurrDayRLThresh1Exceed
          Counter,
        gnOduMonCurrDayRLThresh2Exceed
          Counter,
        gnOduMonCurrMinTL
          INTEGER,
           gnOduMonCurrMaxTL
          INTEGER,
        gnOduMonCurrDayMinTL
          INTEGER,
           gnOduMonCurrDayMaxTL
          INTEGER
}


gnOduMonCurrMinRL OBJECT-TYPE
        SYNTAX  INTEGER
        ACCESS  read-only
        STATUS mandatory
        DESCRIPTION
        "The minimum received signal level (RL) in the current 15 minute interval.
(in DBM) "
        ::= { gnOduMonCurrEntry 1 }


gnOduMonCurrMaxRL OBJECT-TYPE
        SYNTAX  INTEGER
        ACCESS  read-only
        STATUS mandatory
        DESCRIPTION
        "The maximum received signal level (RL) in the current 15 minute interval.
(in DBM). "
        ::= { gnOduMonCurrEntry 2 }

gnOduMonCurrTLThresh1Exceed OBJECT-TYPE
        SYNTAX  Counter
        ACCESS  read-only
        STATUS mandatory
        DESCRIPTION
        " The number of seconds TL exceeded the TL1
         threshold in the last 15 minutes."
        ::= { gnOduMonCurrEntry 3 }


gnOduMonCurrRLThresh1Exceed OBJECT-TYPE
        SYNTAX  Counter
        ACCESS  read-only
        STATUS mandatory
        DESCRIPTION
        " The number of seconds RL exceeded the RL1
         threshold in the last 15 minutes."
        ::= { gnOduMonCurrEntry 4 }

gnOduMonCurrRLThresh2Exceed OBJECT-TYPE
        SYNTAX  Counter
        ACCESS  read-only
        STATUS mandatory
        DESCRIPTION
        " The number of seconds RL exceeded the RL2
         threshold in the last 15 minutes."
        ::= { gnOduMonCurrEntry 5 }


gnOduMonCurrDayMinRL OBJECT-TYPE
        SYNTAX  INTEGER
        ACCESS  read-only
        STATUS mandatory
        DESCRIPTION
        " The minimum Receive Level (in DBM).
        in the last 24 hours."
        ::= { gnOduMonCurrEntry 6}


gnOduMonCurrDayMaxRL OBJECT-TYPE
        SYNTAX  INTEGER
        ACCESS  read-only
        STATUS mandatory
        DESCRIPTION
        " The maximum Receive Level (in DBM).
        in the last 24 hours."
        ::= { gnOduMonCurrEntry 7}

gnOduMonCurrDayTLThresh1Exceed OBJECT-TYPE
        SYNTAX  Counter
        ACCESS  read-only
        STATUS mandatory
        DESCRIPTION
        " The number of seconds TL exceeded the TL1 threshold
        in the last 24 hours."
        ::= { gnOduMonCurrEntry 8}


gnOduMonCurrDayRLThresh1Exceed OBJECT-TYPE
        SYNTAX  Counter
        ACCESS  read-only
        STATUS mandatory
        DESCRIPTION
        " The number of seconds RL exceeded the RL1 threshold
        in the last 24 hours."
        ::= { gnOduMonCurrEntry 9 }

gnOduMonCurrDayRLThresh2Exceed OBJECT-TYPE
        SYNTAX  Counter
        ACCESS  read-only
        STATUS mandatory
        DESCRIPTION
        " The number of seconds RL exceeded the RL2 threshold
        in the last 24 hours."
        ::= { gnOduMonCurrEntry 10 }

gnOduMonCurrMinTL OBJECT-TYPE
        SYNTAX  INTEGER
        ACCESS  read-only
        STATUS mandatory
        DESCRIPTION
        "The minimum transmitted signal level (TL) in the current 15 minute interval.
(in DBM) "
        ::= { gnOduMonCurrEntry 11 }


gnOduMonCurrMaxTL OBJECT-TYPE
        SYNTAX  INTEGER
        ACCESS  read-only
        STATUS mandatory
        DESCRIPTION
        "The maximum transmitted signal level (TL) in the current 15 minute interval.
(in DBM). "
        ::= { gnOduMonCurrEntry 12 }

gnOduMonCurrDayMinTL OBJECT-TYPE
        SYNTAX  INTEGER
        ACCESS  read-only
        STATUS mandatory
        DESCRIPTION
        " The minimum Transmitted Level (in DBM).
        in the last 24 hours."
        ::= { gnOduMonCurrEntry 13}


gnOduMonCurrDayMaxTL OBJECT-TYPE
        SYNTAX  INTEGER
        ACCESS  read-only
        STATUS mandatory
        DESCRIPTION
        " The maximum Transmitted Level (in DBM).
        in the last 24 hours."
        ::= { gnOduMonCurrEntry 14}



gnOduMonIntervalTable OBJECT-TYPE
        SYNTAX  SEQUENCE OF GnOduMonIntervalEntry
        ACCESS  not-accessible
        STATUS mandatory
        DESCRIPTION
        "This table defines/keeps the counters of the 96 last intervals of 15 min."
        ::= { gnOduMonitor 2 }

gnOduMonIntervalEntry OBJECT-TYPE
        SYNTAX GnOduMonIntervalEntry
        ACCESS  not-accessible
        STATUS mandatory
        DESCRIPTION
        "This is an entry in the Interval Table. This table
        is indexed by ifIndex= 1 for local ODU and
        ifIndex = 101 for remote ODU and by interval idx"
        INDEX {  ifIndex, gnOduMonIntervalIdx }
        ::= { gnOduMonIntervalTable 1 }

GnOduMonIntervalEntry ::=
            SEQUENCE {
        gnOduMonIntervalIdx
          INTEGER,
        gnOduMonIntervalMinRL
          INTEGER,
           gnOduMonIntervalMaxRL
          INTEGER,
        gnOduMonIntervalTLThresh1Exceed
          Counter,
    gnOduMonIntervalEvent
           OCTET STRING,
        gnOduMonIntervalRLThresh1Exceed
          Counter,
        gnOduMonIntervalRLThresh2Exceed
          Counter,
        gnOduMonIntervalMinTL
          INTEGER,
           gnOduMonIntervalMaxTL
          INTEGER
}

gnOduMonIntervalIdx OBJECT-TYPE
        SYNTAX  INTEGER (1..96)
        ACCESS  read-only
        STATUS mandatory
        DESCRIPTION
        " The interval number to which this row is related. "
        ::= { gnOduMonIntervalEntry 1 }


gnOduMonIntervalMinRL OBJECT-TYPE
        SYNTAX  INTEGER
        ACCESS  read-only
        STATUS mandatory
        DESCRIPTION
        " The minimum RL in a 15 minutes interval. (in DBM). "
        ::= { gnOduMonIntervalEntry 2 }

gnOduMonIntervalMaxRL OBJECT-TYPE
        SYNTAX  INTEGER
        ACCESS  read-only
        STATUS mandatory
        DESCRIPTION
        " The maximum RL in a 15 minutes interval. (in DBM). "
        ::= { gnOduMonIntervalEntry 3 }

gnOduMonIntervalTLThresh1Exceed OBJECT-TYPE
        SYNTAX  Counter
        ACCESS  read-only
        STATUS mandatory
        DESCRIPTION
        " The number of seconds TL exceeded the TL1
         threshold in a 15 minutes interval."
        ::= { gnOduMonIntervalEntry 4 }


gnOduMonIntervalEvent OBJECT-TYPE
        SYNTAX  OCTET STRING (SIZE(1))
        ACCESS  read-only
        STATUS mandatory
        DESCRIPTION
        " Events
         bit 1 = CommDisc.
         bit 2 = CommCon
     bit 3 = ATPC2Max.
         bit 4 = ATPC2Norm.
         Included for future development, not currently supported."
        ::= { gnOduMonIntervalEntry 5 }

gnOduMonIntervalRLThresh1Exceed OBJECT-TYPE
        SYNTAX  Counter
        ACCESS  read-only
        STATUS mandatory
        DESCRIPTION
        " The number of seconds RL exceeded the RL1
         threshold in a 15 minutes interval."
        ::= { gnOduMonIntervalEntry 6 }

gnOduMonIntervalRLThresh2Exceed OBJECT-TYPE
        SYNTAX  Counter
        ACCESS  read-only
        STATUS mandatory
        DESCRIPTION
        " The number of seconds RL exceeded the RL2
         threshold in a 15 minutes interval."
        ::= { gnOduMonIntervalEntry 7 }

gnOduMonIntervalMinTL OBJECT-TYPE
        SYNTAX  INTEGER
        ACCESS  read-only
        STATUS mandatory
        DESCRIPTION
        " The minimum TL in a 15 minutes interval. (in DBM). "
        ::= { gnOduMonIntervalEntry 8 }

gnOduMonIntervalMaxTL OBJECT-TYPE
        SYNTAX  INTEGER
        ACCESS  read-only
        STATUS mandatory
        DESCRIPTION
        " The maximum TL in a 15 minutes interval. (in DBM). "
        ::= { gnOduMonIntervalEntry 9 }



gnOduMonDayTable OBJECT-TYPE
        SYNTAX  SEQUENCE OF GnOduMonDayEntry
        ACCESS  not-accessible
        STATUS mandatory
        DESCRIPTION
        "This table defines/keeps the counters of 96 intervals of 15 min."
        ::= { gnOduMonitor 3 }

gnOduMonDayEntry OBJECT-TYPE
        SYNTAX GnOduMonDayEntry
        ACCESS  not-accessible
        STATUS mandatory
        DESCRIPTION
        "This is an entry in the Days Table. This table
        is indexed by ifIndex= 1 for local ODU and
        ifIndex = 101 for remote ODU and by day idx.
        gnOduMonDayIdx = 1 is one day from now,
        gnOduMonDayIdx = 2 is two days from now, and so on..."
        INDEX {  ifIndex, gnOduMonDayIdx }
        ::= { gnOduMonDayTable 1 }

GnOduMonDayEntry ::=
            SEQUENCE {
        gnOduMonDayIdx
          INTEGER,
        gnOduMonDayMinRL
           INTEGER,
        gnOduMonDayMaxRL
           INTEGER,
        gnOduMonDayTLThresh1Exceed
          Counter,
        gnOduMonDayRLThresh1Exceed
          Counter,
        gnOduMonDayRLThresh2Exceed
          Counter,
        gnOduMonDayMinTL
           INTEGER,
        gnOduMonDayMaxTL
           INTEGER
}

gnOduMonDayIdx OBJECT-TYPE
        SYNTAX  INTEGER (1..30)
        ACCESS  read-only
        STATUS mandatory
        DESCRIPTION
        " The interval number to which this row is related. "
        ::= { gnOduMonDayEntry 1 }


gnOduMonDayMinRL OBJECT-TYPE
        SYNTAX  INTEGER
        ACCESS  read-only
        STATUS mandatory
        DESCRIPTION
        " The minimum Receive Level (in DBM).
        in a 24 hour interval."
        ::= { gnOduMonDayEntry 2}

gnOduMonDayMaxRL OBJECT-TYPE
        SYNTAX  INTEGER
        ACCESS  read-only
        STATUS mandatory
        DESCRIPTION
        " The maximum Receive Level (in DBM).
        in a 24 hour interval."
        ::= { gnOduMonDayEntry 3}

gnOduMonDayTLThresh1Exceed OBJECT-TYPE
        SYNTAX  Counter
        ACCESS  read-only
        STATUS mandatory
        DESCRIPTION
        " The number of seconds TL exceeded the TL1 threshold
        in a 24 hour interval."
        ::= { gnOduMonDayEntry 4}


gnOduMonDayRLThresh1Exceed OBJECT-TYPE
        SYNTAX  Counter
        ACCESS  read-only
        STATUS mandatory
        DESCRIPTION
        " The number of seconds RL exceeded the RL1 threshold
        in a 24 hour interval."
        ::= { gnOduMonDayEntry 5}


gnOduMonDayRLThresh2Exceed OBJECT-TYPE
        SYNTAX  Counter
        ACCESS  read-only
        STATUS mandatory
        DESCRIPTION
        " The number of seconds RL exceeded the RL2 threshold
        in a 24 hour interval."
        ::= { gnOduMonDayEntry 6}

gnOduMonDayMinTL OBJECT-TYPE
        SYNTAX  INTEGER
        ACCESS  read-only
        STATUS mandatory
        DESCRIPTION
        " The minimum Transmit Level (in DBM).
        in a 24 hour interval."
        ::= { gnOduMonDayEntry 7}

gnOduMonDayMaxTL OBJECT-TYPE
        SYNTAX  INTEGER
        ACCESS  read-only
        STATUS mandatory
        DESCRIPTION
        " The maximum Transmit Level (in DBM).
        in a 24 hour interval."
        ::= { gnOduMonDayEntry 8}



gnOduCfgXTable OBJECT-TYPE
        SYNTAX  SEQUENCE OF GnOduCfgXEntry
        ACCESS  not-accessible
        STATUS mandatory
        DESCRIPTION
        "This table defines the configuration of the Outdoor part
                of the system."
        ::= { gnODU 4 }

gnOduCfgXEntry OBJECT-TYPE
        SYNTAX GnOduCfgXEntry
        ACCESS  not-accessible
        STATUS mandatory
        DESCRIPTION
        "This is an entry in the ODU Configuration Table. This table
        contains two rows, indexed by gnOduCfgXId= 3 for drawer1 ODU and
        gnOduCfgXId = 4 for drawer2 ODU."
        INDEX {  gnOduCfgXId }
        ::= { gnOduCfgXTable 1 }


GnOduCfgXEntry ::=
            SEQUENCE {
        gnOduCfgXId
                INTEGER,
    gnOduCfgXTxFreqNumLocalRemote
          INTEGER,
        gnOduCfgXRLPerfMonThresh1
           INTEGER,
        gnOduCfgXRLPerfMonThresh2
           INTEGER,
        gnOduCfgXATPCStatus
            INTEGER,
        gnOduCfgXMUTEStatus
            INTEGER,
        gnOduCfgXAntennaType
            INTEGER,
        gnOduCfgXTransmitLevel
            INTEGER,
        gnOduCfgXRealTxFreqNumber
            INTEGER,
        gnOduCfgXRealRxFreqNumber
            INTEGER,
        gnOduCfgXMinTxFreqNumber
            INTEGER,
        gnOduCfgXMaxTxFreqNumber
            INTEGER,
        gnOduCfgXMaxTxLevel
            INTEGER,
        gnOduCfgXRefRsl
            INTEGER,
        gnOduCfgXForceRmtMuteTx
                INTEGER,
        gnOduCfgXForceRmtMaxTx
                INTEGER,
        gnOduCfgXTLPerfMonThresh1
           INTEGER,
        gnOduCfgXOperation
                INTEGER,
        gnOduCfgXODUSerialNumber
                DisplayString,
        gnOduCfgXChannelBandwidth
                INTEGER,
        gnOduCfgXMinRxFreqNumber
            INTEGER,
        gnOduCfgXMaxRxFreqNumber
            INTEGER,
    gnOduCfgXRxFreqNumLocalRemote
            INTEGER,
        gnOduCfgXOduLoopSupport
                INTEGER,
        gnOduCfgXOduModel
                INTEGER,
        gnOduCfgXFreqPlanStandard
                DisplayString,
        gnOduCfgXFreqDevider
                INTEGER,
        gnOduCfgXLoopbackOption
                INTEGER,
        gnOduCfgXxpicClockMode
                INTEGER,
        gnOduCfgXUnfadedReferenceRsl
            INTEGER,
        gnOduCfgXRfuMode
            INTEGER,
        gnOduCfgXRslRouteToConnector
            INTEGER,
        gnOduCfgXDelayCalibrationOperation
            INTEGER,
        gnOduCfgXDelayCalibrationValue
                INTEGER,
        gnOduCfgXDelayCalibrationWgType
                DisplayString,
        gnOduCfgXOduLog
                INTEGER,
        gnOduCfgXOduLogPeriod
                INTEGER,
        gnOduCfgXXpiPerfMonThresh
           INTEGER
    }

gnOduCfgXId OBJECT-TYPE
        SYNTAX  INTEGER
        {
                drawer1(3),
                drawer2(4)
        }
    ACCESS  read-only
           STATUS mandatory
    DESCRIPTION
    " "
    ::= { gnOduCfgXEntry 1 }

gnOduCfgXTxFreqNumLocalRemote OBJECT-TYPE
        SYNTAX  INTEGER
        ACCESS  read-write
        STATUS mandatory
        DESCRIPTION
        "Indicates the radio transmit frequency, displayed in
        1/100 MHz. WRITE changes the local and remote sides. Only for systems that
        support        frequency configuration (Not channel)."
        ::= { gnOduCfgXEntry 2}

gnOduCfgXRLPerfMonThresh1 OBJECT-TYPE
        SYNTAX  INTEGER (-75..-15)
        ACCESS  read-write
        STATUS mandatory
        DESCRIPTION
        "When the Received Level (RL) exceeds this threshold a
        performance monitoring RL1 counter increments."
        DEFVAL { -50}
        ::= { gnOduCfgXEntry 3}

gnOduCfgXRLPerfMonThresh2 OBJECT-TYPE
        SYNTAX  INTEGER (-75..-15)
        ACCESS  read-write
        STATUS mandatory
        DESCRIPTION
        "When the Received Level (RL) exceeds this threshold a
        performance monitoring RL2 counter increments."
        DEFVAL { -70}
        ::= { gnOduCfgXEntry 4}


gnOduCfgXATPCStatus OBJECT-TYPE
        SYNTAX  INTEGER { on(2), off(3) }
        ACCESS  read-write
        STATUS mandatory
        DESCRIPTION
        "This parameter indicates if the ATPC option is enabled or disabled."
        DEFVAL { on}
        ::= { gnOduCfgXEntry 5}

gnOduCfgXMUTEStatus OBJECT-TYPE
        SYNTAX  INTEGER { on(2), off(3) }
        ACCESS  read-write
        STATUS mandatory
        DESCRIPTION
        "This parameter indicates if transmitter will be in mute state.
            (Mute on -> don't transmit) "
        DEFVAL { off}
        ::= { gnOduCfgXEntry 6 }

gnOduCfgXAntennaType OBJECT-TYPE
        SYNTAX  INTEGER { oneFoot(2), twoFeet(3), threeFeet(4), fourFeet(5),
sixFeet(6) }
        ACCESS  read-write
        STATUS mandatory
        DESCRIPTION
        "This parameter indicates the size of the antenna used
        in the ODU. This attribute will not auto-detect the antenna size.
        It is used for the unfaded RSL calculation feature included in
CERAGONView."
        DEFVAL { oneFoot }
        ::= { gnOduCfgXEntry 7 }

gnOduCfgXTransmitLevel OBJECT-TYPE
        SYNTAX  INTEGER (-50..34)
        ACCESS  read-write
        STATUS mandatory
        DESCRIPTION
        "This is the transmitter output power level of the signal
        transmitted by the radios, displayed in DBM. "
        ::= { gnOduCfgXEntry 8 }

gnOduCfgXRealTxFreqNumber OBJECT-TYPE
        SYNTAX  INTEGER
        ACCESS  read-write
        STATUS mandatory
        DESCRIPTION
        "Identifies the RF Tx frequency. For 6, 7 and 8 bands the Tx frequency
        resolution is in kHz, for other bands the resolution is in 10kHz.
        If the Tx frequency value is over 4000000 than the band is identified
        as 6, 7 or 8G band."
        ::= { gnOduCfgXEntry 9 }

gnOduCfgXRealRxFreqNumber OBJECT-TYPE
        SYNTAX  INTEGER
        ACCESS  read-write
        STATUS mandatory
        DESCRIPTION
        "Identifies the RF Rx frequency. For 6, 7 and 8 bands the Rx frequency
        resolution is in kHz, for other bands the resolution is in 10kHz.
        If the Rx frequency value is over 4000000 than the band is identified
        as 6, 7 or 8G band."
        ::= { gnOduCfgXEntry 10}

gnOduCfgXMinTxFreqNumber OBJECT-TYPE
        SYNTAX  INTEGER (0..65535)
        ACCESS  read-only
        STATUS mandatory
        DESCRIPTION
        "This the Minimum TX frequency that the ODU can receive - Used by the
management station."
        ::= { gnOduCfgXEntry 11 }

gnOduCfgXMaxTxFreqNumber OBJECT-TYPE
        SYNTAX  INTEGER (0..65535)
        ACCESS  read-only
        STATUS mandatory
        DESCRIPTION
        "This the Maximum TX frequency that the ODU can receive - Used by the
management station."
        ::= { gnOduCfgXEntry 12}

gnOduCfgXMaxTxLevel  OBJECT-TYPE
        SYNTAX  INTEGER (0..99)
        ACCESS  read-only
        STATUS mandatory
        DESCRIPTION
        "This is the theoretical maximum level that this ODU unit
         can transmit."
        ::= { gnOduCfgXEntry 13 }

gnOduCfgXRefRsl OBJECT-TYPE
        SYNTAX  INTEGER (-70..-30)
        ACCESS  read-write
        STATUS mandatory
        DESCRIPTION
        "This is the received level reference, applicable when utilizing ATPC mode;
         displayed in dBm."
        ::= { gnOduCfgXEntry 14 }

gnOduCfgXForceRmtMuteTx OBJECT-TYPE
        SYNTAX  INTEGER { on(2), off(3) }
        ACCESS  read-write
        STATUS mandatory
        DESCRIPTION
        "When on, this parameter force the transmitter to be in mute state.
            (Mute on -> don't transmit) "
        DEFVAL { off }
        ::= { gnOduCfgXEntry 15 }

gnOduCfgXForceRmtMaxTx OBJECT-TYPE
        SYNTAX  INTEGER (-50..30)
        ACCESS  read-write
        STATUS mandatory
        DESCRIPTION
        "This parameter force the transmitter output power level of the signal
        transmitted by the radio. "
        ::= { gnOduCfgXEntry 16 }

gnOduCfgXTLPerfMonThresh1 OBJECT-TYPE
        SYNTAX  INTEGER (-10..25)
        ACCESS  read-write
        STATUS mandatory
        DESCRIPTION
        "When the Transmitted Level (TL) exceeds this threshold a
        performance monitoring TL1 counter increments."
        DEFVAL { 25 }
        ::= { gnOduCfgXEntry 17 }

gnOduCfgXOperation OBJECT-TYPE
        SYNTAX  INTEGER
        {
                noOperation(2),
        setOduDefaultConf(3),
        resetODU(4),
                swResetODU(5)
        }
        ACCESS  read-write
        STATUS mandatory
        DESCRIPTION
                "This parameter allows to perform ODU operations.
                  (3) will SET all ODU default configurations.
                  (4) will implement ODU reset."
        DEFVAL { noOperation }
        ::= { gnOduCfgXEntry 18 }

gnOduCfgXODUSerialNumber OBJECT-TYPE
        SYNTAX  DisplayString(SIZE(0..20))
        ACCESS  read-only
        STATUS mandatory
        DESCRIPTION
        "This is the ODU serial number - up to 20 characters "
        ::= { gnOduCfgXEntry 19 }

gnOduCfgXChannelBandwidth OBJECT-TYPE
        SYNTAX  INTEGER
        ACCESS  read-only
        STATUS mandatory
        DESCRIPTION
        "The TX channel bandwidth, displayed in 1/100 MHz.
        For example:
        An STM-1 ETSI TX channel bandwidth of 56MHz is displayed as the value 5600."
        ::= { gnOduCfgXEntry 20 }

gnOduCfgXMinRxFreqNumber OBJECT-TYPE
        SYNTAX  INTEGER
        ACCESS  read-only
        STATUS mandatory
        DESCRIPTION
        "This the Minimum RX frequency that the ODU can receive - Used by the
management station."
        ::= { gnOduCfgXEntry 21 }

gnOduCfgXMaxRxFreqNumber OBJECT-TYPE
        SYNTAX  INTEGER
        ACCESS  read-only
        STATUS mandatory
        DESCRIPTION
        "This the Maximum RX frequency that the ODU can receive - Used by the
management station."
        ::= { gnOduCfgXEntry 22}


gnOduCfgXRxFreqNumLocalRemote OBJECT-TYPE
        SYNTAX  INTEGER
        ACCESS  read-write
        STATUS mandatory
        DESCRIPTION
        "Indicates the radio transmit frequency, displayed in
        1/100 MHz. WRITE changes the local and remote sides. Only for systems that
        support        frequency configuration (Not channel)."
        ::= { gnOduCfgXEntry 23}

gnOduCfgXOduLoopSupport OBJECT-TYPE
        SYNTAX  INTEGER {
                notSupported(2),
                supported(3)
        }
        ACCESS  read-only
        STATUS mandatory
        DESCRIPTION
        "Inidcation for loopback support by the connected ODU."
        ::= { gnOduCfgXEntry 24}

gnOduCfgXOduModel OBJECT-TYPE
        SYNTAX  INTEGER {
                unknown(2),
                v2(3), --Phos ODU
                v1(4), --Fibe ODU
                v3(5)  -- Titan ODU
        }
        ACCESS  read-only
        STATUS mandatory
        DESCRIPTION
        "."
        ::= { gnOduCfgXEntry 25}


gnOduCfgXFreqPlanStandard OBJECT-TYPE
        SYNTAX  DisplayString
        ACCESS  read-write
        STATUS mandatory
        DESCRIPTION
        "For the NMS use."
        ::= { gnOduCfgXEntry 26}


gnOduCfgXFreqDevider OBJECT-TYPE
        SYNTAX  INTEGER
        ACCESS  read-only
        STATUS mandatory
        DESCRIPTION
        "Indicates the number with which we should divide the MIB Freq value to get to the actual Freq (100 or 1000) "
        ::= { gnOduCfgXEntry 27}


gnOduCfgXLoopbackOption OBJECT-TYPE
        SYNTAX  INTEGER {
                noloopback(2),
                interfaceInterLoop(3)
                }
        ACCESS  read-write
        STATUS mandatory
        DESCRIPTION
        " This parameter enable the user to activate an ODU loopback ."
        DEFVAL { noloopback }
        ::= { gnOduCfgXEntry  28 }

gnOduCfgXxpicClockMode OBJECT-TYPE
        SYNTAX  INTEGER {
                standAlone(2),
                masterClock(3),
                slaveClock(4)
                }
        ACCESS  read-only
        STATUS mandatory
        DESCRIPTION "This is the status of the xpic clock mode."
        ::= { gnOduCfgXEntry  29 }

gnOduCfgXUnfadedReferenceRsl OBJECT-TYPE
        SYNTAX  INTEGER (-70..-15)
        ACCESS  read-write
        STATUS mandatory
        DESCRIPTION
        "This is used for the unfaded RSL calculation feature included in
        CERAGONView."
        DEFVAL { -70 }
        ::= { gnOduCfgXEntry 30 }

gnOduCfgXRfuMode OBJECT-TYPE
        SYNTAX  INTEGER
        {
        main(2),
        diversity(3),
        combined(4)
        }
        ACCESS  read-write
        STATUS mandatory
        DESCRIPTION
        "The RX mode of operation."
        DEFVAL {main }
        ::= { gnOduCfgXEntry 31 }

gnOduCfgXRslRouteToConnector OBJECT-TYPE
        SYNTAX  INTEGER
        {
        main(2),
        diversity(3)
        }
        ACCESS  read-write
        STATUS mandatory
        DESCRIPTION
        "Choose the receive level signal for the RSL connector."
        DEFVAL {main }
        ::= { gnOduCfgXEntry 32 }

gnOduCfgXDelayCalibrationOperation OBJECT-TYPE
        SYNTAX  INTEGER
        {
        noAction(2),
        activate(3),
        error(4)
        }
        ACCESS  read-write
        STATUS mandatory
        DESCRIPTION
        "This parameter enables launching a delay calibration parameters calculation."
        DEFVAL {noAction }
        ::= { gnOduCfgXEntry 33 }

gnOduCfgXDelayCalibrationValue OBJECT-TYPE
        SYNTAX INTEGER (-130..130)
        ACCESS  read-write
        STATUS mandatory
        DESCRIPTION
        "This parameter indicates the delay calibration result and delay calibration override value.
         values are between -130 to 130."
        ::= { gnOduCfgXEntry 34 }

gnOduCfgXDelayCalibrationWgType OBJECT-TYPE
        SYNTAX  DisplayString (SIZE(0..45))
        ACCESS  read-write
        STATUS mandatory
        DESCRIPTION
        "Delay Calibration WG Type For the NMS use."
        ::= { gnOduCfgXEntry 35 }

gnOduCfgXOduLog OBJECT-TYPE
        SYNTAX  INTEGER
        {
                enable(2),
                disable(3)
        }
        ACCESS  read-write
        STATUS mandatory
        DESCRIPTION
        "This parameter enable the user to activate ODU log."
        ::= { gnOduCfgXEntry 36 }

gnOduCfgXOduLogPeriod OBJECT-TYPE
        SYNTAX  INTEGER (1..600)
        ACCESS  read-write
        STATUS mandatory
        DESCRIPTION
        "This parameter enable the user to chose the log peroid (in sec)."
        ::= { gnOduCfgXEntry 37 }

gnOduCfgXXpiPerfMonThresh OBJECT-TYPE
        SYNTAX  INTEGER (10..30)
        ACCESS  read-write
        STATUS mandatory
        DESCRIPTION
        "When the Received XPI beneath this threshold a
        performance monitoring XPI counter increments (future develope)."
        DEFVAL {20}
        ::= { gnOduCfgXEntry 38}

-- RO parameters described the state of the ODU.
gnOduStatusXTable OBJECT-TYPE
        SYNTAX  SEQUENCE OF GnOduStatusXEntry
        ACCESS  not-accessible
        STATUS mandatory
        DESCRIPTION
        "This table defines the status of the Outdoor unit
                of the system."
        ::= { gnODU 5 }

gnOduStatusXEntry OBJECT-TYPE
        SYNTAX GnOduStatusXEntry
        ACCESS  not-accessible
        STATUS mandatory
        DESCRIPTION
        "This is an entry in the ODU Status Table. This table
        contains two rows, indexed by gnOduStatusXId= 3 for drawer1 ODU
        and gnOduStatusXId = 4 for drawer2 ODU."
        INDEX {  gnOduStatusXId }
        ::= { gnOduStatusXTable 1 }


GnOduStatusXEntry ::=
            SEQUENCE {
        gnOduStatusXId
                INTEGER,
        gnOduStatusXCelsiusTemp
          INTEGER,
        gnOduStatusXFahrenheitTemp
          INTEGER,
        gnOduStatusXTransmitLevel
          INTEGER,
    gnOduStatusXReceiveLevel
                 INTEGER,
        gnOduStatusXSynthesizerVCOLock
           OCTET STRING,
        gnOduStatusXPowerSupply
           OCTET STRING,
        gnOduStatusXIfcSupported
                INTEGER,
        gnOduStatusXRslDiversity
                INTEGER,
        gnOduStatusXRslCombined
                INTEGER,
        gnOduStatusXRfuAddress
                INTEGER,
        gnOduStatusXMinTransmitLevel
                INTEGER,
        gnOduStatusXOduSWVer
                DisplayString,
        gnOduStatusXOduSWPostVer
                DisplayString,
        gnOduStatusXRfuFwVer
           DisplayString,
		gnOduStatusXValidIntervals
           INTEGER
    }

gnOduStatusXId OBJECT-TYPE
        SYNTAX  INTEGER
        {
                drawer1(3),
                drawer2(4)
        }
    ACCESS  read-only
           STATUS mandatory
    DESCRIPTION
    " "
    ::= { gnOduStatusXEntry 1 }

gnOduStatusXCelsiusTemp OBJECT-TYPE
        SYNTAX  INTEGER (-70..80)
        ACCESS  read-only
        STATUS mandatory
        DESCRIPTION
        "This is the temperature of the ODU in degrees Celsius."
        ::= { gnOduStatusXEntry 2 }

gnOduStatusXFahrenheitTemp OBJECT-TYPE
        SYNTAX  INTEGER  (-58..176)
        ACCESS  read-only
        STATUS mandatory
        DESCRIPTION
        "This is the temperature of the ODU in degrees Fahrenheit."
        ::= { gnOduStatusXEntry 3 }

gnOduStatusXTransmitLevel OBJECT-TYPE
        SYNTAX  INTEGER (-99..34)
        ACCESS  read-only
        STATUS mandatory
        DESCRIPTION
        "This is the transmit level of the signal transmitted by the radios
         transmitter, displayed in DBM."
        ::= { gnOduStatusXEntry 4 }

gnOduStatusXReceiveLevel OBJECT-TYPE
        SYNTAX  INTEGER (-99..-15)
        ACCESS  read-only
        STATUS mandatory
        DESCRIPTION
        "This is the receive level of the signal transmitted by the radios
         transmitter, displayed in DBM."
        ::= { gnOduStatusXEntry 5}


gnOduStatusXSynthesizerVCOLock OBJECT-TYPE
        SYNTAX  OCTET STRING(SIZE(1))
        ACCESS  read-only
        STATUS mandatory
        DESCRIPTION
        "This octet represents the ODU status as follows (bit 1, LSB):
        bit 1 on = TX IF synthesizer
        bit 2 on = RX IF synthesizer
        bit 3 on = Xband synthesizer
        bit 4 on = History TX IF synthesizer
        bit 5 on = History RX IF synthesizer
        bit 6 on = History Xband synthesizer  "
        ::= { gnOduStatusXEntry 6}

gnOduStatusXPowerSupply OBJECT-TYPE
        SYNTAX OCTET STRING(SIZE(1))
        ACCESS  read-only
        STATUS mandatory
        DESCRIPTION
        "This octet represents the status of the power
        supplies of the ODU:
        bit 1 on = +5V faulty
        bit 2 on = +8V faulty
        bit 3 on = +12V faulty
        bit 4 on = -12V faulty."
        ::= { gnOduStatusXEntry 7}

gnOduStatusXIfcSupported OBJECT-TYPE
        SYNTAX INTEGER
        {
                yes(2),
                no(3)
        }
        ACCESS  read-only
        STATUS mandatory
        DESCRIPTION
        "Indication for IFC support."
        ::= { gnOduStatusXEntry 8}

gnOduStatusXRslDiversity OBJECT-TYPE
        SYNTAX INTEGER (-99..0)
        ACCESS  read-only
        STATUS mandatory
        DESCRIPTION
        "This is the receive level of the space diversity signal, displayed in DBM."
        ::= { gnOduStatusXEntry 9}

gnOduStatusXRslCombined OBJECT-TYPE
        SYNTAX INTEGER (-99..0)
        ACCESS  read-only
        STATUS mandatory
        DESCRIPTION
        "This is the receive level of the combined signal, displayed in DBM."
        ::= { gnOduStatusXEntry 10 }


gnOduStatusXRfuAddress OBJECT-TYPE
        SYNTAX INTEGER (0..31)
        ACCESS  read-only
        STATUS mandatory
        DESCRIPTION
        "The RFU Address."
        ::= { gnOduStatusXEntry 11 }

gnOduStatusXMinTransmitLevel OBJECT-TYPE
        SYNTAX INTEGER (-50..34)
        ACCESS  read-only
        STATUS mandatory
        DESCRIPTION
        "This is the minimum transmit level of the signal transmitted by the radios
         transmitter, displayed in DBM.. (for RFU unit only)"
        ::= { gnOduStatusXEntry 12 }

gnOduStatusXOduSWVer OBJECT-TYPE
        SYNTAX  DisplayString (SIZE(0..15))
        ACCESS  read-only
        STATUS mandatory
        DESCRIPTION
        "This is the ODU software version."
        ::= { gnOduStatusXEntry 13 }


gnOduStatusXOduSWPostVer OBJECT-TYPE
        SYNTAX  DisplayString (SIZE(0..15))
        ACCESS  read-only
        STATUS mandatory
        DESCRIPTION
        "This is the ODU post reset software version."
        ::= { gnOduStatusXEntry 14 }

gnOduStatusXRfuFwVer OBJECT-TYPE
        SYNTAX  DisplayString (SIZE(0..15))
        ACCESS  read-only
        STATUS mandatory
        DESCRIPTION
        "This is the RFU FW version."
        ::= { gnOduStatusXEntry 15 }

gnOduStatusXValidIntervals OBJECT-TYPE
        SYNTAX INTEGER (0..96)
        ACCESS  read-only
        STATUS mandatory
        DESCRIPTION
        "The number of previous valid intervals for which valid data has been stored
         for the specific ODU."
        ::= { gnOduStatusXEntry 16 }

-- This part of the MIB deals with the performance monitoring
-- of the ODU part of the system.
-- This part is built according the habits in the telcos/datacom community.
-- There are three tables:
-- gnOduMonCurrXTable that keeps the counters of the current 15 min interval.
-- gnOduMonIntervalXTable that keeps the counters of the past 96 intervals.
-- gnOduMonDayXTable that keeps the counters of the past 30 days.

gnOduMonitorX  OBJECT IDENTIFIER ::= { gnODU 6 }

gnOduMonCurrXTable OBJECT-TYPE
        SYNTAX  SEQUENCE OF GnOduMonCurrXEntry
        ACCESS  not-accessible
        STATUS mandatory
        DESCRIPTION
        "This table defines/keeps the counters of the current 15 min interval."
        ::= { gnOduMonitorX 1 }

gnOduMonCurrXEntry OBJECT-TYPE
        SYNTAX GnOduMonCurrXEntry
        ACCESS  not-accessible
        STATUS mandatory
        DESCRIPTION
        "This is an entry in the Current Interval Table. This table
        contains two rows, indexed by gnOduMonCurrXId= 3 for drawer1 ODU and
        gnOduMonCurrXId = 4 for drawer2 ODU."
        INDEX {  gnOduMonCurrXId }
        ::= { gnOduMonCurrXTable 1 }

GnOduMonCurrXEntry ::=
            SEQUENCE {
        gnOduMonCurrXId
                INTEGER,
        gnOduMonCurrXMinRL
          INTEGER,
           gnOduMonCurrXMaxRL
          INTEGER,
        gnOduMonCurrXTLThresh1Exceed
          Counter,
        gnOduMonCurrXRLThresh1Exceed
          Counter,
        gnOduMonCurrXRLThresh2Exceed
          Counter,
        gnOduMonCurrXDayMinRL
           INTEGER,
        gnOduMonCurrXDayMaxRL
           INTEGER,
        gnOduMonCurrXDayTLThresh1Exceed
          Counter,
        gnOduMonCurrXDayRLThresh1Exceed
          Counter,
        gnOduMonCurrXDayRLThresh2Exceed
          Counter,
        gnOduMonCurrXMinTL
          INTEGER,
           gnOduMonCurrXMaxTL
          INTEGER,
        gnOduMonCurrXDayMinTL
          INTEGER,
           gnOduMonCurrXDayMaxTL
          INTEGER,
           gnOduMonCurrXXpi
          INTEGER,
           gnOduMonCurrXMinXpi
          INTEGER,
           gnOduMonCurrXMaxXpi
          INTEGER,
        gnOduMonCurrXDayMinXpi
          INTEGER,
           gnOduMonCurrXDayMaxXpi
          INTEGER,
        gnOduMonCurrXXpiThreshExceed
          Counter,
        gnOduMonCurrXDayXpiThreshExceed
          Counter,
        gnOduMonCurrXMse
          INTEGER,
        gnOduMonCurrXLastDayIDF
          INTEGER
}

gnOduMonCurrXId OBJECT-TYPE
        SYNTAX  INTEGER
        {
                drawer1(3),
                drawer2(4)
        }
    ACCESS  read-only
           STATUS mandatory
    DESCRIPTION
    " "
    ::= { gnOduMonCurrXEntry 1 }

gnOduMonCurrXMinRL OBJECT-TYPE
        SYNTAX  INTEGER
        ACCESS  read-only
        STATUS mandatory
        DESCRIPTION
        "The minimum received signal level (RL) in the current 15 minute interval.
(in DBM) "
        ::= { gnOduMonCurrXEntry 2 }


gnOduMonCurrXMaxRL OBJECT-TYPE
        SYNTAX  INTEGER
        ACCESS  read-only
        STATUS mandatory
        DESCRIPTION
        "The maximum received signal level (RL) in the current 15 minute interval.
(in DBM). "
        ::= { gnOduMonCurrXEntry 3 }

gnOduMonCurrXTLThresh1Exceed OBJECT-TYPE
        SYNTAX  Counter
        ACCESS  read-only
        STATUS mandatory
        DESCRIPTION
        " The number of seconds TL exceeded the TL1
         threshold in the last 15 minutes."
        ::= { gnOduMonCurrXEntry 4 }


gnOduMonCurrXRLThresh1Exceed OBJECT-TYPE
        SYNTAX  Counter
        ACCESS  read-only
        STATUS mandatory
        DESCRIPTION
        " The number of seconds RL exceeded the RL1
         threshold in the last 15 minutes."
        ::= { gnOduMonCurrXEntry 5 }

gnOduMonCurrXRLThresh2Exceed OBJECT-TYPE
        SYNTAX  Counter
        ACCESS  read-only
        STATUS mandatory
        DESCRIPTION
        " The number of seconds RL exceeded the RL2
         threshold in the last 15 minutes."
        ::= { gnOduMonCurrXEntry 6 }


gnOduMonCurrXDayMinRL OBJECT-TYPE
        SYNTAX  INTEGER
        ACCESS  read-only
        STATUS mandatory
        DESCRIPTION
        " The minimum Receive Level (in DBM).
        in the last 24 hours."
        ::= { gnOduMonCurrXEntry 7}


gnOduMonCurrXDayMaxRL OBJECT-TYPE
        SYNTAX  INTEGER
        ACCESS  read-only
        STATUS mandatory
        DESCRIPTION
        " The maximum Receive Level (in DBM).
        in the last 24 hours."
        ::= { gnOduMonCurrXEntry 8}

gnOduMonCurrXDayTLThresh1Exceed OBJECT-TYPE
        SYNTAX  Counter
        ACCESS  read-only
        STATUS mandatory
        DESCRIPTION
        " The number of seconds TL exceeded the TL1 threshold
        in the last 24 hours."
        ::= { gnOduMonCurrXEntry 9}


gnOduMonCurrXDayRLThresh1Exceed OBJECT-TYPE
        SYNTAX  Counter
        ACCESS  read-only
        STATUS mandatory
        DESCRIPTION
        " The number of seconds RL exceeded the RL1 threshold
        in the last 24 hours."
        ::= { gnOduMonCurrXEntry 10 }

gnOduMonCurrXDayRLThresh2Exceed OBJECT-TYPE
        SYNTAX  Counter
        ACCESS  read-only
        STATUS mandatory
        DESCRIPTION
        " The number of seconds RL exceeded the RL2 threshold
        in the last 24 hours."
        ::= { gnOduMonCurrXEntry 11 }

gnOduMonCurrXMinTL OBJECT-TYPE
        SYNTAX  INTEGER
        ACCESS  read-only
        STATUS mandatory
        DESCRIPTION
        "The minimum transmitted signal level (TL) in the current 15 minute interval.
(in DBM) "
        ::= { gnOduMonCurrXEntry 12 }


gnOduMonCurrXMaxTL OBJECT-TYPE
        SYNTAX  INTEGER
        ACCESS  read-only
        STATUS mandatory
        DESCRIPTION
        "The maximum transmitted signal level (TL) in the current 15 minute interval.
(in DBM). "
        ::= { gnOduMonCurrXEntry 13 }

gnOduMonCurrXDayMinTL OBJECT-TYPE
        SYNTAX  INTEGER
        ACCESS  read-only
        STATUS mandatory
        DESCRIPTION
        " The minimum Transmitted Level (in DBM).
        in the last 24 hours."
        ::= { gnOduMonCurrXEntry 14}

gnOduMonCurrXDayMaxTL OBJECT-TYPE
        SYNTAX  INTEGER
        ACCESS  read-only
        STATUS mandatory
        DESCRIPTION
        " The maximum Transmitted Level (in DBM).
        in the last 24 hours."
        ::= { gnOduMonCurrXEntry 15}

gnOduMonCurrXXpi OBJECT-TYPE
        SYNTAX  INTEGER
        ACCESS  read-only
        STATUS mandatory
        DESCRIPTION
        "The Current XPI level (in [DBM/100]).
         For [DBM] level divide by 100."
        ::= { gnOduMonCurrXEntry 16}

gnOduMonCurrXMinXpi OBJECT-TYPE
        SYNTAX  INTEGER
        ACCESS  read-only
        STATUS mandatory
        DESCRIPTION
        " The minimum XPI Level (in [DBM/100]).
        in the last 15 minute (future develope).
        For [DBM] level divide by 100."
        ::= { gnOduMonCurrXEntry 17}

gnOduMonCurrXMaxXpi OBJECT-TYPE
        SYNTAX  INTEGER
        ACCESS  read-only
        STATUS mandatory
        DESCRIPTION
        " The maximum XPI Level (in [DBM/100]).
        in the last 15 minute (future develope).
        For [DBM] level divide by 100."
        ::= { gnOduMonCurrXEntry 18}

gnOduMonCurrXDayMinXpi OBJECT-TYPE
        SYNTAX  INTEGER
        ACCESS  read-only
        STATUS mandatory
        DESCRIPTION
        " The minimum XPI Level (in [DBM/100]).
        in the last 24 hours (future develope).
        For [DBM] level divide by 100."
        ::= { gnOduMonCurrXEntry 19}

gnOduMonCurrXDayMaxXpi OBJECT-TYPE
        SYNTAX  INTEGER
        ACCESS  read-only
        STATUS mandatory
        DESCRIPTION
        " The maximum XPI Level (in [DBM/100]).
        in the last 24 hours (future develope).
        For [DBM] level divide by 100."
        ::= { gnOduMonCurrXEntry 20}

gnOduMonCurrXXpiThreshExceed OBJECT-TYPE
        SYNTAX  Counter
        ACCESS  read-only
        STATUS mandatory
        DESCRIPTION
        " The number of seconds XPI beneath the XPI
         threshold in the last 15 minutes (future develope)."
        ::= { gnOduMonCurrXEntry 21 }

gnOduMonCurrXDayXpiThreshExceed OBJECT-TYPE
        SYNTAX  Counter
        ACCESS  read-only
        STATUS mandatory
        DESCRIPTION
        " The number of seconds XPI beneath the XPI threshold
        in the last 24 hours (future develope)."
        ::= { gnOduMonCurrXEntry 22}

gnOduMonCurrXMse OBJECT-TYPE
        SYNTAX  INTEGER
        ACCESS  read-only
        STATUS mandatory
        DESCRIPTION
        "The Current MSE level (in [DBM/100]).
        For [DBM] level divide by 100."
        ::= { gnOduMonCurrXEntry 23}

gnOduMonCurrXLastDayIDF OBJECT-TYPE
        SYNTAX  INTEGER {
                        off(2),
                        on(3)
        }
        ACCESS read-only
        STATUS mandatory
        DESCRIPTION
        "IDF = Invalid Data Flag."
        DEFVAL { off }
        ::= { gnOduMonCurrXEntry 24 }

gnOduMonIntervalXTable OBJECT-TYPE
        SYNTAX  SEQUENCE OF GnOduMonIntervalXEntry
        ACCESS  not-accessible
        STATUS mandatory
        DESCRIPTION
        "This table defines/keeps the counters of the 96 last intervals of 15 min."
        ::= { gnOduMonitorX 2 }

gnOduMonIntervalXEntry OBJECT-TYPE
        SYNTAX GnOduMonIntervalXEntry
        ACCESS  not-accessible
        STATUS mandatory
        DESCRIPTION
        "This is an entry in the Interval Table. This table
        is indexed by gnOduMonIntervalXId= 3 for drawer1 ODU and
        gnOduMonIntervalXId = 4 for drawer2 ODU and by interval idx"
        INDEX {  gnOduMonIntervalXId, gnOduMonIntervalXIdx }
        ::= { gnOduMonIntervalXTable 1 }

GnOduMonIntervalXEntry ::=
            SEQUENCE {
        gnOduMonIntervalXId
                INTEGER,
        gnOduMonIntervalXIdx
          INTEGER,
        gnOduMonIntervalXMinRL
          INTEGER,
           gnOduMonIntervalXMaxRL
          INTEGER,
        gnOduMonIntervalXTLThresh1Exceed
          Counter,
    gnOduMonIntervalXEvent
           OCTET STRING,
        gnOduMonIntervalXRLThresh1Exceed
          Counter,
        gnOduMonIntervalXRLThresh2Exceed
          Counter,
        gnOduMonIntervalXMinTL
          INTEGER,
           gnOduMonIntervalXMaxTL
          INTEGER,
        gnOduMonIntervalXMinXpi
          INTEGER,
        gnOduMonIntervalXMaxXpi
          INTEGER,
        gnOduMonIntervalXXpiThreshExceed
          Counter,
        gnOduMonIntervalXIDF
          INTEGER
}

gnOduMonIntervalXId OBJECT-TYPE
        SYNTAX  INTEGER
        {
                drawer1(3),
                drawer2(4)
        }
    ACCESS  read-only
           STATUS mandatory
    DESCRIPTION
    " "
    ::= { gnOduMonIntervalXEntry 1 }

gnOduMonIntervalXIdx OBJECT-TYPE
        SYNTAX  INTEGER (1..96)
        ACCESS  read-only
        STATUS mandatory
        DESCRIPTION
        " The interval number to which this row is related. "
        ::= { gnOduMonIntervalXEntry 2 }


gnOduMonIntervalXMinRL OBJECT-TYPE
        SYNTAX  INTEGER
        ACCESS  read-only
        STATUS mandatory
        DESCRIPTION
        " The minimum RL in a 15 minutes interval. (in DBM). "
        ::= { gnOduMonIntervalXEntry 3 }

gnOduMonIntervalXMaxRL OBJECT-TYPE
        SYNTAX  INTEGER
        ACCESS  read-only
        STATUS mandatory
        DESCRIPTION
        " The maximum RL in a 15 minutes interval. (in DBM). "
        ::= { gnOduMonIntervalXEntry 4 }

gnOduMonIntervalXTLThresh1Exceed OBJECT-TYPE
        SYNTAX  Counter
        ACCESS  read-only
        STATUS mandatory
        DESCRIPTION
        " The number of seconds TL exceeded the TL1
         threshold in a 15 minutes interval."
        ::= { gnOduMonIntervalXEntry 5 }


gnOduMonIntervalXEvent OBJECT-TYPE
        SYNTAX  OCTET STRING (SIZE(1))
        ACCESS  read-only
        STATUS mandatory
        DESCRIPTION
        " Events
         bit 1 = CommDisc.
         bit 2 = CommCon
     bit 3 = ATPC2Max.
         bit 4 = ATPC2Norm.
         Included for future development, not currently supported."
        ::= { gnOduMonIntervalXEntry 6 }

gnOduMonIntervalXRLThresh1Exceed OBJECT-TYPE
        SYNTAX  Counter
        ACCESS  read-only
        STATUS mandatory
        DESCRIPTION
        " The number of seconds RL exceeded the RL1
         threshold in a 15 minutes interval."
        ::= { gnOduMonIntervalXEntry 7 }

gnOduMonIntervalXRLThresh2Exceed OBJECT-TYPE
        SYNTAX  Counter
        ACCESS  read-only
        STATUS mandatory
        DESCRIPTION
        " The number of seconds RL exceeded the RL2
         threshold in a 15 minutes interval."
        ::= { gnOduMonIntervalXEntry 8 }

gnOduMonIntervalXMinTL OBJECT-TYPE
        SYNTAX  INTEGER
        ACCESS  read-only
        STATUS mandatory
        DESCRIPTION
        " The minimum TL in a 15 minutes interval. (in DBM). "
        ::= { gnOduMonIntervalXEntry 9 }

gnOduMonIntervalXMaxTL OBJECT-TYPE
        SYNTAX  INTEGER
        ACCESS  read-only
        STATUS mandatory
        DESCRIPTION
        " The maximum TL in a 15 minutes interval. (in DBM). "
        ::= { gnOduMonIntervalXEntry 10 }

gnOduMonIntervalXMinXpi OBJECT-TYPE
        SYNTAX  INTEGER
        ACCESS  read-only
        STATUS mandatory
        DESCRIPTION
        " The minimum XPI level (in [DBM/100]) in a 15 minutes intervalin (future develope).
        For [DBM] level divide by 100."
        ::= { gnOduMonIntervalXEntry 11 }

gnOduMonIntervalXMaxXpi OBJECT-TYPE
        SYNTAX  INTEGER
        ACCESS  read-only
        STATUS mandatory
        DESCRIPTION
        " The maximum XPI level (in [DBM/100]) in a 15 minutes interval (future develope).
        For [DBM] level divide by 100."
        ::= { gnOduMonIntervalXEntry 12 }

gnOduMonIntervalXXpiThreshExceed OBJECT-TYPE
        SYNTAX  Counter
        ACCESS  read-only
        STATUS mandatory
        DESCRIPTION
        " The number of seconds XPI exceeded the XPI
         threshold in a 15 minutes interval (future develope)."
        ::= { gnOduMonIntervalXEntry 13 }

gnOduMonIntervalXIDF OBJECT-TYPE
        SYNTAX  INTEGER {
                        off(2),
                        on(3)
        }
        ACCESS read-only
        STATUS mandatory
        DESCRIPTION
        "IDF = Invalid Data Flag."
        DEFVAL { off }
        ::= { gnOduMonIntervalXEntry 14 }


gnOduMonDayXTable OBJECT-TYPE
        SYNTAX  SEQUENCE OF GnOduMonDayXEntry
        ACCESS  not-accessible
        STATUS mandatory
        DESCRIPTION
        "This table defines/keeps the counters of 96 intervals of 15 min."
        ::= { gnOduMonitorX 3 }

gnOduMonDayXEntry OBJECT-TYPE
        SYNTAX GnOduMonDayXEntry
        ACCESS  not-accessible
        STATUS mandatory
        DESCRIPTION
        "This is an entry in the Days Table. This table
        is indexed by gnOduMonDayXId= 3 for drawer1 ODU and
        gnOduMonDayXId = 4 for drawer2 ODU and by day idx.
        gnOduMonDayIdx = 1 is one day from now,
        gnOduMonDayIdx = 2 is two days from now, and so on..."
        INDEX {  gnOduMonDayXId, gnOduMonDayXIdx }
        ::= { gnOduMonDayXTable 1 }

GnOduMonDayXEntry ::=
            SEQUENCE {
        gnOduMonDayXId
                INTEGER,
        gnOduMonDayXIdx
          INTEGER,
        gnOduMonDayXMinRL
           INTEGER,
        gnOduMonDayXMaxRL
           INTEGER,
        gnOduMonDayXTLThresh1Exceed
          Counter,
        gnOduMonDayXRLThresh1Exceed
          Counter,
        gnOduMonDayXRLThresh2Exceed
          Counter,
        gnOduMonDayXMinTL
           INTEGER,
        gnOduMonDayXMaxTL
           INTEGER,
        gnOduMonDayXMinXpi
           INTEGER,
        gnOduMonDayXMaxXpi
           INTEGER,
        gnOduMonDayXXpiThreshExceed
           Counter,
        gnOduMonDayXIDF
           INTEGER
}

gnOduMonDayXId OBJECT-TYPE
        SYNTAX  INTEGER
        {
                drawer1(3),
                drawer2(4)
        }
    ACCESS  read-only
           STATUS mandatory
    DESCRIPTION
    " "
    ::= { gnOduMonDayXEntry 1 }

gnOduMonDayXIdx OBJECT-TYPE
        SYNTAX  INTEGER (1..30)
        ACCESS  read-only
        STATUS mandatory
        DESCRIPTION
        " The interval number to which this row is related. "
        ::= { gnOduMonDayXEntry 2 }


gnOduMonDayXMinRL OBJECT-TYPE
        SYNTAX  INTEGER
        ACCESS  read-only
        STATUS mandatory
        DESCRIPTION
        " The minimum Receive Level (in DBM).
        in a 24 hour interval."
        ::= { gnOduMonDayXEntry 3}

gnOduMonDayXMaxRL OBJECT-TYPE
        SYNTAX  INTEGER
        ACCESS  read-only
        STATUS mandatory
        DESCRIPTION
        " The maximum Receive Level (in DBM).
        in a 24 hour interval."
        ::= { gnOduMonDayXEntry 4}

gnOduMonDayXTLThresh1Exceed OBJECT-TYPE
        SYNTAX  Counter
        ACCESS  read-only
        STATUS mandatory
        DESCRIPTION
        " The number of seconds TL exceeded the TL1 threshold
        in a 24 hour interval."
        ::= { gnOduMonDayXEntry 5}


gnOduMonDayXRLThresh1Exceed OBJECT-TYPE
        SYNTAX  Counter
        ACCESS  read-only
        STATUS mandatory
        DESCRIPTION
        " The number of seconds RL exceeded the RL1 threshold
        in a 24 hour interval."
        ::= { gnOduMonDayXEntry 6}


gnOduMonDayXRLThresh2Exceed OBJECT-TYPE
        SYNTAX  Counter
        ACCESS  read-only
        STATUS mandatory
        DESCRIPTION
        " The number of seconds RL exceeded the RL2 threshold
        in a 24 hour interval."
        ::= { gnOduMonDayXEntry 7}

gnOduMonDayXMinTL OBJECT-TYPE
        SYNTAX  INTEGER
        ACCESS  read-only
        STATUS mandatory
        DESCRIPTION
        " The minimum Transmit Level (in DBM).
        in a 24 hour interval."
        ::= { gnOduMonDayXEntry 8}

gnOduMonDayXMaxTL OBJECT-TYPE
        SYNTAX  INTEGER
        ACCESS  read-only
        STATUS mandatory
        DESCRIPTION
        " The maximum Transmit Level (in DBM).
        in a 24 hour interval."
        ::= { gnOduMonDayXEntry 9}

gnOduMonDayXMinXpi OBJECT-TYPE
        SYNTAX  INTEGER
        ACCESS  read-only
        STATUS mandatory
        DESCRIPTION
        " The minimum XPI Level (in [DBM/100]) in a 24 hour interval (future develope).
        For [DBM] level divide by 100."
        ::= { gnOduMonDayXEntry 10}

gnOduMonDayXMaxXpi OBJECT-TYPE
        SYNTAX  INTEGER
        ACCESS  read-only
        STATUS mandatory
        DESCRIPTION
        " The maximum XPI Level (in [DBM/100]) in a 24 hour interval (future develope).
        For [DBM] level divide by 100."
        ::= { gnOduMonDayXEntry 11}

gnOduMonDayXXpiThreshExceed OBJECT-TYPE
        SYNTAX  Counter
        ACCESS  read-only
        STATUS mandatory
        DESCRIPTION
        " The number of seconds XPI exceeded the XPI threshold
        in a 24 hour interval (future develope)."
        ::= { gnOduMonDayXEntry 12}

gnOduMonDayXIDF OBJECT-TYPE
        SYNTAX  INTEGER {
                        off(2),
                        on(3)
        }
        ACCESS read-only
        STATUS mandatory
        DESCRIPTION
        "IDF = Invalid Data Flag."
        DEFVAL { off }
        ::= { gnOduMonDayXEntry 13 }


gnOduMonCurrDiversityXTable OBJECT-TYPE
        SYNTAX  SEQUENCE OF GnOduMonCurrDiversityXEntry
        ACCESS  not-accessible
        STATUS mandatory
        DESCRIPTION
        "This table defines/keeps the counters of the current 15 min interval."
        ::= { gnOduMonitorX 4 }

gnOduMonCurrDiversityXEntry OBJECT-TYPE
        SYNTAX GnOduMonCurrDiversityXEntry
        ACCESS  not-accessible
        STATUS mandatory
        DESCRIPTION
        "This is an entry in the Current Interval Table. This table
        contains two rows, indexed by gnOduMonCurrCombinedXId= 3 for drawer1 ODU and
        gnOduMonCurrDiversityXId = 4 for drawer2 ODU."
        INDEX {  gnOduMonCurrDiversityXId }
        ::= { gnOduMonCurrDiversityXTable 1 }

GnOduMonCurrDiversityXEntry ::=
            SEQUENCE {
        gnOduMonCurrDiversityXId
                INTEGER,
        gnOduMonCurrDiversityXMinRL
          INTEGER,
           gnOduMonCurrDiversityXMaxRL
          INTEGER,
        gnOduMonCurrDiversityXRLThresh1Exceed
          Counter,
        gnOduMonCurrDiversityXRLThresh2Exceed
          Counter,
        gnOduMonCurrDiversityXDayMinRL
           INTEGER,
        gnOduMonCurrDiversityXDayMaxRL
           INTEGER,
        gnOduMonCurrDiversityXDayRLThresh1Exceed
           INTEGER,
        gnOduMonCurrDiversityXDayRLThresh2Exceed
           INTEGER
}

gnOduMonCurrDiversityXId OBJECT-TYPE
        SYNTAX  INTEGER
        {
                drawer1(3),
                drawer2(4)
        }
    ACCESS  read-only
           STATUS mandatory
    DESCRIPTION
    " "
    ::= { gnOduMonCurrDiversityXEntry 1 }

gnOduMonCurrDiversityXMinRL OBJECT-TYPE
        SYNTAX  INTEGER
        ACCESS  read-only
        STATUS mandatory
        DESCRIPTION
        "The minimum received signal level (RL) in the current 15 minute interval.
(in DBM) "
        ::= { gnOduMonCurrDiversityXEntry 2 }

gnOduMonCurrDiversityXMaxRL OBJECT-TYPE
        SYNTAX  INTEGER
        ACCESS  read-only
        STATUS mandatory
        DESCRIPTION
        "The maximum received signal level (RL) in the current 15 minute interval.
(in DBM). "
        ::= { gnOduMonCurrDiversityXEntry 3 }

gnOduMonCurrDiversityXRLThresh1Exceed OBJECT-TYPE
        SYNTAX  Counter
        ACCESS  read-only
        STATUS mandatory
        DESCRIPTION
        " The number of seconds RL exceeded the RL1
         threshold in the last 15 minutes."
        ::= { gnOduMonCurrDiversityXEntry 4 }

gnOduMonCurrDiversityXRLThresh2Exceed OBJECT-TYPE
        SYNTAX  Counter
        ACCESS  read-only
        STATUS mandatory
        DESCRIPTION
        " The number of seconds RL exceeded the RL2
         threshold in the last 15 minutes."
        ::= { gnOduMonCurrDiversityXEntry 5 }

gnOduMonCurrDiversityXDayMinRL OBJECT-TYPE
        SYNTAX  INTEGER
        ACCESS  read-only
        STATUS mandatory
        DESCRIPTION
        " The minimum Receive Level (in DBM).
        in the last 24 hours."
        ::= { gnOduMonCurrDiversityXEntry 6}

gnOduMonCurrDiversityXDayMaxRL OBJECT-TYPE
        SYNTAX  INTEGER
        ACCESS  read-only
        STATUS mandatory
        DESCRIPTION
        " The maximum Receive Level (in DBM).
        in the last 24 hours."
        ::= { gnOduMonCurrDiversityXEntry 7}

gnOduMonCurrDiversityXDayRLThresh1Exceed OBJECT-TYPE
        SYNTAX  INTEGER
        ACCESS  read-only
        STATUS mandatory
        DESCRIPTION
        "The number of seconds Diversity RL exceeded the RL1 threshold
        in the last 24 hours."
        ::= { gnOduMonCurrDiversityXEntry 8}

gnOduMonCurrDiversityXDayRLThresh2Exceed OBJECT-TYPE
        SYNTAX  INTEGER
        ACCESS  read-only
        STATUS mandatory
        DESCRIPTION
        "The number of seconds Diversity RL exceeded the RL2 threshold
        in the last 24 hours."
        ::= { gnOduMonCurrDiversityXEntry 9}

gnOduMonIntervalDiversityXTable OBJECT-TYPE
        SYNTAX  SEQUENCE OF GnOduMonIntervalDiversityXEntry
        ACCESS  not-accessible
        STATUS mandatory
        DESCRIPTION
        "This table defines/keeps the counters of the 96 last intervals of 15 min."
        ::= { gnOduMonitorX 5 }

gnOduMonIntervalDiversityXEntry OBJECT-TYPE
        SYNTAX GnOduMonIntervalDiversityXEntry
        ACCESS  not-accessible
        STATUS mandatory
        DESCRIPTION
        "This is an entry in the Interval Table. This table
        is indexed by gnOduMonIntervalDiversityXId= 3 for drawer1 ODU and
        gnOduMonIntervalDiversityXId = 4 for drawer2 ODU and by interval idx"
        INDEX {  gnOduMonIntervalDiversityXId, gnOduMonIntervalDiversityXIdx }
        ::= { gnOduMonIntervalDiversityXTable 1 }

GnOduMonIntervalDiversityXEntry ::=
            SEQUENCE {
        gnOduMonIntervalDiversityXId
                INTEGER,
        gnOduMonIntervalDiversityXIdx
          INTEGER,
        gnOduMonIntervalDiversityXMinRL
          INTEGER,
           gnOduMonIntervalDiversityXMaxRL
          INTEGER,
        gnOduMonIntervalDiversityXRLThresh1Exceed
          Counter,
        gnOduMonIntervalDiversityXRLThresh2Exceed
          Counter

}

gnOduMonIntervalDiversityXId OBJECT-TYPE
        SYNTAX  INTEGER
        {
                drawer1(3),
                drawer2(4)
        }
    ACCESS  read-only
           STATUS mandatory
    DESCRIPTION
    " "
    ::= { gnOduMonIntervalDiversityXEntry 1 }

gnOduMonIntervalDiversityXIdx OBJECT-TYPE
        SYNTAX  INTEGER (1..96)
        ACCESS  read-only
        STATUS mandatory
        DESCRIPTION
        " The interval number to which this row is related. "
        ::= { gnOduMonIntervalDiversityXEntry 2 }


gnOduMonIntervalDiversityXMinRL OBJECT-TYPE
        SYNTAX  INTEGER
        ACCESS  read-only
        STATUS mandatory
        DESCRIPTION
        " The minimum RL in a 15 minutes interval. (in DBM). "
        ::= { gnOduMonIntervalDiversityXEntry 3 }

gnOduMonIntervalDiversityXMaxRL OBJECT-TYPE
        SYNTAX  INTEGER
        ACCESS  read-only
        STATUS mandatory
        DESCRIPTION
        " The maximum RL in a 15 minutes interval. (in DBM). "
        ::= { gnOduMonIntervalDiversityXEntry 4 }

gnOduMonIntervalDiversityXRLThresh1Exceed OBJECT-TYPE
        SYNTAX  Counter
        ACCESS  read-only
        STATUS mandatory
        DESCRIPTION
        " The number of seconds RL exceeded the RL1
         threshold in a 15 minutes interval."
        ::= { gnOduMonIntervalDiversityXEntry 5 }

gnOduMonIntervalDiversityXRLThresh2Exceed OBJECT-TYPE
        SYNTAX  Counter
        ACCESS  read-only
        STATUS mandatory
        DESCRIPTION
        " The number of seconds RL exceeded the RL2
         threshold in a 15 minutes interval."
        ::= { gnOduMonIntervalDiversityXEntry 6 }


gnOduMonDayDiversityXTable OBJECT-TYPE
        SYNTAX  SEQUENCE OF GnOduMonDayDiversityXEntry
        ACCESS  not-accessible
        STATUS mandatory
        DESCRIPTION
        "This table defines/keeps the counters of 96 intervals of 15 min."
        ::= { gnOduMonitorX 6 }

gnOduMonDayDiversityXEntry OBJECT-TYPE
        SYNTAX GnOduMonDayDiversityXEntry
        ACCESS  not-accessible
        STATUS mandatory
        DESCRIPTION
        "This is an entry in the Days Table. This table
        is indexed by gnOduMonDayDiversityXId= 3 for drawer1 ODU and
        gnOduMonDayDiversityXId = 4 for drawer2 ODU and by day idx.
        gnOduMonDayDiversityXIdx = 1 is one day from now,
        gnOduMonDayDiversityXIdx = 2 is two days from now, and so on..."
        INDEX {  gnOduMonDayDiversityXId, gnOduMonDayDiversityXIdx }
        ::= { gnOduMonDayDiversityXTable 1 }

GnOduMonDayDiversityXEntry ::=
            SEQUENCE {
        gnOduMonDayDiversityXId
                INTEGER,
        gnOduMonDayDiversityXIdx
          INTEGER,
        gnOduMonDayDiversityXMinRL
           INTEGER,
        gnOduMonDayDiversityXMaxRL
           INTEGER,
        gnOduMonDayDiversityXRLThresh1Exceed
          Counter,
        gnOduMonDayDiversityXRLThresh2Exceed
          Counter

}

gnOduMonDayDiversityXId OBJECT-TYPE
        SYNTAX  INTEGER
        {
                drawer1(3),
                drawer2(4)
        }
    ACCESS  read-only
           STATUS mandatory
    DESCRIPTION
    " "
    ::= { gnOduMonDayDiversityXEntry 1 }

gnOduMonDayDiversityXIdx OBJECT-TYPE
        SYNTAX  INTEGER (1..30)
        ACCESS  read-only
        STATUS mandatory
        DESCRIPTION
        " The interval number to which this row is related. "
        ::= { gnOduMonDayDiversityXEntry 2 }

gnOduMonDayDiversityXMinRL OBJECT-TYPE
        SYNTAX  INTEGER
        ACCESS  read-only
        STATUS mandatory
        DESCRIPTION
        " The minimum Receive Level (in DBM).
        in a 24 hour interval."
        ::= { gnOduMonDayDiversityXEntry 3}

gnOduMonDayDiversityXMaxRL OBJECT-TYPE
        SYNTAX  INTEGER
        ACCESS  read-only
        STATUS mandatory
        DESCRIPTION
        " The maximum Receive Level (in DBM).
        in a 24 hour interval."
        ::= { gnOduMonDayDiversityXEntry 4}

gnOduMonDayDiversityXRLThresh1Exceed OBJECT-TYPE
        SYNTAX  Counter
        ACCESS  read-only
        STATUS mandatory
        DESCRIPTION
        " The number of seconds RL exceeded the RL1 threshold
        in a 24 hour interval."
        ::= { gnOduMonDayDiversityXEntry 5}

gnOduMonDayDiversityXRLThresh2Exceed OBJECT-TYPE
        SYNTAX  Counter
        ACCESS  read-only
        STATUS mandatory
        DESCRIPTION
        " The number of seconds RL exceeded the RL2 threshold
        in a 24 hour interval."
        ::= { gnOduMonDayDiversityXEntry 6}

gnOduMonCurrCombinedXTable OBJECT-TYPE
        SYNTAX  SEQUENCE OF GnOduMonCurrCombinedXEntry
        ACCESS  not-accessible
        STATUS mandatory
        DESCRIPTION
        "This table defines/keeps the counters of the current 15 min interval."
        ::= { gnOduMonitorX 7 }


gnOduMonCurrCombinedXEntry OBJECT-TYPE
        SYNTAX GnOduMonCurrCombinedXEntry
        ACCESS  not-accessible
        STATUS mandatory
        DESCRIPTION
        "This is an entry in the Current Interval Table. This table
        contains two rows, indexed by gnOduMonCurrCombinedXId= 3 for drawer1 ODU and
        gnOduMonCurrCombinedXId = 4 for drawer2 ODU."
        INDEX {  gnOduMonCurrCombinedXId }
        ::= { gnOduMonCurrCombinedXTable 1 }

GnOduMonCurrCombinedXEntry ::=
            SEQUENCE {
        gnOduMonCurrCombinedXId
                INTEGER,
        gnOduMonCurrCombinedXMinRL
          INTEGER,
           gnOduMonCurrCombinedXMaxRL
          INTEGER,
        gnOduMonCurrCombinedXRLThresh1Exceed
          Counter,
        gnOduMonCurrCombinedXRLThresh2Exceed
          Counter,
        gnOduMonCurrCombinedXDayMinRL
           INTEGER,
        gnOduMonCurrCombinedXDayMaxRL
           INTEGER,
        gnOduMonCurrCombinedXDayRLThresh1Exceed
           INTEGER,
        gnOduMonCurrCombinedXDayRLThresh2Exceed
           INTEGER

}

gnOduMonCurrCombinedXId OBJECT-TYPE
        SYNTAX  INTEGER
        {
                drawer1(3),
                drawer2(4)
        }
    ACCESS  read-only
           STATUS mandatory
    DESCRIPTION
    " "
    ::= { gnOduMonCurrCombinedXEntry 1 }

gnOduMonCurrCombinedXMinRL OBJECT-TYPE
        SYNTAX  INTEGER
        ACCESS  read-only
        STATUS mandatory
        DESCRIPTION
        "The minimum received signal level (RL) in the current 15 minute interval.
(in DBM) "
        ::= { gnOduMonCurrCombinedXEntry 2 }

gnOduMonCurrCombinedXMaxRL OBJECT-TYPE
        SYNTAX  INTEGER
        ACCESS  read-only
        STATUS mandatory
        DESCRIPTION
        "The maximum received signal level (RL) in the current 15 minute interval.
(in DBM). "
        ::= { gnOduMonCurrCombinedXEntry 3 }

gnOduMonCurrCombinedXRLThresh1Exceed OBJECT-TYPE
        SYNTAX  Counter
        ACCESS  read-only
        STATUS mandatory
        DESCRIPTION
        " The number of seconds RL exceeded the RL1
         threshold in the last 15 minutes."
        ::= { gnOduMonCurrCombinedXEntry 4 }

gnOduMonCurrCombinedXRLThresh2Exceed OBJECT-TYPE
        SYNTAX  Counter
        ACCESS  read-only
        STATUS mandatory
        DESCRIPTION
        " The number of seconds RL exceeded the RL2
         threshold in the last 15 minutes."
        ::= { gnOduMonCurrCombinedXEntry 5 }

gnOduMonCurrCombinedXDayMinRL OBJECT-TYPE
        SYNTAX  INTEGER
        ACCESS  read-only
        STATUS mandatory
        DESCRIPTION
        " The minimum Receive Level (in DBM).
        in the last 24 hours."
        ::= { gnOduMonCurrCombinedXEntry 6}

gnOduMonCurrCombinedXDayMaxRL OBJECT-TYPE
        SYNTAX  INTEGER
        ACCESS  read-only
        STATUS mandatory
        DESCRIPTION
        " The maximum Receive Level (in DBM).
        in the last 24 hours."
        ::= { gnOduMonCurrCombinedXEntry 7}

gnOduMonCurrCombinedXDayRLThresh1Exceed OBJECT-TYPE
        SYNTAX  INTEGER
        ACCESS  read-only
        STATUS mandatory
        DESCRIPTION
        "The number of seconds Combined RL exceeded the RL1 threshold
        in the last 24 hours."
        ::= { gnOduMonCurrCombinedXEntry 8}

gnOduMonCurrCombinedXDayRLThresh2Exceed OBJECT-TYPE
        SYNTAX  INTEGER
        ACCESS  read-only
        STATUS mandatory
        DESCRIPTION
        "The number of seconds Combined RL exceeded the RL2 threshold
        in the last 24 hours."
        ::= { gnOduMonCurrCombinedXEntry 9}

gnOduMonIntervalCombinedXTable OBJECT-TYPE
        SYNTAX  SEQUENCE OF GnOduMonIntervalCombinedXEntry
        ACCESS  not-accessible
        STATUS mandatory
        DESCRIPTION
        "This table defines/keeps the counters of the 96 last intervals of 15 min."
        ::= { gnOduMonitorX 8 }

gnOduMonIntervalCombinedXEntry OBJECT-TYPE
        SYNTAX GnOduMonIntervalCombinedXEntry
        ACCESS  not-accessible
        STATUS mandatory
        DESCRIPTION
        "This is an entry in the Interval Table. This table
        is indexed by gnOduMonIntervalCombinedXId= 3 for drawer1 ODU and
        gnOduMonIntervalCombinedXId = 4 for drawer2 ODU and by interval idx"
        INDEX {  gnOduMonIntervalCombinedXId, gnOduMonIntervalCombinedXIdx }
        ::= { gnOduMonIntervalCombinedXTable 1 }

GnOduMonIntervalCombinedXEntry ::=
            SEQUENCE {
        gnOduMonIntervalCombinedXId
                INTEGER,
        gnOduMonIntervalCombinedXIdx
          INTEGER,
        gnOduMonIntervalCombinedXMinRL
          INTEGER,
           gnOduMonIntervalCombinedXMaxRL
          INTEGER,
        gnOduMonIntervalCombinedXRLThresh1Exceed
          Counter,
        gnOduMonIntervalCombinedXRLThresh2Exceed
          Counter
}

gnOduMonIntervalCombinedXId OBJECT-TYPE
        SYNTAX  INTEGER
        {
                drawer1(3),
                drawer2(4)
        }
    ACCESS  read-only
           STATUS mandatory
    DESCRIPTION
    " "
    ::= { gnOduMonIntervalCombinedXEntry 1 }

gnOduMonIntervalCombinedXIdx OBJECT-TYPE
        SYNTAX  INTEGER (1..96)
        ACCESS  read-only
        STATUS mandatory
        DESCRIPTION
        " The interval number to which this row is related. "
        ::= { gnOduMonIntervalCombinedXEntry 2 }


gnOduMonIntervalCombinedXMinRL OBJECT-TYPE
        SYNTAX  INTEGER
        ACCESS  read-only
        STATUS mandatory
        DESCRIPTION
        " The minimum RL in a 15 minutes interval. (in DBM). "
        ::= { gnOduMonIntervalCombinedXEntry 3 }

gnOduMonIntervalCombinedXMaxRL OBJECT-TYPE
        SYNTAX  INTEGER
        ACCESS  read-only
        STATUS mandatory
        DESCRIPTION
        " The maximum RL in a 15 minutes interval. (in DBM). "
        ::= { gnOduMonIntervalCombinedXEntry 4 }

gnOduMonIntervalCombinedXRLThresh1Exceed OBJECT-TYPE
        SYNTAX  Counter
        ACCESS  read-only
        STATUS mandatory
        DESCRIPTION
        " The number of seconds RL exceeded the RL1
         threshold in a 15 minutes interval."
        ::= { gnOduMonIntervalCombinedXEntry 5 }

gnOduMonIntervalCombinedXRLThresh2Exceed OBJECT-TYPE
        SYNTAX  Counter
        ACCESS  read-only
        STATUS mandatory
        DESCRIPTION
        " The number of seconds RL exceeded the RL2
         threshold in a 15 minutes interval."
        ::= { gnOduMonIntervalCombinedXEntry 6 }


gnOduMonDayCombinedXTable OBJECT-TYPE
        SYNTAX  SEQUENCE OF GnOduMonDayCombinedXEntry
        ACCESS  not-accessible
        STATUS mandatory
        DESCRIPTION
        "This table defines/keeps the counters of 96 intervals of 15 min."
        ::= { gnOduMonitorX 9 }

gnOduMonDayCombinedXEntry OBJECT-TYPE
        SYNTAX GnOduMonDayCombinedXEntry
        ACCESS  not-accessible
        STATUS mandatory
        DESCRIPTION
        "This is an entry in the Days Table. This table
        is indexed by gnOduMonDayDiversityXId= 3 for drawer1 ODU and
        gnOduMonDayCombinedXId = 4 for drawer2 ODU and by day idx.
        gnOduMonDayCombinedXIdx = 1 is one day from now,
        gnOduMonDayCombinedXIdx = 2 is two days from now, and so on..."
        INDEX {  gnOduMonDayCombinedXId, gnOduMonDayCombinedXIdx }
        ::= { gnOduMonDayCombinedXTable 1 }

GnOduMonDayCombinedXEntry ::=
            SEQUENCE {
        gnOduMonDayCombinedXId
                INTEGER,
        gnOduMonDayCombinedXIdx
          INTEGER,
        gnOduMonDayCombinedXMinRL
           INTEGER,
        gnOduMonDayCombinedXMaxRL
           INTEGER,
        gnOduMonDayCombinedXRLThresh1Exceed
          Counter,
        gnOduMonDayCombinedXRLThresh2Exceed
          Counter
}

gnOduMonDayCombinedXId OBJECT-TYPE
        SYNTAX  INTEGER
        {
                drawer1(3),
                drawer2(4)
        }
    ACCESS  read-only
           STATUS mandatory
    DESCRIPTION
    "."
    ::= { gnOduMonDayCombinedXEntry 1 }

gnOduMonDayCombinedXIdx OBJECT-TYPE
        SYNTAX  INTEGER (1..30)
        ACCESS  read-only
        STATUS mandatory
        DESCRIPTION
        " The interval number to which this row is related. "
        ::= { gnOduMonDayCombinedXEntry 2 }

gnOduMonDayCombinedXMinRL OBJECT-TYPE
        SYNTAX  INTEGER
        ACCESS  read-only
        STATUS mandatory
        DESCRIPTION
        " The minimum Receive Level (in DBM).
        in a 24 hour interval."
        ::= { gnOduMonDayCombinedXEntry 3}

gnOduMonDayCombinedXMaxRL OBJECT-TYPE
        SYNTAX  INTEGER
        ACCESS  read-only
        STATUS mandatory
        DESCRIPTION
        " The maximum Receive Level (in DBM).
        in a 24 hour interval."
        ::= { gnOduMonDayCombinedXEntry 4}

gnOduMonDayCombinedXRLThresh1Exceed OBJECT-TYPE
        SYNTAX  Counter
        ACCESS  read-only
        STATUS mandatory
        DESCRIPTION
        " The number of seconds RL exceeded the RL1 threshold
        in a 24 hour interval."
        ::= { gnOduMonDayCombinedXEntry 5}

gnOduMonDayCombinedXRLThresh2Exceed OBJECT-TYPE
        SYNTAX  Counter
        ACCESS  read-only
        STATUS mandatory
        DESCRIPTION
        " The number of seconds RL exceeded the RL2 threshold
        in a 24 hour interval."
        ::= { gnOduMonDayCombinedXEntry 6}

----------------------------------------------------

gnIDU OBJECT IDENTIFIER ::=  { gnUnits 2 }

gnMdm OBJECT IDENTIFIER ::=  { gnIDU 1 }

gnMdmStatTable OBJECT-TYPE
        SYNTAX  SEQUENCE OF GnMdmStatEntry
        ACCESS  not-accessible
        STATUS mandatory
        DESCRIPTION
        "This table maintains the status of the Indoor part
                of the system."
        ::= { gnMdm 2 }

gnMdmStatEntry OBJECT-TYPE
        SYNTAX GnMdmStatEntry
        ACCESS  not-accessible
        STATUS mandatory
        DESCRIPTION
        "This is an entry in the IDU Modem Configuration Table. This table
        contains two rows, indexed by ifIndex= 1 for local modem and
        ifIndex = 101 for remote modem."
        INDEX {  ifIndex }
        ::= { gnMdmStatTable 1 }


GnMdmStatEntry ::=
            SEQUENCE {
        gnMdmModStatus
          INTEGER,
        gnMdmDemodStatus
          INTEGER,
        gnMdmDefectBlocks
          INTEGER,
        gnMdmBytesCorrected
          INTEGER,
    gnMdmClearBC
          INTEGER
}



gnMdmModStatus OBJECT-TYPE
        SYNTAX  INTEGER  {
                ok(2),
                modulatorFault(3)
                }
        ACCESS  read-only
        STATUS mandatory
        DESCRIPTION
        "This parameters indicates a modem fault. "
        ::= { gnMdmStatEntry 1 }

gnMdmDemodStatus OBJECT-TYPE
        SYNTAX  INTEGER
        ACCESS  read-only
        STATUS mandatory
        DESCRIPTION
        "This parameters indicates a demodem fault - For Ceragon internal use."
        ::= { gnMdmStatEntry 2 }

gnMdmDefectBlocks OBJECT-TYPE
        SYNTAX  INTEGER
        ACCESS  read-only
        STATUS mandatory
        DESCRIPTION
        "The number of defected blocks that could not be corrected by the
         FEC "
        ::= { gnMdmStatEntry 3 }

gnMdmBytesCorrected OBJECT-TYPE
        SYNTAX  INTEGER
        ACCESS  read-only
        STATUS mandatory
        DESCRIPTION
        " Number of bytes corrected by the FEC"
        ::= { gnMdmStatEntry 4 }


gnMdmClearBC OBJECT-TYPE
        SYNTAX  INTEGER {
                                noAction(2),
                     clear(3)
        }
        ACCESS  read-write
        STATUS mandatory
        DESCRIPTION
        " clears Defected Blocks, Defected Bytes and Blocks Corrected."
        ::= { gnMdmStatEntry 5 }



gnMdmStatXTable OBJECT-TYPE
        SYNTAX  SEQUENCE OF GnMdmStatXEntry
        ACCESS  not-accessible
        STATUS mandatory
        DESCRIPTION
        "This table maintains the status of the Indoor part
                of the system."
        ::= { gnMdm 3 }

gnMdmStatXEntry OBJECT-TYPE
        SYNTAX GnMdmStatXEntry
        ACCESS  not-accessible
        STATUS mandatory
        DESCRIPTION
        "This is an entry in the IDU Modem Configuration Table."
        INDEX {  gnMdmStatXId }
        ::= { gnMdmStatXTable 1 }


GnMdmStatXEntry ::=
            SEQUENCE {
        gnMdmStatXId
                INTEGER,
        gnMdmStatXStandardOrg
        INTEGER,
        gnMdmStatXRemoteConnection
                INTEGER,
        gnMdmStatXModemType
                INTEGER,
        gnMdmStatXModemWorkTime
                INTEGER,
        gnMdmStatXModemSerialNumber
                DisplayString,
        gnMdmStatXModemFWVer
          DisplayString,
        gnMdmStatXModemFWPostVer
          DisplayString,
        gnMdmStatXModemScriptVer
          DisplayString,
        gnMdmStatXModemScriptPostVer
          DisplayString,
        gnMdmStatXIfLoopbackTimeOut
                INTEGER,
        gnMdmStatXBoardType
                INTEGER,
        gnMdmStatXDefectedBlocks
                INTEGER
}

gnMdmStatXId OBJECT-TYPE
        SYNTAX  INTEGER
        {
                modem1(3),
                modem2(4)
        }
    ACCESS  read-only
           STATUS mandatory
    DESCRIPTION
    " "
    ::= { gnMdmStatXEntry 1 }

gnMdmStatXStandardOrg OBJECT-TYPE
        SYNTAX  INTEGER {
                etsi(2),
                fcc(3),
                japan(4),
                lmds(5),
                cmds(6),
                australia(7),
                other(8)
        }
        ACCESS  read-only
        STATUS mandatory
        DESCRIPTION
        "This parameter specifies which international standard is used."
        ::= { gnMdmStatXEntry 2 }

gnMdmStatXRemoteConnection OBJECT-TYPE
        SYNTAX  INTEGER {
                connected(2),
                disconnected(3)
        }
        ACCESS  read-only
        STATUS mandatory
        DESCRIPTION
        "Is the connection between the local manager and
         the remote manager."
        ::= { gnMdmStatXEntry 3 }

gnMdmStatXModemType OBJECT-TYPE
        SYNTAX  INTEGER (1..65535)
    ACCESS  read-only
    STATUS mandatory
        DESCRIPTION
        "This parameter specifies the modem qam."
    ::= { gnMdmStatXEntry 4 }

gnMdmStatXModemWorkTime OBJECT-TYPE
        SYNTAX  INTEGER
        ACCESS  read-only
        STATUS mandatory
                DESCRIPTION
                "The modem Work Time (hours)."
            DEFVAL        {0}
        ::= { gnMdmStatXEntry 5 }

gnMdmStatXModemSerialNumber OBJECT-TYPE
        SYNTAX  DisplayString(SIZE(0..20))
        ACCESS  read-only
        STATUS mandatory
        DESCRIPTION
        "This is the modem serial number - up to 20 characters "
        ::= { gnMdmStatXEntry 6 }

gnMdmStatXModemFWVer OBJECT-TYPE
        SYNTAX  DisplayString (SIZE(0..15))
        ACCESS  read-only
        STATUS mandatory
        DESCRIPTION
        "This is the Modem firmware version."
        ::= { gnMdmStatXEntry 7 }

gnMdmStatXModemFWPostVer OBJECT-TYPE
        SYNTAX  DisplayString (SIZE(0..15))
        ACCESS  read-only
        STATUS mandatory
        DESCRIPTION
        "This is the Modem post reset firmware version."
        ::= { gnMdmStatXEntry 8 }

gnMdmStatXModemScriptVer OBJECT-TYPE
        SYNTAX  DisplayString (SIZE(0..15))
        ACCESS  read-only
        STATUS mandatory
        DESCRIPTION
        "This is the Modem script version."
        ::= { gnMdmStatXEntry 9 }

gnMdmStatXModemScriptPostVer OBJECT-TYPE
        SYNTAX  DisplayString (SIZE(0..15))
        ACCESS  read-only
        STATUS mandatory
        DESCRIPTION
        "This is the Modem post reset script version."
        ::= { gnMdmStatXEntry 10 }

gnMdmStatXIfLoopbackTimeOut OBJECT-TYPE
        SYNTAX INTEGER (0..1440)
        ACCESS  read-only
        STATUS mandatory
        DESCRIPTION
        "This variable indicates the remaining time (in minutes)
        till the relevant loopback timer will be expired.
        when starting a loopback and the value of gnMdmStatXIfLoopbackTimeOut is x,
        the gnMdmStatXIfLoopbackTimeOut will be also x, after one minute it will be x-1, etc."
        ::= { gnMdmStatXEntry 11 }

        gnMdmStatXBoardType OBJECT-TYPE
        SYNTAX  INTEGER {
                        v1(2), -- phos
                        v2(3), -- summit
                        v3(4)  -- avalon
        }
        ACCESS  read-only
        STATUS mandatory
        DESCRIPTION
        "This parameter defines the type of the modem for NMS use."
        DEFVAL { v1 }
        ::= { gnMdmStatXEntry 12 }

gnMdmStatXDefectedBlocks OBJECT-TYPE
        SYNTAX  INTEGER
        ACCESS  read-only
        STATUS mandatory
        DESCRIPTION
        "The number of defected blocks. "
        ::= { gnMdmStatXEntry 13 }

gnMdmCfgTable OBJECT-TYPE
        SYNTAX  SEQUENCE OF GnMdmCfgEntry
        ACCESS  not-accessible
        STATUS mandatory
        DESCRIPTION
        ""
        ::= { gnMdm 4 }

gnMdmCfgEntry OBJECT-TYPE
        SYNTAX GnMdmCfgEntry
        ACCESS  not-accessible
        STATUS mandatory
        DESCRIPTION
        ""
        INDEX {  gnMdmCfgId }
        ::= { gnMdmCfgTable 1 }

GnMdmCfgEntry ::=
            SEQUENCE {
        gnMdmCfgId
                INTEGER,
        gnMdmCfgDiversityMode
                INTEGER
}

gnMdmCfgId OBJECT-TYPE
        SYNTAX  INTEGER
        {
                drawer1(3),
                drawer2(4)
        }
    ACCESS  read-only
           STATUS mandatory
    DESCRIPTION
    " "
    ::= { gnMdmCfgEntry 1 }

gnMdmCfgDiversityMode OBJECT-TYPE
        SYNTAX  INTEGER  {
                enable(2),
                disable(3)
                }
        ACCESS  read-write
        STATUS mandatory
        DESCRIPTION
        " "
        DEFVAL { disable }
        ::= { gnMdmCfgEntry 2 }

gnMdmCfgXTable OBJECT-TYPE
        SYNTAX  SEQUENCE OF GnMdmCfgXEntry
        ACCESS  not-accessible
        STATUS mandatory
        DESCRIPTION
        "This table defines the configuration of modem."
        ::= { gnMdm 5 }

gnMdmCfgXEntry OBJECT-TYPE
        SYNTAX GnMdmCfgXEntry
        ACCESS  not-accessible
        STATUS mandatory
        DESCRIPTION
        "This is an entry in the modem configuration table."
        INDEX {  gnMdmCfgXId }
        ::= { gnMdmCfgXTable 1 }

GnMdmCfgXEntry ::=
            SEQUENCE {
        gnMdmCfgXId
                INTEGER,
        gnMdmCfgXLatencyType
                INTEGER,
        gnMdmCfgXLinkId
                INTEGER,
        gnMdmCfgXRadioSide
                INTEGER,
        gnMdmCfgXMrmcConf
                INTEGER,
        gnMdmCfgXIfLoopback
                INTEGER,
        gnMdmCfgXHwReset
                INTEGER,
        gnMdmCfgXPrbsTest
                INTEGER,
        gnMdmCfgXClearCounters
                INTEGER
}

gnMdmCfgXId OBJECT-TYPE
        SYNTAX  INTEGER
        {
                modem1(3),
                modem2(4)
        }
    ACCESS  read-only
           STATUS mandatory
    DESCRIPTION
    "This value indicates which device is involved
        in the specific row."
    ::= { gnMdmCfgXEntry 1 }

gnMdmCfgXLatencyType OBJECT-TYPE
        SYNTAX  INTEGER  {
                low(2),
                high(3)
                }
        ACCESS  read-write
        STATUS mandatory
        DESCRIPTION
        " "
        DEFVAL { high }
        ::= { gnMdmCfgXEntry 2 }

gnMdmCfgXLinkId OBJECT-TYPE
        SYNTAX INTEGER (0..65535)
        ACCESS  read-write
        STATUS mandatory
                DESCRIPTION
                "0 for 'old' system that doesn't support the link ID.
                the user can enter values from 1 to 65535"
            DEFVAL        {0}
        ::= { gnMdmCfgXEntry 3 }

gnMdmCfgXRadioSide OBJECT-TYPE
        SYNTAX  INTEGER {
                                east(2),
                     west(3)
                }
        ACCESS  read-write
        STATUS mandatory
            DEFVAL        {east}
        ::= { gnMdmCfgXEntry 4 }

gnMdmCfgXMrmcConf        OBJECT-TYPE
        SYNTAX  INTEGER        {
                                mrmc1528                                    (1),
                            mrmc1550                             (2),
                                mrmc3156                (3),
                                mrmc3150                (4),
                                mrmc1228                    (5),
                                mrmc1540                                    (6),
                            mrmc4410                             (7),
                                mrmc4420                (8),
                                mrmc4440                (9),
                                mrmc1125                    (10),
                                mrmc2050                (11),
                                mrmc2030                (12),
                                mrmc1340                    (13)
                }
    ACCESS  read-write
    STATUS  mandatory
    DESCRIPTION
        "The Link data capacity"
         ::= { gnMdmCfgXEntry 5 }

gnMdmCfgXIfLoopback OBJECT-TYPE
        SYNTAX  INTEGER {
                none(2),
                active(3)
                }
        ACCESS  read-write
        STATUS mandatory
        DESCRIPTION
        " This parameter enable the user to activate a loopback."
        DEFVAL { none }
        ::= { gnMdmCfgXEntry  6 }

gnMdmCfgXHwReset OBJECT-TYPE
                SYNTAX  INTEGER
                {
                        noOperation(2),
                        hwReset(3)
                }
                ACCESS  read-write
                STATUS mandatory
                DESCRIPTION
                "hwReset - Hardware reset for modem board."
                DEFVAL { noOperation }
                ::= { gnMdmCfgXEntry 7 }

gnMdmCfgXPrbsTest OBJECT-TYPE
        SYNTAX  INTEGER {
                notActive(2),
                active(3)
                }
        ACCESS  read-write
        STATUS mandatory
        DESCRIPTION
        " This parameter enable the user to activate the PRBS test."
        DEFVAL { notActive }
        ::= { gnMdmCfgXEntry  8 }

gnMdmCfgXClearCounters OBJECT-TYPE
        SYNTAX  INTEGER {
                noAction(2),
				clearCounters(3)
        }
        ACCESS  read-write
        STATUS mandatory
        DESCRIPTION
        " This parameter enable the user to clear the PRBS counters."
        DEFVAL { noAction }
        ::= { gnMdmCfgXEntry  9 }

-- This group contains the parameters concerning the SPI
gnSpi  OBJECT IDENTIFIER ::=  { gnIDU 2 }

gnSpiCfgTable OBJECT-TYPE
        SYNTAX  SEQUENCE OF GnSpiCfgEntry
        ACCESS  not-accessible
        STATUS mandatory
        DESCRIPTION
        "This table defines the configuration of the SPI part
                of the system."
        ::= { gnSpi 1 }

gnSpiCfgEntry OBJECT-TYPE
        SYNTAX GnSpiCfgEntry
        ACCESS  not-accessible
        STATUS mandatory
        DESCRIPTION
        "This is an entry in the SPI Configuration Table. This table
        contains two  rows, indexed by ifIndex= 2 for local SPI and
        ifIndex = 102 for remote SPI."
        INDEX {  ifIndex }
        ::= { gnSpiCfgTable 1 }

GnSpiCfgEntry ::=
            SEQUENCE {
        gnSpiCfgConnector
         INTEGER
}

gnSpiCfgConnector OBJECT-TYPE
        SYNTAX  INTEGER {
                        nointerface(1),
                        fiber(2),
                        electrical(3),
                        utp(4),
                        stp(5)
        }
        ACCESS  read-only
        STATUS mandatory
        DESCRIPTION
        " The physical connector of the SPI - Used only in old regenerators "
        DEFVAL { fiber }
        ::= { gnSpiCfgEntry 1 }



-- This group contains the parameters concerning the MUX
gnMux OBJECT IDENTIFIER ::=  { gnIDU 3 }

-- This table is for parameters configuration of the regenerator

gnRstCfgTable OBJECT-TYPE
        SYNTAX  SEQUENCE OF GnRstCfgEntry
        ACCESS  not-accessible
        STATUS mandatory
        DESCRIPTION
        "This table defines the configuration of the regenerator part
                of the MUX."
        ::= { gnMux 1 }

gnRstCfgEntry OBJECT-TYPE
        SYNTAX GnRstCfgEntry
        ACCESS  not-accessible
        STATUS mandatory
        DESCRIPTION
        "This is an entry in the Regenerator part of the MUX Configuration Table.
        This table contains a row for every interface which type is SONET(39).
        for example  regenerator on local and remote sides will have four entries
1,2 for local
        IDU and 101 and 102 for remote IDU."
        INDEX {  ifIndex }
        ::= { gnRstCfgTable 1 }

GnRstCfgEntry ::=
            SEQUENCE {
        gnRstCfgTransmittedJ0
           DisplayString,
        gnRstCfgExpectedJ0
           DisplayString,
        gnRstCfgTransparencyJ0
            INTEGER,
        gnRstCfgRSTAISMode
             INTEGER,
        gnRstCfgRstEXCThresh
             INTEGER,
        gnRstCfgRstSDThresh
             INTEGER,
        gnRstCfgTransparencyE1
             INTEGER,
        gnRstCfgTransparencyF1
             INTEGER,
        gnRstCfgTransparencyUnscrambled
             INTEGER,
        gnRstCfgMngByteLocation
             INTEGER,
        gnRstCfgE1waysideChannel
             INTEGER,
        gnRstCfgTransparencyDCCR
             INTEGER,
        gnRstCfgTransparencyB1Chan
             INTEGER,
        gnRstCfgTestActivate
             OCTET STRING,
        gnRstCfgLoopbackOption
                INTEGER
        }



gnRstCfgTransmittedJ0 OBJECT-TYPE
        SYNTAX  DisplayString (SIZE(0..15))
        ACCESS  read-write
        STATUS mandatory
        DESCRIPTION
        "This is the J0 string that would be sent. This string must be 15
characters in length."
        DEFVAL {"  FIBEAIR1500  "}
        ::= { gnRstCfgEntry 1 }

gnRstCfgExpectedJ0 OBJECT-TYPE
        SYNTAX  DisplayString (SIZE(0..15))
        ACCESS  read-write
        STATUS mandatory
        DESCRIPTION
        "This is the J0 string that is expected to be received. This string must be
15 characters in length."
        DEFVAL {"  FIBEAIR1500  "}
        ::= { gnRstCfgEntry 2 }

gnRstCfgTransparencyJ0 OBJECT-TYPE
        SYNTAX  INTEGER {
                        active(2),
                        passthrough(3),
                        notActive(4)
        }
        ACCESS  read-write
        STATUS mandatory
        DESCRIPTION
        " Send the received J0 string transparently or send the Transmitted J0
             configured string."
        DEFVAL { passthrough }
        ::= { gnRstCfgEntry 3 }

gnRstCfgRSTAISMode OBJECT-TYPE
        SYNTAX  INTEGER {
                        sendAIS(2),
                        doNotSendAIS(3)
        }
        ACCESS  read-write
        STATUS mandatory
        DESCRIPTION
        " In the case of a J0 mismatch error, send or don't send AIS."
        DEFVAL { doNotSendAIS }
        ::= { gnRstCfgEntry 4 }

gnRstCfgRstEXCThresh OBJECT-TYPE
        SYNTAX  INTEGER {
                        tenExpMinus3(2),
                        tenExpMinus4(3),
                        tenExpMinus5(4)
        }
        ACCESS  read-write
        STATUS mandatory
        DESCRIPTION
        " If the bit error rate is higher than this threshold
         an EXC alarm would be generated.
        EXC is for excessive."
        DEFVAL { tenExpMinus3}
        ::= { gnRstCfgEntry 5 }

gnRstCfgRstSDThresh OBJECT-TYPE
        SYNTAX  INTEGER {
                        tenExpMinus6(3),
                        tenExpMinus7(4),
                        tenExpMinus8(5),
                        tenExpMinus9(6)
        }
        ACCESS  read-write
        STATUS mandatory
        DESCRIPTION
        " If the bit error rate is higher than this threshold
         a SD alarm would be generated.
        SD is for Signal Degrade."
        DEFVAL { tenExpMinus6}
        ::= { gnRstCfgEntry 6 }

gnRstCfgTransparencyE1 OBJECT-TYPE
        SYNTAX  INTEGER {
                        active(2),
                        passthrough(3),
                        disable(4)
        }
        ACCESS  read-write
        STATUS mandatory
        DESCRIPTION
        "Transmit the order wire data received or terminate the E1 data received."
        DEFVAL { active }
        ::= { gnRstCfgEntry 7 }

gnRstCfgTransparencyF1 OBJECT-TYPE
        SYNTAX  INTEGER {
                        active(2),
                        passthrough(3),
                        disable(4)
        }
        ACCESS  read-write
        STATUS mandatory
        DESCRIPTION
        "Transmit the F1/User channel data received or terminate the F1/User channel data received.
        set the TransparencyF1 to disable when the User channel used by In-Band management."
        DEFVAL { active }
        ::= { gnRstCfgEntry 8 }

gnRstCfgTransparencyUnscrambled OBJECT-TYPE
        SYNTAX  INTEGER {
                        active(2),
                        passthrough(3)
        }
        ACCESS  read-write
        STATUS mandatory
        DESCRIPTION
        "Transmit the unscrambled national bytes data received or terminate the
unscrambled national bytes data received."
        DEFVAL { passthrough }
        ::= { gnRstCfgEntry 9 }

gnRstCfgMngByteLocation OBJECT-TYPE
        SYNTAX  INTEGER {
                        mediaSpecificBytes(2),
                        spareA1A0Bytes(3),
                        e1Byets(4),
                        noMngBytes(5),
                        dccr(6),
                        dccm(7),
                        userChannel(8),
                        waysideChannel(9)
        }
        ACCESS  read-write
        STATUS mandatory
        DESCRIPTION
        "This parameter indicates which media specific bytes are in use and which
are transparent.
         not currently supported"
        DEFVAL { mediaSpecificBytes }
        ::= { gnRstCfgEntry 10 }

gnRstCfgE1waysideChannel OBJECT-TYPE
        SYNTAX  INTEGER {
                        enabled(2),
                        disabled(3)
--                        inband(4)
        }
        ACCESS  read-write
        STATUS mandatory
        DESCRIPTION
        "If this parameter is enabled, an E1 wayside channel will be sent
        through the network using the unused bytes in the SDH header."
        DEFVAL { enabled }
        ::= { gnRstCfgEntry 11 }

gnRstCfgTransparencyDCCR OBJECT-TYPE
        SYNTAX  INTEGER {
                        active(2),
                        passthrough(3)
        }
        ACCESS  read-write
        STATUS mandatory
        DESCRIPTION
        "Transmit on the DCCR channel or terminate the DCCR channel."
        DEFVAL { passthrough }
        ::= { gnRstCfgEntry 12 }

gnRstCfgTransparencyB1Chan OBJECT-TYPE
        SYNTAX  INTEGER {
                        active(2),
                        passthrough(3)
        }
        ACCESS  read-write
        STATUS mandatory
        DESCRIPTION
        "Correct B1 byte or send transmit it transparently ."
        DEFVAL { passthrough }
        ::= { gnRstCfgEntry 13 }

gnRstCfgTestActivate OBJECT-TYPE
        SYNTAX  OCTET STRING (SIZE(1))
        ACCESS  read-write
        STATUS mandatory
        DESCRIPTION
        "This field allows the NMS to activate the
        following tests:
        bit 1 = 1 Force AIS
        bit 2 = 1 Force RDI."
        ::= { gnRstCfgEntry 14 }

gnRstCfgLoopbackOption OBJECT-TYPE
        SYNTAX  INTEGER {
                noloopback(2),
                interfaceInterLoop(3),
                interfaceExterLoop(4)
                }
        ACCESS  read-write
        STATUS mandatory
        DESCRIPTION
        " This parameter enable the user to activate a loopback ."
        DEFVAL { noloopback }
        ::= { gnRstCfgEntry  15 }

gnRstStatTable OBJECT-TYPE
        SYNTAX  SEQUENCE OF GnRstStatEntry
        ACCESS  not-accessible
        STATUS mandatory
        DESCRIPTION
        "This table defines the status of the regenerator part
                of the MUX."
        ::= { gnMux 2 }

gnRstStatEntry OBJECT-TYPE
        SYNTAX GnRstStatEntry
        ACCESS  not-accessible
        STATUS mandatory
        DESCRIPTION
        "This is an entry in the Regenerator part of the MUX
         Status Table. This table contains a row for every interface which type is
SONET(39)."
        INDEX {  ifIndex }
        ::= { gnRstStatTable 1 }

GnRstStatEntry ::=
            SEQUENCE {
        gnRstStatReceivedJ0
             DisplayString,
        gnRstStatBERCur
             INTEGER,
        gnRstStatStatus
           OCTET STRING,
        gnRstStatClearLoopTimer
             INTEGER
}

gnRstStatReceivedJ0 OBJECT-TYPE
        SYNTAX  DisplayString (SIZE(0..15))
        ACCESS  read-only
        STATUS mandatory
        DESCRIPTION
        "This is the J0 string received."
        ::= { gnRstStatEntry 1 }

gnRstStatBERCur OBJECT-TYPE
        SYNTAX  INTEGER {
                        tenExpMinus3(2),
                        tenExpMinus4(3),
                        tenExpMinus5(4),
                        tenExpMinus6(5),
                        tenExpMinus7(6),
                        tenExpMinus8(7),
                        tenExpMinus9(8),
                        tenExpMinus10(9),
                        tenExpMinus11(10),
                        tenExpMinus12(11),
                        tenExpMinus13(12),
                        tenExpMinus14(13)
        }
        ACCESS  read-only
        STATUS mandatory
        DESCRIPTION
        " Current Bit Error Rate. "
        ::= { gnRstStatEntry 2 }

gnRstStatStatus OBJECT-TYPE
        SYNTAX OCTET STRING(SIZE(2))
        ACCESS  read-only
        STATUS mandatory
        DESCRIPTION
        " bit 2  = LOS
          bit 3  = LOF
          bit 7  = TIM
          bit 9  = SD
          bit 10 = EXC
          bit 11 = UNEXP"
        ::= { gnRstStatEntry 3 }

gnRstStatClearLoopTimer OBJECT-TYPE
        SYNTAX INTEGER (0..1440)
        ACCESS  read-only
        STATUS mandatory
        DESCRIPTION
        "This variable indicates the remaining time (in minutes)
        till the relevant loopback timer will be expired.
        when starting a loopback and the value of gnGenCfgClearLoopTimeout is x,
        the gnRstStatClearLoopTimer will be also x, after one minute it will be x-1, etc.
        gnRstStatClearLoopTimer.1 is for the radio aggregate loopbacks,
        gnRstStatClearLoopTimer.2 is for the line aggregate loopbacks"
        ::= { gnRstStatEntry 4 }

-- Statistics For Regenerator
gnRstMon OBJECT IDENTIFIER ::=  { gnMux 3 }

gnRstMonCurrTable OBJECT-TYPE
        SYNTAX  SEQUENCE OF GnRstMonCurrEntry
        ACCESS  not-accessible
        STATUS mandatory
        DESCRIPTION
        "This table maintains the counters of the regenerator part
                of the MUX."
        ::= { gnRstMon 1 }

gnRstMonCurrEntry OBJECT-TYPE
        SYNTAX GnRstMonCurrEntry
        ACCESS  not-accessible
        STATUS mandatory
        DESCRIPTION
        "This is an entry in the Regenerator part of the MUX
         Counters Table. This table contains a row for every interface which type
is SONET(39)."
        INDEX {  ifIndex }
        ::= { gnRstMonCurrTable 1 }

GnRstMonCurrEntry ::=
            SEQUENCE {
        --gnRstMonCurrES rfc1595
        --     Counter,
        --gnRstMonCurrSES
        --     Counter,
        gnRstMonCurrBBE
             Gauge,
        gnRstMonCurrUAS
             Gauge,
        --gnRstMonCurrOFS
        --     Counter,
        gnRstMonCurrLastDayES
             Gauge,
        gnRstMonCurrLastDaySES
             Gauge,
        gnRstMonCurrLastDayBBE
             Gauge,
        gnRstMonCurrLastDayUAS
             Gauge,
        gnRstMonCurrLastDayOFS
             Gauge,
        gnRstMonCurrLastDayIDF
                 INTEGER
}



gnRstMonCurrBBE OBJECT-TYPE
        SYNTAX  Gauge
        ACCESS  read-only
        STATUS mandatory
        DESCRIPTION
        " The current number of Background Block Errors
         starting from the present 15 minutes period."
        ::= { gnRstMonCurrEntry 1}

gnRstMonCurrUAS OBJECT-TYPE
        SYNTAX  Gauge
        ACCESS  read-only
        STATUS mandatory
        DESCRIPTION
        " The current number of Unavailable Seconds
         starting from the present 15 minutes period."
        ::= { gnRstMonCurrEntry 2}


gnRstMonCurrLastDayES OBJECT-TYPE
        SYNTAX  Gauge
        ACCESS  read-only
        STATUS mandatory
        DESCRIPTION
        " The current number of Errored Seconds
         starting from the present 24 hours period."
        ::= { gnRstMonCurrEntry 3 }

gnRstMonCurrLastDaySES OBJECT-TYPE
        SYNTAX  Gauge
        ACCESS  read-only
        STATUS mandatory
        DESCRIPTION
        " The current number of Severely Errored Seconds
         starting from the present 24 hours period."
        ::= { gnRstMonCurrEntry 4 }

gnRstMonCurrLastDayBBE OBJECT-TYPE
        SYNTAX  Gauge
        ACCESS  read-only
        STATUS mandatory
        DESCRIPTION
        " The current number of Background Block Errors
         starting from the present 24 hours period."
        ::= { gnRstMonCurrEntry 5 }

gnRstMonCurrLastDayUAS OBJECT-TYPE
        SYNTAX  Gauge
        ACCESS  read-only
        STATUS mandatory
        DESCRIPTION
        " The current number of Unavailable Seconds
         starting from the present 24 hours period."
        ::= { gnRstMonCurrEntry 6 }

gnRstMonCurrLastDayOFS OBJECT-TYPE
        SYNTAX  Gauge
        ACCESS  read-only
        STATUS mandatory
        DESCRIPTION
        " The current number of Out Of Frame Seconds
         starting from the present 24 hours period."
        ::= { gnRstMonCurrEntry 7}

gnRstMonCurrLastDayIDF OBJECT-TYPE
        SYNTAX  INTEGER {
                        off(2),
                        on(3)
        }
        ACCESS read-only
        STATUS mandatory
        DESCRIPTION
        "IDF = Invalid Data Flag."
        DEFVAL { off }
        ::= { gnRstMonCurrEntry 8 }


gnRstMonIntervalTable OBJECT-TYPE
        SYNTAX  SEQUENCE OF GnRstMonIntervalEntry
        ACCESS  not-accessible
        STATUS mandatory
        DESCRIPTION
        "This table maintains the counters of the regenerator part
                of the MUX per interval."
        ::= { gnRstMon 2 }

gnRstMonIntervalEntry OBJECT-TYPE
        SYNTAX GnRstMonIntervalEntry
        ACCESS  not-accessible
        STATUS mandatory
        DESCRIPTION
        "This is an entry in the Regenerator part of the MUX
         Counters Table. This table contains an interface index for every interface
         which type is SONET(39).
        This table is indexed by an interval index, between 1
        to 96 and representing each one 15 minutes.
               The oldest is 96."
        INDEX {  ifIndex, gnRstMonIntervalIdx}
        ::= { gnRstMonIntervalTable 1 }

GnRstMonIntervalEntry ::=
            SEQUENCE {
        gnRstMonIntervalIdx
              INTEGER,
        --gnRstMonIntervalES
        --     Counter,
        --gnRstMonIntervalSES
        --     Counter,
        gnRstMonIntervalBBE
             Gauge,
        gnRstMonIntervalUAS
        --     Counter,
        --gnRstMonIntervalOFS
             Gauge,
        gnRstMonIntervalIDF
                 INTEGER
--             ,
--        gnRstMonIntervalTimeStampMonth
--              INTEGER,
--        gnRstMonIntervalTimeStampDay
--              INTEGER,
--        gnRstMonIntervalTimeStampHour
--              INTEGER,
--        gnRstMonIntervalTimeStampMinute
--              INTEGER
}

gnRstMonIntervalIdx OBJECT-TYPE
        SYNTAX INTEGER (1..96)
        ACCESS read-only
        STATUS mandatory
        DESCRIPTION
        "This table is indexed per interval number. Each interval
        is of 15 minutes and the oldest is 96."
        ::= { gnRstMonIntervalEntry 1 }

gnRstMonIntervalBBE OBJECT-TYPE
        SYNTAX  Gauge
        ACCESS  read-only
        STATUS mandatory
        DESCRIPTION
        " The number of Background Block Errors
        per interval."
        ::= { gnRstMonIntervalEntry 2}

gnRstMonIntervalUAS OBJECT-TYPE
        SYNTAX  Gauge
        ACCESS  read-only
        STATUS mandatory
        DESCRIPTION
        " The number of Unavailable Seconds per interval."
        ::= { gnRstMonIntervalEntry 3}

gnRstMonIntervalIDF OBJECT-TYPE
        SYNTAX  INTEGER {
                        off(2),
                        on(3)
        }
        ACCESS read-only
        STATUS mandatory
        DESCRIPTION
        "IDF = Invalid Data Flag."
        DEFVAL { off }
        ::= { gnRstMonIntervalEntry 4 }


-- gnRstMonIntervalTimeStampMonth OBJECT-TYPE
--        SYNTAX INTEGER (1..12)
--        ACCESS read-only
--        STATUS mandatory
--        DESCRIPTION
--        "The Month of this interval time stamp.Not currently supported."
--        ::= { gnRstMonIntervalEntry 4 }

-- gnRstMonIntervalTimeStampDay OBJECT-TYPE
--                SYNTAX INTEGER (1..31)
--                ACCESS read-only
--                STATUS mandatory
--                DESCRIPTION
--                "The Day of this interval time stamp.Not currently supported."
--                ::= { gnRstMonIntervalEntry 5 }

-- gnRstMonIntervalTimeStampHour OBJECT-TYPE
--                SYNTAX INTEGER (0..23)
--                ACCESS read-only
--                STATUS mandatory
--                DESCRIPTION
--                "The Hour of this interval time stamp.Not currently supported."
--                ::= { gnRstMonIntervalEntry 6 }

-- gnRstMonIntervalTimeStampMinute OBJECT-TYPE
--                SYNTAX INTEGER (0..59)
--                ACCESS read-only
--                STATUS mandatory
--                DESCRIPTION
--                "The Minute of this interval time stamp.Not currently supported."
--                ::= { gnRstMonIntervalEntry 7 }


gnRstMonDayTable OBJECT-TYPE
        SYNTAX  SEQUENCE OF GnRstMonDayEntry
        ACCESS  not-accessible
        STATUS mandatory
        DESCRIPTION
        "This table maintains the counters of the regenerator part
                of the MUX per 24 hours interval."
        ::= { gnRstMon 3 }

gnRstMonDayEntry OBJECT-TYPE
        SYNTAX GnRstMonDayEntry
        ACCESS  not-accessible
        STATUS mandatory
        DESCRIPTION
        "This is an entry in the Regenerator part of the MUX
         Counters Table. This table contains an interface index for every interface
         which type is SONET(39).
        This table is indexed by an interval index, between 1
        to 30 and representing each one 24 hours.
               The oldest is 30."
        INDEX {  ifIndex, gnRstMonDayIdx}
        ::= { gnRstMonDayTable 1 }

GnRstMonDayEntry ::=
            SEQUENCE {
        gnRstMonDayIdx
              INTEGER,
        gnRstMonDayES
             Gauge,
        gnRstMonDaySES
             Gauge,
        gnRstMonDayBBE
             Gauge,
        gnRstMonDayUAS
             Gauge,
        gnRstMonDayOFS
             Gauge,
        gnRstMonDayIDF
                 INTEGER

--        ,
--         gnRstMonDayTimeStampMonth
--                      INTEGER,
--                gnRstMonDayTimeStampDay
--                      INTEGER,
--                gnRstMonDayTimeStampHour
--                      INTEGER,
--                gnRstMonDayTimeStampMinute
--                      INTEGER
}

gnRstMonDayIdx OBJECT-TYPE
        SYNTAX INTEGER (1..30)
        ACCESS read-only
        STATUS mandatory
        DESCRIPTION
        "This table is indexed per interval number. Each interval
        is of 24 hours and the oldest is 30."
        ::= { gnRstMonDayEntry 1 }

gnRstMonDayES OBJECT-TYPE
        SYNTAX  Gauge
        ACCESS  read-only
        STATUS mandatory
        DESCRIPTION
        " The number of Errored Seconds per interval of 24 hours."
        ::= { gnRstMonDayEntry 2}

gnRstMonDaySES OBJECT-TYPE
        SYNTAX  Gauge
        ACCESS  read-only
        STATUS mandatory
        DESCRIPTION
        " The number of Severely Errored Seconds
         per interval of 24 hours."
        ::= { gnRstMonDayEntry 3}

gnRstMonDayBBE OBJECT-TYPE
        SYNTAX  Gauge
        ACCESS  read-only
        STATUS mandatory
        DESCRIPTION
        " The number of Background Block Errors
         per interval of 24 hours."
        ::= { gnRstMonDayEntry 4 }

gnRstMonDayUAS OBJECT-TYPE
        SYNTAX  Gauge
        ACCESS  read-only
        STATUS mandatory
        DESCRIPTION
        " The number of Unavailable Seconds
         per interval of 24 hours."
        ::= { gnRstMonDayEntry 5 }

gnRstMonDayOFS OBJECT-TYPE
        SYNTAX  Gauge
        ACCESS  read-only
        STATUS mandatory
        DESCRIPTION
        " The number of Out Of Frame Seconds
         per interval of 24 hours."
        ::= { gnRstMonDayEntry 6}

gnRstMonDayIDF OBJECT-TYPE
        SYNTAX  INTEGER {
                        off(2),
                        on(3)
        }
        ACCESS read-only
        STATUS mandatory
        DESCRIPTION
        "IDF = Invalid Data Flag."
        DEFVAL { off }
        ::= { gnRstMonDayEntry 7 }


-- gnRstMonDayTimeStampMonth OBJECT-TYPE
--                SYNTAX INTEGER (1..12)
--                ACCESS read-only
--                STATUS mandatory
--                DESCRIPTION
--                "The Month of this interval time stamp.Not currently supported."
--                ::= { gnRstMonDayEntry 7 }

-- gnRstMonDayTimeStampDay OBJECT-TYPE
--                SYNTAX INTEGER (1..31)
--                ACCESS read-only
--                STATUS mandatory
--                DESCRIPTION
--                "The Day of this interval time stamp.Not currently supported."
--                ::= { gnRstMonDayEntry 8 }

-- gnRstMonDayTimeStampHour OBJECT-TYPE
--                SYNTAX INTEGER (0..23)
--                ACCESS read-only
--                STATUS mandatory
--                DESCRIPTION
--                "The Hour of this interval time stamp.Not currently supported."
--                ::= { gnRstMonDayEntry 9 }

-- gnRstMonDayTimeStampMinute OBJECT-TYPE
--                SYNTAX INTEGER (0..59)
--                ACCESS read-only
--                STATUS mandatory
--                DESCRIPTION
--                "The Minute of this interval time stamp.Not currently supported."
--                ::= { gnRstMonDayEntry 10 }



-- MST part of the MUX. All of the MST tables are included for future
-- development and are not currently implemented.
gnMstCfgTable OBJECT-TYPE
        SYNTAX  SEQUENCE OF GnMstCfgEntry
        ACCESS  not-accessible
        STATUS mandatory
        DESCRIPTION
        "This table maintains the counters of the MST part
                of the MUX."
        ::= { gnMux 4 }

gnMstCfgEntry OBJECT-TYPE
        SYNTAX GnMstCfgEntry
        ACCESS  not-accessible
        STATUS mandatory
        DESCRIPTION
        "This is an entry in the MST part of the MUX
         Configuration Table. This table contains a row for every interface
         which type is SONET(39)."
        INDEX {  ifIndex }
        ::= { gnMstCfgTable 1 }

GnMstCfgEntry ::=
            SEQUENCE {
        gnMstCfgEXCThresh
                INTEGER,
        gnMstCfgSDThresh
           INTEGER
}


gnMstCfgEXCThresh OBJECT-TYPE
        SYNTAX  INTEGER {
                        tenExpMinus3(2),
                        tenExpMinus4(3),
                        tenExpMinus5(4)
        }
        ACCESS  read-write
        STATUS mandatory
        DESCRIPTION
        " If the bit error rate is higher than this threshold
         an EXC alarm would be generated.
        EXC is for excessive."
        DEFVAL { tenExpMinus3}
        ::= { gnMstCfgEntry 1 }

gnMstCfgSDThresh OBJECT-TYPE
        SYNTAX  INTEGER {
                        tenExpMinus6(3),
                        tenExpMinus7(4),
                        tenExpMinus8(5),
                        tenExpMinus9(6)
        }
        ACCESS  read-write
        STATUS mandatory
        DESCRIPTION
        " If the bit error rate is higher than this threshold
         a SD alarm would be generated.
        SD is for Signal Degrade."
        DEFVAL { tenExpMinus6}
        ::= { gnMstCfgEntry 2 }


gnMstStatTable OBJECT-TYPE
        SYNTAX  SEQUENCE OF GnMstStatEntry
        ACCESS  not-accessible
        STATUS mandatory
        DESCRIPTION
        "This table defines the status of the MST part
                of the MUX."
        ::= { gnMux 5 }

gnMstStatEntry OBJECT-TYPE
        SYNTAX GnMstStatEntry
        ACCESS  not-accessible
        STATUS mandatory
        DESCRIPTION
        "This is an entry in the MST part of the MUX
         Status Table. This table contains a row for every interface which type is
SONET(39)."
        INDEX {  ifIndex }
        ::= { gnMstStatTable 1 }

GnMstStatEntry ::=
            SEQUENCE {
        gnMstStatReceivedS1
             INTEGER,
        gnMstStatStatus
             OCTET STRING,
        gnMstStatTransmitS1
                INTEGER,
        gnMstStatCurrentBer
                INTEGER,
        gnMstStatReceivedK1
             INTEGER,
        gnMstStatReceivedK2
             INTEGER,
        gnMstStatTransmitK1
                INTEGER,
        gnMstStatTransmitK2
                INTEGER
}

gnMstStatReceivedS1 OBJECT-TYPE
        SYNTAX  INTEGER (0..15)
        ACCESS  read-only
        STATUS mandatory
        DESCRIPTION
        " Received Synchronization status byte."
        ::= { gnMstStatEntry 1 }

gnMstStatStatus OBJECT-TYPE
        SYNTAX OCTET STRING(SIZE(4))
        ACCESS  read-only
        STATUS mandatory
        DESCRIPTION
        " Alarm status. Bit 1 is MSB, bit=1 when alarm active.
        bit 5  = RDI
        bit 6  = AIS
        bit 9  = SD
        bit 10 = EXC
        bit 16 = PAM (MSP)
        bit 17 = SCM (MSP)
        bit 18 = INV (MSP)
        "
        ::= { gnMstStatEntry 2 }

gnMstStatTransmitS1 OBJECT-TYPE
        SYNTAX  INTEGER (0..15)
        ACCESS  read-only
        STATUS mandatory
        DESCRIPTION
        " Transmitted Synchronization status byte."
        ::= { gnMstStatEntry 3 }

gnMstStatCurrentBer OBJECT-TYPE
        SYNTAX  INTEGER {
                        tenExpMinus3(2),
                        tenExpMinus4(3),
                        tenExpMinus5(4),
                        tenExpMinus6(5),
                        tenExpMinus7(6),
                        tenExpMinus8(7),
                        tenExpMinus9(8),
                        tenExpMinus10(9),
                        tenExpMinus11(10),
                        tenExpMinus12(11),
                        tenExpMinus13(12),
                        tenExpMinus14(13)
        }
        ACCESS  read-only
        STATUS mandatory
        DESCRIPTION
        " "
        ::= { gnMstStatEntry 4 }

gnMstStatReceivedK1 OBJECT-TYPE
        SYNTAX  INTEGER (0..255)
        ACCESS  read-only
        STATUS mandatory
        DESCRIPTION
        "Received K1 byte (Automatic Protection Switch message)."
        ::= { gnMstStatEntry 5 }

gnMstStatReceivedK2 OBJECT-TYPE
        SYNTAX  INTEGER (0..255)
        ACCESS  read-only
        STATUS mandatory
        DESCRIPTION
        "Received K2 byte (Automatic Protection Switch message)."
        ::= { gnMstStatEntry 6 }

gnMstStatTransmitK1 OBJECT-TYPE
        SYNTAX  INTEGER (0..255)
        ACCESS  read-only
        STATUS mandatory
        DESCRIPTION
        "Transmitted K1 byte (Automatic Protection Switch message)."
        ::= { gnMstStatEntry 7 }

gnMstStatTransmitK2 OBJECT-TYPE
        SYNTAX  INTEGER (0..255)
        ACCESS  read-only
        STATUS mandatory
        DESCRIPTION
        "Transmitted K2 byte (Automatic Protection Switch message)."
        ::= { gnMstStatEntry 8 }


-- Statistics For MST. All MST tables are included for future development
-- and are not currently implemented.
gnMstMon OBJECT IDENTIFIER ::=  { gnMux 6 }
gnMstMonCurrTable OBJECT-TYPE
        SYNTAX  SEQUENCE OF GnMstMonCurrEntry
        ACCESS  not-accessible
        STATUS mandatory
        DESCRIPTION
        "This table maintains the counters of the MST part
                of the MUX."
        ::= { gnMstMon 1 }

gnMstMonCurrEntry OBJECT-TYPE
        SYNTAX GnMstMonCurrEntry
        ACCESS  not-accessible
        STATUS mandatory
        DESCRIPTION
        "This is an entry in the MST part of the MUX
         Counters Table. This table contains a row for every interface which type
is SONET(39)."
        INDEX {  ifIndex }
        ::= { gnMstMonCurrTable 1 }

GnMstMonCurrEntry ::=
            SEQUENCE {
        --gnMstMonCurrES rfc1595
        --     Counter,
        --gnMstMonCurrSES
        --     Counter,
        gnMstMonCurrBBE
             Gauge,
        gnMstMonCurrUAS
             Gauge,
        gnMstMonCurrLastDayES
             Gauge,
        gnMstMonCurrLastDaySES
             Gauge,
        gnMstMonCurrLastDayBBE
             Gauge,
        gnMstMonCurrLastDayUAS
             Gauge
}



gnMstMonCurrBBE OBJECT-TYPE
        SYNTAX  Gauge
        ACCESS  read-only
        STATUS mandatory
        DESCRIPTION
        " The current number of Background Block Errors
         starting  from the present 15 minutes period."
        ::= { gnMstMonCurrEntry 1}

gnMstMonCurrUAS OBJECT-TYPE
        SYNTAX  Gauge
        ACCESS  read-only
        STATUS mandatory
        DESCRIPTION
        " The current number of Unavailable Seconds
         starting from the present 15 minutes period."
        ::= { gnMstMonCurrEntry 2}


gnMstMonCurrLastDayES OBJECT-TYPE
        SYNTAX  Gauge
        ACCESS  read-only
        STATUS mandatory
        DESCRIPTION
        " The current number of Errored Seconds
         starting from the present 24 hours period."
        ::= { gnMstMonCurrEntry 3 }

gnMstMonCurrLastDaySES OBJECT-TYPE
        SYNTAX  Gauge
        ACCESS  read-only
        STATUS mandatory
        DESCRIPTION
        " The current number of Severely Errored Seconds
         starting from the present 24 hours period."
        ::= { gnMstMonCurrEntry 4 }

gnMstMonCurrLastDayBBE OBJECT-TYPE
        SYNTAX  Gauge
        ACCESS  read-only
        STATUS mandatory
        DESCRIPTION
        " The current number of Background Block Errors
         starting from the present 24 hours period."
        ::= { gnMstMonCurrEntry 5 }

gnMstMonCurrLastDayUAS OBJECT-TYPE
        SYNTAX  Gauge
        ACCESS  read-only
        STATUS mandatory
        DESCRIPTION
        " The current number of Unavailable Seconds
         starting from the present 24 hours period."
        ::= { gnMstMonCurrEntry 6 }


gnMstMonIntervalTable OBJECT-TYPE
        SYNTAX  SEQUENCE OF GnMstMonIntervalEntry
        ACCESS  not-accessible
        STATUS mandatory
        DESCRIPTION
        "This table maintains the counters of the MST part
                of the MUX per interval."
        ::= { gnMstMon 2 }

gnMstMonIntervalEntry OBJECT-TYPE
        SYNTAX GnMstMonIntervalEntry
        ACCESS  not-accessible
        STATUS mandatory
        DESCRIPTION
        "This is an entry in the MST part of the MUX
         Counters Table. This table contains an interface index for every interface
         which type is SONET(39).
        This table is indexed by an interval index, between 1
        to 96 and representing each one 15 minutes.
               The oldest is 96."
        INDEX {  ifIndex, gnMstMonIntervalIdx}
        ::= { gnMstMonIntervalTable 1 }

GnMstMonIntervalEntry ::=
            SEQUENCE {
        gnMstMonIntervalIdx
              INTEGER,
        --gnMstMonIntervalES
        --     Counter,
        --gnMstMonIntervalSES
        --     Counter,
        gnMstMonIntervalBBE
             Gauge,
        gnMstMonIntervalUAS
             Gauge
}

gnMstMonIntervalIdx OBJECT-TYPE
        SYNTAX INTEGER (1..96)
        ACCESS read-only
        STATUS mandatory
        DESCRIPTION
        "This table is indexed per interval number. Each interval
        is of 15 minutes and the oldest is 96."
        ::= { gnMstMonIntervalEntry 1 }

gnMstMonIntervalBBE OBJECT-TYPE
        SYNTAX  Gauge
        ACCESS  read-only
        STATUS mandatory
        DESCRIPTION
        " The number of Background Block Errors
        per interval."
        ::= { gnMstMonIntervalEntry 2}

gnMstMonIntervalUAS OBJECT-TYPE
        SYNTAX  Gauge
        ACCESS  read-only
        STATUS mandatory
        DESCRIPTION
        " The  number of Unavailable Seconds per interval."
        ::= { gnMstMonIntervalEntry 3}


gnMstMonDayTable OBJECT-TYPE
        SYNTAX  SEQUENCE OF GnMstMonDayEntry
        ACCESS  not-accessible
        STATUS mandatory
        DESCRIPTION
        "This table maintains the counters of the MST part
                of the MUX per 24 hours interval."
        ::= { gnMstMon 3 }

gnMstMonDayEntry OBJECT-TYPE
        SYNTAX GnMstMonDayEntry
        ACCESS  not-accessible
        STATUS mandatory
        DESCRIPTION
        "This is an entry in the MST part of the MUX
         Counters Table. This table contains an interface index for every interface
         which type is SONET(39).
        This table is indexed by an interval index, between 1
        to 30 and representing each one 24 hours.
               The oldest is 30."
        INDEX {  ifIndex, gnMstMonDayIdx}
        ::= { gnMstMonDayTable 1 }

GnMstMonDayEntry ::=
            SEQUENCE {
        gnMstMonDayIdx
              INTEGER,
        gnMstMonDayES
             Gauge,
        gnMstMonDaySES
             Gauge,
        gnMstMonDayBBE
             Gauge,
        gnMstMonDayUAS
             Gauge
}

gnMstMonDayIdx OBJECT-TYPE
        SYNTAX INTEGER (1..30)
        ACCESS read-only
        STATUS mandatory
        DESCRIPTION
        "This table is indexed per interval number. Each interval
        is of 24 hours and the oldest is 30."
        ::= { gnMstMonDayEntry 1 }

gnMstMonDayES OBJECT-TYPE
        SYNTAX  Gauge
        ACCESS  read-only
        STATUS mandatory
        DESCRIPTION
        " The number of Errored Seconds per interval of 24 hours."
        ::= { gnMstMonDayEntry 2}

gnMstMonDaySES OBJECT-TYPE
        SYNTAX  Gauge
        ACCESS  read-only
        STATUS mandatory
        DESCRIPTION
        " The number of Severely Errored Seconds
         per interval of 24 hours."
        ::= { gnMstMonDayEntry 3}

gnMstMonDayBBE OBJECT-TYPE
        SYNTAX  Gauge
        ACCESS  read-only
        STATUS mandatory
        DESCRIPTION
        " The number of Background Block Errors
         per interval of 24 hours."
        ::= { gnMstMonDayEntry 4 }

gnMstMonDayUAS OBJECT-TYPE
        SYNTAX  Gauge
        ACCESS  read-only
        STATUS mandatory
        DESCRIPTION
        " The number of Unavailable Seconds
         per interval of 24 hours."
        ::= { gnMstMonDayEntry 5 }


gnMstFarEndMonCurrTable OBJECT-TYPE
        SYNTAX  SEQUENCE OF GnMstFarEndMonCurrEntry
        ACCESS  not-accessible
        STATUS mandatory
        DESCRIPTION
        "This table maintains the counters of the far end MST part of the MUX.
        This Table is not supported."
        ::= { gnMstMon 4 }

gnMstFarEndMonCurrEntry OBJECT-TYPE
        SYNTAX GnMstFarEndMonCurrEntry
        ACCESS  not-accessible
        STATUS mandatory
        DESCRIPTION
        "This is an entry in the far end MST part of the MUX
         Counters Table. This table contains an interface index for every interface
         which type is SONET(39)."
        INDEX {  ifIndex }
        ::= { gnMstFarEndMonCurrTable 1 }

GnMstFarEndMonCurrEntry ::=
            SEQUENCE {
        --gnMstFarEndMonCurrES rfc1595
        --     Counter,
        --gnMstFarEndMonCurrSES
        --     Counter,
        gnMstFarEndMonCurrBBE
             Gauge,
        gnMstFarEndMonCurrUAS
             Gauge,
        gnMstFarEndMonCurrLastDayES
             Gauge,
        gnMstFarEndMonCurrLastDaySES
             Gauge,
        gnMstFarEndMonCurrLastDayBBE
             Gauge,
        gnMstFarEndMonCurrLastDayUAS
             Gauge
}



gnMstFarEndMonCurrBBE OBJECT-TYPE
        SYNTAX  Gauge
        ACCESS  read-only
        STATUS mandatory
        DESCRIPTION
        " The current number of Background Block Errors
         starting from the present 15 minutes period."
        ::= { gnMstFarEndMonCurrEntry 1}

gnMstFarEndMonCurrUAS OBJECT-TYPE
        SYNTAX  Gauge
        ACCESS  read-only
        STATUS mandatory
        DESCRIPTION
        " The current number of Unavailable Seconds
         starting from the present 15 minutes period."
        ::= { gnMstFarEndMonCurrEntry 2}


gnMstFarEndMonCurrLastDayES OBJECT-TYPE
        SYNTAX  Gauge
        ACCESS  read-only
        STATUS mandatory
        DESCRIPTION
        " The current number of Errored Seconds
         starting from the present 24 hours period."
        ::= { gnMstFarEndMonCurrEntry 3 }

gnMstFarEndMonCurrLastDaySES OBJECT-TYPE
        SYNTAX  Gauge
        ACCESS  read-only
        STATUS mandatory
        DESCRIPTION
        " The current number of Severely Errored Seconds
         starting from the present 24 hours period."
        ::= { gnMstFarEndMonCurrEntry 4 }

gnMstFarEndMonCurrLastDayBBE OBJECT-TYPE
        SYNTAX  Gauge
        ACCESS  read-only
        STATUS mandatory
        DESCRIPTION
        " The current number of Background Block Errors
         starting from the present 24 hours period."
        ::= { gnMstFarEndMonCurrEntry 5 }

gnMstFarEndMonCurrLastDayUAS OBJECT-TYPE
        SYNTAX  Gauge
        ACCESS  read-only
        STATUS mandatory
        DESCRIPTION
        " The current number of Unavailable Seconds
         starting from the present 24 hours period."
        ::= { gnMstFarEndMonCurrEntry 6 }


gnMstFarEndMonIntervalTable OBJECT-TYPE
        SYNTAX  SEQUENCE OF GnMstFarEndMonIntervalEntry
        ACCESS  not-accessible
        STATUS mandatory
        DESCRIPTION
        "This table maintains the counters of the far end MST part
         of the MUX per interval.
         This Table is not supported."
        ::= { gnMstMon 5 }

gnMstFarEndMonIntervalEntry OBJECT-TYPE
        SYNTAX GnMstFarEndMonIntervalEntry
        ACCESS  not-accessible
        STATUS mandatory
        DESCRIPTION
        "This is an entry in the far end MST part of the MUX
         Counters Table. This table contains an interface index for every interface
         which type is SONET(39)
        This table is indexed by an interval index, between 1
        to 96 and representing each one 15 minutes.
               The oldest is 96."
        INDEX {  ifIndex, gnMstFarEndMonIntervalIdx}
        ::= { gnMstFarEndMonIntervalTable 1 }

GnMstFarEndMonIntervalEntry ::=
            SEQUENCE {
        gnMstFarEndMonIntervalIdx
              INTEGER,
        --gnMstFarEndMonIntervalES
        --     Counter,
        --gnMstFarEndMonIntervalSES
        --     Counter,
        gnMstFarEndMonIntervalBBE
             Gauge,
        gnMstFarEndMonIntervalUAS
             Gauge
}

gnMstFarEndMonIntervalIdx OBJECT-TYPE
        SYNTAX INTEGER (1..96)
        ACCESS read-only
        STATUS mandatory
        DESCRIPTION
        "This table is indexed per interval number. Each interval
        is of 15 minutes and the oldest is 96."
        ::= { gnMstFarEndMonIntervalEntry 1 }

gnMstFarEndMonIntervalBBE OBJECT-TYPE
        SYNTAX  Gauge
        ACCESS  read-only
        STATUS mandatory
        DESCRIPTION
        " The number of Background Block Errors
        per interval."
        ::= { gnMstFarEndMonIntervalEntry 2}

gnMstFarEndMonIntervalUAS OBJECT-TYPE
        SYNTAX  Gauge
        ACCESS  read-only
        STATUS mandatory
        DESCRIPTION
        " The  number of Unavailable Seconds per interval."
        ::= { gnMstFarEndMonIntervalEntry 3}


gnMstFarEndMonDayTable OBJECT-TYPE
        SYNTAX  SEQUENCE OF GnMstFarEndMonDayEntry
        ACCESS  not-accessible
        STATUS mandatory
        DESCRIPTION
        "This table maintains the counters of the far end MST part
     of the MUX per 24 hours interval.
     This Table is not supported."
        ::= { gnMstMon 6 }

gnMstFarEndMonDayEntry OBJECT-TYPE
        SYNTAX GnMstFarEndMonDayEntry
        ACCESS  not-accessible
        STATUS mandatory
        DESCRIPTION
        "This is an entry in the far end MST part of the MUX
         Counters Table. This table contains an interface index for every interface
         which type is SONET(39).
        This table is indexed by an interval index, between 1
        to 30 and representing each one 24 hours.
               The oldest is 30."
        INDEX {  ifIndex, gnMstFarEndMonDayIdx}
        ::= { gnMstFarEndMonDayTable 1 }

GnMstFarEndMonDayEntry ::=
            SEQUENCE {
        gnMstFarEndMonDayIdx
              INTEGER,
        gnMstFarEndMonDayES
             Gauge,
        gnMstFarEndMonDaySES
             Gauge,
        gnMstFarEndMonDayBBE
             Gauge,
        gnMstFarEndMonDayUAS
             Gauge
}

gnMstFarEndMonDayIdx OBJECT-TYPE
        SYNTAX INTEGER (1..30)
        ACCESS read-only
        STATUS mandatory
        DESCRIPTION
        "This table is indexed per interval number. Each interval
        is of 24 hours and the oldest is 30."
        ::= { gnMstFarEndMonDayEntry 1 }

gnMstFarEndMonDayES OBJECT-TYPE
        SYNTAX  Gauge
        ACCESS  read-only
        STATUS mandatory
        DESCRIPTION
        " The number of Errored Seconds per interval of 24 hours."
        ::= { gnMstFarEndMonDayEntry 2}

gnMstFarEndMonDaySES OBJECT-TYPE
        SYNTAX  Gauge
        ACCESS  read-only
        STATUS mandatory
        DESCRIPTION
        " The number of Severely Errored Seconds
         per interval of 24 hours."
        ::= { gnMstFarEndMonDayEntry 3}

gnMstFarEndMonDayBBE OBJECT-TYPE
        SYNTAX  Gauge
        ACCESS  read-only
        STATUS mandatory
        DESCRIPTION
        " The number of Background Block Errors
         per interval of 24 hours."
        ::= { gnMstFarEndMonDayEntry 4 }

gnMstFarEndMonDayUAS OBJECT-TYPE
        SYNTAX  Gauge
        ACCESS  read-only
        STATUS mandatory
        DESCRIPTION
        " The number of Unavailable Seconds
         per interval of 24 hours."
        ::= { gnMstFarEndMonDayEntry 5 }

-- HPT part of the MUX. All HPT tables are included for future development
-- and are not currently implemented.
gnHptCfgTable OBJECT-TYPE
        SYNTAX  SEQUENCE OF GnHptCfgEntry
        ACCESS  not-accessible
        STATUS mandatory
        DESCRIPTION
        "This table maintains the counters of the HPT part
                of the MUX."
        ::= { gnMux 7 }

gnHptCfgEntry OBJECT-TYPE
        SYNTAX GnHptCfgEntry
        ACCESS  not-accessible
        STATUS mandatory
        DESCRIPTION
        "This is an entry in the HPT part of the MUX
         Configuration Table. This table contains an interface index for every
interface
         which type is PATH(50, according to RFC1573)."
        INDEX {  ifIndex }
        ::= { gnHptCfgTable 1 }

GnHptCfgEntry ::=
            SEQUENCE {
        gnHptCfgTransmittedJ1
            DisplayString,
        gnHptCfgExpectedJ1
             DisplayString,
        gnHptCfgMismatchJ1
             INTEGER,
        gnHptCfgTransparencyJ1
                INTEGER,
        gnHptCfgEXCThresh
                INTEGER,
        gnHptCfgSDThresh
                INTEGER,
        gnHptCfgTug3Structure1
             OCTET STRING,
        gnHptCfgTug3Structure2
             OCTET STRING,
        gnHptCfgTug3Structure3
             OCTET STRING,
        gnHptCfgSignalLabelMismatch
                INTEGER,
        gnHptCfgTrailPT1
             OCTET STRING,
        gnHptCfgTrailPT2
             OCTET STRING,
        gnHptCfgTrailPT3
             OCTET STRING
}


gnHptCfgTransmittedJ1 OBJECT-TYPE
        SYNTAX  DisplayString (SIZE(0..15))
        ACCESS  read-write
        STATUS mandatory
        DESCRIPTION
        " This is the J1 string that would be sent."
        DEFVAL { "  ACCESS MUX   " }
        ::= { gnHptCfgEntry 1 }

gnHptCfgExpectedJ1 OBJECT-TYPE
        SYNTAX  DisplayString (SIZE(0..15))
        ACCESS  read-write
        STATUS mandatory
        DESCRIPTION
          " This is the J1 string that is expected to be received."
        DEFVAL { "  ACCESS MUX   " }
        ::= { gnHptCfgEntry 2 }

gnHptCfgMismatchJ1 OBJECT-TYPE
        SYNTAX INTEGER{
                sendAlarm(2),
                sendAIS(3)
        }
        ACCESS  read-write
        STATUS mandatory
        DESCRIPTION
          " In case of a J1 mismatch error, send or don't send AIS."
        DEFVAL { sendAlarm }
        ::= { gnHptCfgEntry 3 }


gnHptCfgTransparencyJ1 OBJECT-TYPE
        SYNTAX  INTEGER {
                        active(2),
                        passthrough(3),
                        notActive(4)
        }
        ACCESS  read-write
        STATUS mandatory
        DESCRIPTION
        " Send the received J1 string transparently or send the Transmitted J1
             configured string."
        DEFVAL { passthrough }
        ::= { gnHptCfgEntry 4 }


gnHptCfgEXCThresh OBJECT-TYPE
        SYNTAX  INTEGER {
                        tenExpMinus3(2),
                        tenExpMinus4(3),
                        tenExpMinus5(4)
        }
        ACCESS  read-write
        STATUS mandatory
        DESCRIPTION
        " If the bit error rate is higher than this threshold
         an EXC alarm would be generated.
        EXC is for excessive."
        DEFVAL { tenExpMinus3}
        ::= { gnHptCfgEntry 5 }

gnHptCfgSDThresh OBJECT-TYPE
        SYNTAX  INTEGER {
                        tenExpMinus6(3),
                        tenExpMinus7(4),
                        tenExpMinus8(5),
                        tenExpMinus9(6)
        }
        ACCESS  read-write
        STATUS mandatory
        DESCRIPTION
        " If the bit error rate is higher than this threshold
         a SD alarm would be generated.
        SD is for Signal Degrade."
        DEFVAL { tenExpMinus6}
        ::= { gnHptCfgEntry 6 }


gnHptCfgTug3Structure1 OBJECT-TYPE
        SYNTAX  OCTET STRING (SIZE(4))
        ACCESS  read-write
        STATUS mandatory
        DESCRIPTION
        "This field set the TUG-3 #1 structure: (hexadecimal number)
        the lsb 4 bits set VC12=0 or VC3=1 structure to the TUG3 #1. (the K of the KLM index is 1)
        for VC12 structure the next 21 bits (for SDH) or 28 bits (for SONET) set each of the VC12
        to be blocked (bit is 0) or unblocked (bit is 1).
        if it is VC3 only one more bit indicates if it is blocked (0) or unblocked (1).
        if a VC12 is set to blocked (this is the default) the system will send TU-AIS in that VC12.
        it it is unblocked it will be path-through or mapped to a E1/T1 port (according to the gnAccessCfgLowPathIndex).
        the 21 or 28 bits order is as folwed (from lsb to msb direction): first 7 bits for M=1 (from KLM index),
        the next 7 bits for M=2, the next for M=3, and the last (only for SONET) for M=4.
        Example : SDH, VC12 strcture, blocked VCs: KLM=111,121 (M=1), 112,122 (M=2), 163,173 (M=3), unblocked VCs: all the other.
        the value in bits will be: 0011111 1111100 1111100 0000, and in Hexadecimal: 0x7FE7C0. (so enter: 00 7F E7 C0)."
        ::= { gnHptCfgEntry 7 }

gnHptCfgTug3Structure2 OBJECT-TYPE
        SYNTAX  OCTET STRING (SIZE(4))
        ACCESS  read-write
        STATUS mandatory
        DESCRIPTION
        "This field set the TUG-3 #2 structure: (hexadecimal number)
        the lsb 4 bits set VC12=0 or VC3=1 structure to the TUG-3 #2. (the K of the KLM index is 2)
        for VC12 structure the next 21 bits (for SDH) or 28 bits (for SONET) set each of the VC12
        to be blocked (bit is 0) or unblocked (bit is 1).
        if it is VC3 only one more bit indicates if it is blocked (0) or unblocked (1).
        if a VC12 is set to blocked (this is the default) the system will send TU-AIS in that VC12.
        it it is unblocked it will be path-through or mapped to a E1/T1 port (according to the gnAccessCfgLowPathIndex).
        the 21 or 28 bits order is as folwed (from lsb to msb direction): first 7 bits for M=1 (from KLM index),
        the next 7 bits for M=2, the next for M=3, and the last (only for SONET) for M=4.
        Example : SDH, VC12 strcture, blocked VCs: KLM=211,221 (M=1), 212,222 (M=2), 263,273 (M=3), unblocked VCs: all the other.
        the value in bits will be: 0011111 1111100 1111100 0000, and in Hexadecimal: 0x7FE7C0. (so enter: 00 7F E7 C0)."
        ::= { gnHptCfgEntry 8 }

gnHptCfgTug3Structure3 OBJECT-TYPE
        SYNTAX  OCTET STRING (SIZE(4))
        ACCESS  read-write
        STATUS mandatory
        DESCRIPTION
        "This field set the TUG-3 #3 structure: (hexadecimal number)
        the lsb 4 bits set VC12=0 or VC3=1 structure to the TUG-3 #3. (the K of the KLM index is 3)
        for VC12 structure the next 21 bits (for SDH) or 28 bits (for SONET) set each of the VC12
        to be blocked (bit is 0) or unblocked (bit is 1).
        if it is VC3 only one more bit indicates if it is blocked (0) or unblocked (1).
        if a VC12 is set to blocked (this is the default) the system will send TU-AIS in that VC12.
        it it is unblocked it will be path-through or mapped to a E1/T1 port (according to the gnAccessCfgLowPathIndex).
        the 21 or 28 bits order is as folwed (from lsb to msb direction): first 7 bits for M=1 (from KLM index),
        the next 7 bits for M=2, the next for M=3, and the last (only for SONET) for M=4.
        Example : SDH, VC12 strcture, blocked VCs: KLM=311,321 (M=1), 312,322 (M=2), 363,373 (M=3), unblocked VCs: all the other.
        the value in bits will be: 0011111 1111100 1111100 0000, and in Hexadecimal: 0x7FE7C0. (so enter: 00 7F E7 C0)."
        ::= { gnHptCfgEntry 9 }

gnHptCfgSignalLabelMismatch OBJECT-TYPE
        SYNTAX  INTEGER{
                sendAlarm(2),
                sendAIS(3)
        }
        ACCESS  read-write
        STATUS mandatory
                DESCRIPTION
                  " In case of a C2 mismatch error, send or don't send AIS."
            DEFVAL        { sendAlarm }
        ::= { gnHptCfgEntry 10 }


gnHptCfgTrailPT1 OBJECT-TYPE
        SYNTAX  OCTET STRING (SIZE(4))
        ACCESS  read-write
        STATUS mandatory
        DESCRIPTION
        "This field set the TUG-3 #1 Trails Pass Through (hexadecimal number)
        It used by the NMS to indicate that a trail is not 'ended' on this ADM, but it is the
        last in the configuration chain.
        the lsb 4 bits set VC12=0 or VC3=1 structure to the TUG-3 #1.
        for VC12 structure the next 21 bits (for SDH) or 28 bits (for SONET) set each of the VC12
        to be blocked (bit is 0) or unblocked (bit is 1).
        if it is VC3 only one more bit indicates if it is Pass-Through disabled (0, default) or Pass-Through enabled (1).
        if it is VC12, the 21 or 28 bits order is as folwed (from lsb to msb direction): first 7 bits for M=1 (from KLM index),
        the next 7 bits for M=2, the next for M=3, and the last (only for SONET) for M=4."
        ::= { gnHptCfgEntry 11 }

gnHptCfgTrailPT2 OBJECT-TYPE
        SYNTAX  OCTET STRING (SIZE(4))
        ACCESS  read-write
        STATUS mandatory
        DESCRIPTION
        "This field set the TUG-3 #2 Trails Pass Through (hexadecimal number).
        It used by the NMS to indicate that a trail is not 'ended' on this ADM, but it is the
        last in the configuration chain.
        the lsb 4 bits set VC12=0 or VC3=1 structure to the TUG-3 #2.
        for VC12 structure the next 21 bits (for SDH) or 28 bits (for SONET) set each of the VC12
        to be blocked (bit is 0) or unblocked (bit is 1).
        if it is VC3 only one more bit indicates if it is Pass-Through disabled (0, default) or Pass-Through enabled (1).
        if it is VC12, the 21 or 28 bits order is as folwed (from lsb to msb direction): first 7 bits for M=1 (from KLM index),
        the next 7 bits for M=2, the next for M=3, and the last (only for SONET) for M=4."
        ::= { gnHptCfgEntry 12 }

gnHptCfgTrailPT3 OBJECT-TYPE
        SYNTAX  OCTET STRING (SIZE(4))
        ACCESS  read-write
        STATUS mandatory
        DESCRIPTION
        "This field set the TUG-3 #3 Trails Pass Through (hexadecimal number)
        It used by the NMS to indicate that a trail is not 'ended' on this ADM, but it is the
        last in the configuration chain.
        the lsb 4 bits set VC12=0 or VC3=1 structure to the TUG-3 #3.
        for VC12 structure the next 21 bits (for SDH) or 28 bits (for SONET) set each of the VC12
        to be blocked (bit is 0) or unblocked (bit is 1).
        if it is VC3 only one more bit indicates if it is Pass-Through disabled (0, default) or Pass-Through enabled (1).
        if it is VC12, the 21 or 28 bits order is as folwed (from lsb to msb direction): first 7 bits for M=1 (from KLM index),
        the next 7 bits for M=2, the next for M=3, and the last (only for SONET) for M=4."
        ::= { gnHptCfgEntry 13 }

gnHptStatTable OBJECT-TYPE
        SYNTAX  SEQUENCE OF GnHptStatEntry
        ACCESS  not-accessible
        STATUS mandatory
        DESCRIPTION
        "This table defines the status of the HPT part
                of the MUX."
        ::= { gnMux 8 }

gnHptStatEntry OBJECT-TYPE
        SYNTAX GnHptStatEntry
        ACCESS  not-accessible
        STATUS mandatory
        DESCRIPTION
        "This is an entry in the HPT part of the MUX
         Status Table. This table contains an interface index for every interface
         which type is PATH(50, according to RFC1573)."
        INDEX {  ifIndex }
        ::= { gnHptStatTable 1 }

GnHptStatEntry ::=
            SEQUENCE {
        gnHptStatReceivedJ1
             DisplayString,
        gnHptStatStatus
             OCTET STRING,
--        gnHptStatFarEndStatus
--             OCTET STRING,
        gnHptStatCurrentBer
                INTEGER,
        gnHptStatFarEndCurrentBer
                INTEGER,
        gnHptStatReceivedSignalLabel
             OCTET STRING
}

gnHptStatReceivedJ1 OBJECT-TYPE
        SYNTAX  DisplayString(SIZE(0..15))
        ACCESS  read-only
        STATUS mandatory
        DESCRIPTION
        "This is the J1 string that was received."
        ::= { gnHptStatEntry 1 }

gnHptStatStatus OBJECT-TYPE
        SYNTAX OCTET STRING(SIZE(2))
        ACCESS  read-only
        STATUS mandatory
        DESCRIPTION
         "Alarm status byte. Bit 1 is MSB, bit=1 when alarm active.
          bit 4  = LOP
          bit 5  = RDI
          bit 6  = AIS
          bit 7  = TIM
          bit 8  = SLM/PLM
          bit 9  = SD
          bit 10 = EXC
          bit 12 = UNEQ
          bit 15 = LOM"
        ::= { gnHptStatEntry 2 }

--gnHptStatFarEndStatus OBJECT-TYPE
--        SYNTAX OCTET STRING(SIZE(2))
--        ACCESS  read-only
--        STATUS mandatory
--        DESCRIPTION
--         "Alarm status byte. Bit 1 is MSB, bit=1 when alarm active.
--          bit 5  = RDI"
--        ::= { gnHptStatEntry 3 }

gnHptStatCurrentBer OBJECT-TYPE
        SYNTAX  INTEGER {
                        tenExpMinus3(2),
                        tenExpMinus4(3),
                        tenExpMinus5(4),
                        tenExpMinus6(5),
                        tenExpMinus7(6),
                        tenExpMinus8(7),
                        tenExpMinus9(8),
                        tenExpMinus10(9),
                        tenExpMinus11(10),
                        tenExpMinus12(11),
                        tenExpMinus13(12),
                        tenExpMinus14(13)
        }
        ACCESS  read-only
        STATUS mandatory
        DESCRIPTION
        " "
        ::= { gnHptStatEntry 3 }

gnHptStatFarEndCurrentBer OBJECT-TYPE
        SYNTAX  INTEGER {
                        tenExpMinus3(2),
                        tenExpMinus4(3),
                        tenExpMinus5(4),
                        tenExpMinus6(5),
                        tenExpMinus7(6),
                        tenExpMinus8(7),
                        tenExpMinus9(8),
                        tenExpMinus10(9),
                        tenExpMinus11(10),
                        tenExpMinus12(11),
                        tenExpMinus13(12),
                        tenExpMinus14(13)
        }
        ACCESS  read-only
        STATUS mandatory
        DESCRIPTION
        " "
        ::= { gnHptStatEntry 4 }

gnHptStatReceivedSignalLabel OBJECT-TYPE
        SYNTAX OCTET STRING(SIZE(1))
        ACCESS  read-only
        STATUS mandatory
        DESCRIPTION
        "This is the C2 string that was received."
        ::= { gnHptStatEntry 5 }


-- Statistics For HPT. All HPT tables are included for future development
-- and are not currently implemented.
gnHptMon OBJECT IDENTIFIER ::=  { gnMux 9 }

gnHptMonCurrTable OBJECT-TYPE
        SYNTAX  SEQUENCE OF GnHptMonCurrEntry
        ACCESS  not-accessible
        STATUS mandatory
        DESCRIPTION
        "This table maintains the counters of the HPT part
                of the MUX."
        ::= { gnHptMon 1 }

gnHptMonCurrEntry OBJECT-TYPE
        SYNTAX GnHptMonCurrEntry
        ACCESS  not-accessible
        STATUS mandatory
        DESCRIPTION
        "This is an entry in the HPT part of the MUX
         Counters Table. This table contains an interface index for every interface
         which type is PATH(50, according to RFC1573)."
        INDEX {  ifIndex }
        ::= { gnHptMonCurrTable 1 }

GnHptMonCurrEntry ::=
            SEQUENCE {
        --gnHptMonCurrES rfc1595
        --     Counter,
        --gnHptMonCurrSES
        --     Counter,
        gnHptMonCurrBBE
             Gauge,
        gnHptMonCurrUAS
             Gauge,
        gnHptMonCurrLastDayES
             Gauge,
        gnHptMonCurrLastDaySES
             Gauge,
        gnHptMonCurrLastDayBBE
             Gauge,
        gnHptMonCurrLastDayUAS
             Gauge
}



gnHptMonCurrBBE OBJECT-TYPE
        SYNTAX  Gauge
        ACCESS  read-only
        STATUS mandatory
        DESCRIPTION
        " The current number of Background Block Errors
         starting  from the present 15 minutes period."
        ::= { gnHptMonCurrEntry 1}

gnHptMonCurrUAS OBJECT-TYPE
        SYNTAX  Gauge
        ACCESS  read-only
        STATUS mandatory
        DESCRIPTION
        " The current number of Unavailable Seconds
         starting  from the present 15 minutes period."
        ::= { gnHptMonCurrEntry 2}


gnHptMonCurrLastDayES OBJECT-TYPE
        SYNTAX  Gauge
        ACCESS  read-only
        STATUS mandatory
        DESCRIPTION
        " The current number of Errored Seconds
         starting from the present 24 hours period."
        ::= { gnHptMonCurrEntry 3 }

gnHptMonCurrLastDaySES OBJECT-TYPE
        SYNTAX  Gauge
        ACCESS  read-only
        STATUS mandatory
        DESCRIPTION
        " The current number of Severely Errored Seconds
         starting from the present 24 hours period."
        ::= { gnHptMonCurrEntry 4 }

gnHptMonCurrLastDayBBE OBJECT-TYPE
        SYNTAX  Gauge
        ACCESS  read-only
        STATUS mandatory
        DESCRIPTION
        " The current number of Background Block Errors
         starting from the present 24 hours period."
        ::= { gnHptMonCurrEntry 5 }

gnHptMonCurrLastDayUAS OBJECT-TYPE
        SYNTAX  Gauge
        ACCESS  read-only
        STATUS mandatory
        DESCRIPTION
        " The current number of Unavailable  Seconds
         starting from the present 24 hours period."
        ::= { gnHptMonCurrEntry 6 }


gnHptMonIntervalTable OBJECT-TYPE
        SYNTAX  SEQUENCE OF GnHptMonIntervalEntry
        ACCESS  not-accessible
        STATUS mandatory
        DESCRIPTION
        "This table maintains the counters of the HPT part
                of the MUX per interval."
        ::= { gnHptMon 2 }

gnHptMonIntervalEntry OBJECT-TYPE
        SYNTAX GnHptMonIntervalEntry
        ACCESS  not-accessible
        STATUS mandatory
        DESCRIPTION
        "This is an entry in the HPT part of the MUX
         Counters Table. This table contains an interface index for every interface
         which type is PATH(50, according to RFC1573).
        This table is indexed by an interval index, between 1
        to 96 and representing each one 15 minutes.
               The oldest is 96."
        INDEX {  ifIndex, gnHptMonIntervalIdx}
        ::= { gnHptMonIntervalTable 1 }

GnHptMonIntervalEntry ::=
            SEQUENCE {
        gnHptMonIntervalIdx
              INTEGER,
        --gnHptMonIntervalES
        --     Counter,
        --gnHptMonIntervalSES
        --     Counter,
        gnHptMonIntervalBBE
             Gauge,
        gnHptMonIntervalUAS
             Gauge
}

gnHptMonIntervalIdx OBJECT-TYPE
        SYNTAX INTEGER (1..96)
        ACCESS read-only
        STATUS mandatory
        DESCRIPTION
        "This table is indexed per interval number. Each interval
        is of 15 minutes and the oldest is 96."
        ::= { gnHptMonIntervalEntry 1 }

gnHptMonIntervalBBE OBJECT-TYPE
        SYNTAX  Gauge
        ACCESS  read-only
        STATUS mandatory
        DESCRIPTION
        " The number of Background Block Errors
        per interval."
        ::= { gnHptMonIntervalEntry 2}

gnHptMonIntervalUAS OBJECT-TYPE
        SYNTAX  Gauge
        ACCESS  read-only
        STATUS mandatory
        DESCRIPTION
        " The  number of Unavailable Seconds per interval."
        ::= { gnHptMonIntervalEntry 3}


gnHptMonDayTable OBJECT-TYPE
        SYNTAX  SEQUENCE OF GnHptMonDayEntry
        ACCESS  not-accessible
        STATUS mandatory
        DESCRIPTION
        "This table maintains the counters of the HPT part
                of the MUX per 24 hours interval."
        ::= { gnHptMon 3 }

gnHptMonDayEntry OBJECT-TYPE
        SYNTAX GnHptMonDayEntry
        ACCESS  not-accessible
        STATUS mandatory
        DESCRIPTION
        "This is an entry in the HPT part of the MUX
         Counters Table. This table contains an interface index for every interface
         which type is PATH(50, according to RFC1573).
        This table is indexed by an interval index, between 1
        to 30 and representing each one 24 hours.
               The oldest is 30."
        INDEX {  ifIndex, gnHptMonDayIdx}
        ::= { gnHptMonDayTable 1 }

GnHptMonDayEntry ::=
            SEQUENCE {
        gnHptMonDayIdx
              INTEGER,
        gnHptMonDayES
             Gauge,
        gnHptMonDaySES
             Gauge,
        gnHptMonDayBBE
             Gauge,
        gnHptMonDayUAS
             Gauge
}

gnHptMonDayIdx OBJECT-TYPE
        SYNTAX INTEGER (1..30)
        ACCESS read-only
        STATUS mandatory
        DESCRIPTION
        "This table is indexed per interval number. Each interval
        is of 24 hours and the oldest is 30."
        ::= { gnHptMonDayEntry 1 }

gnHptMonDayES OBJECT-TYPE
        SYNTAX  Gauge
        ACCESS  read-only
        STATUS mandatory
        DESCRIPTION
        " The number of Errored Seconds per interval of 24 hours."
        ::= { gnHptMonDayEntry 2}

gnHptMonDaySES OBJECT-TYPE
        SYNTAX  Gauge
        ACCESS  read-only
        STATUS mandatory
        DESCRIPTION
        " The number of Severely Errored Seconds
         per interval of 24 hours."
        ::= { gnHptMonDayEntry 3}

gnHptMonDayBBE OBJECT-TYPE
        SYNTAX  Gauge
        ACCESS  read-only
        STATUS mandatory
        DESCRIPTION
        " The number of Background Block Errors
         per interval of 24 hours."
        ::= { gnHptMonDayEntry 4 }

gnHptMonDayUAS OBJECT-TYPE
        SYNTAX  Gauge
        ACCESS  read-only
        STATUS mandatory
        DESCRIPTION
        " The number of Unavailable Seconds
         per interval of 24 hours."
        ::= { gnHptMonDayEntry 5 }


gnHptFarEndMonCurrTable OBJECT-TYPE
        SYNTAX  SEQUENCE OF GnHptFarEndMonCurrEntry
        ACCESS  not-accessible
        STATUS mandatory
        DESCRIPTION
        "This table maintains the counters of the far end HPT part
                of the MUX."
        ::= { gnHptMon 4 }

gnHptFarEndMonCurrEntry OBJECT-TYPE
        SYNTAX GnHptFarEndMonCurrEntry
        ACCESS  not-accessible
        STATUS mandatory
        DESCRIPTION
        "This is an entry in the far end HPT part of the MUX
         Counters Table. This table contains an interface index for every interface
         which type is PATH(50, according to RFC1573)."
        INDEX {  ifIndex }
        ::= { gnHptFarEndMonCurrTable 1 }

GnHptFarEndMonCurrEntry ::=
            SEQUENCE {
        --gnHptFarEndMonCurrES rfc1595
        --     Counter,
        --gnHptFarEndMonCurrSES
        --     Counter,
        gnHptFarEndMonCurrBBE
             Gauge,
        gnHptFarEndMonCurrUAS
             Gauge,
        gnHptFarEndMonCurrLastDayES
             Gauge,
        gnHptFarEndMonCurrLastDaySES
             Gauge,
        gnHptFarEndMonCurrLastDayBBE
             Gauge,
        gnHptFarEndMonCurrLastDayUAS
             Gauge
}



gnHptFarEndMonCurrBBE OBJECT-TYPE
        SYNTAX  Gauge
        ACCESS  read-only
        STATUS mandatory
        DESCRIPTION
        " The current number of Background Block Errors
         starting from the present 15 minutes period."
        ::= { gnHptFarEndMonCurrEntry 1}

gnHptFarEndMonCurrUAS OBJECT-TYPE
        SYNTAX  Gauge
        ACCESS  read-only
        STATUS mandatory
        DESCRIPTION
        " The current number of Unavailable Seconds
         starting from the present 15 minutes period."
        ::= { gnHptFarEndMonCurrEntry 2}


gnHptFarEndMonCurrLastDayES OBJECT-TYPE
        SYNTAX  Gauge
        ACCESS  read-only
        STATUS mandatory
        DESCRIPTION
        " The current number of Errored Seconds
         starting from the present 24 hours period."
        ::= { gnHptFarEndMonCurrEntry 3 }

gnHptFarEndMonCurrLastDaySES OBJECT-TYPE
        SYNTAX  Gauge
        ACCESS  read-only
        STATUS mandatory
        DESCRIPTION
        " The current number of Severely Errored Seconds
         starting from the present 24 hours period."
        ::= { gnHptFarEndMonCurrEntry 4 }

gnHptFarEndMonCurrLastDayBBE OBJECT-TYPE
        SYNTAX  Gauge
        ACCESS  read-only
        STATUS mandatory
        DESCRIPTION
        " The current number of Background Block Errors
         starting         from the present 24 hours period."
        ::= { gnHptFarEndMonCurrEntry 5 }

gnHptFarEndMonCurrLastDayUAS OBJECT-TYPE
        SYNTAX  Gauge
        ACCESS  read-only
        STATUS mandatory
        DESCRIPTION
        " The current number of Unavailable  Seconds
         starting         from the present 24 hours period."
        ::= { gnHptFarEndMonCurrEntry 6 }


gnHptFarEndMonIntervalTable OBJECT-TYPE
        SYNTAX  SEQUENCE OF GnHptFarEndMonIntervalEntry
        ACCESS  not-accessible
        STATUS mandatory
        DESCRIPTION
        "This table maintains the counters of the far end HPT part
                of the MUX per interval."
        ::= { gnHptMon 5 }

gnHptFarEndMonIntervalEntry OBJECT-TYPE
        SYNTAX GnHptFarEndMonIntervalEntry
        ACCESS  not-accessible
        STATUS mandatory
        DESCRIPTION
        "This is an entry in the far end HPT part of the MUX
         Counters Table. This table contains an interface index for every interface
         which type is PATH(50, according to RFC1573).
        This table is indexed by an interval index, between 1
        to 96 and representing each one 15 minutes.
               The oldest is 96."
        INDEX {  ifIndex, gnHptFarEndMonIntervalIdx}
        ::= { gnHptFarEndMonIntervalTable 1 }

GnHptFarEndMonIntervalEntry ::=
            SEQUENCE {
        gnHptFarEndMonIntervalIdx
              INTEGER,
        --gnHptFarEndMonIntervalES
        --     Counter,
        --gnHptFarEndMonIntervalSES
        --     Counter,
        gnHptFarEndMonIntervalBBE
             Gauge,
        gnHptFarEndMonIntervalUAS
             Gauge
}

gnHptFarEndMonIntervalIdx OBJECT-TYPE
        SYNTAX INTEGER (1..96)
        ACCESS read-only
        STATUS mandatory
        DESCRIPTION
        "This table is indexed per interval number. Each interval
        is of 15 minutes and the oldest is 96."
        ::= { gnHptFarEndMonIntervalEntry 1 }

gnHptFarEndMonIntervalBBE OBJECT-TYPE
        SYNTAX  Gauge
        ACCESS  read-only
        STATUS mandatory
        DESCRIPTION
        " The number of Background Block Errors
        per interval."
        ::= { gnHptFarEndMonIntervalEntry 2}

gnHptFarEndMonIntervalUAS OBJECT-TYPE
        SYNTAX  Gauge
        ACCESS  read-only
        STATUS mandatory
        DESCRIPTION
        " The  number of Unavailable Seconds per interval."
        ::= { gnHptFarEndMonIntervalEntry 3}


gnHptFarEndMonDayTable OBJECT-TYPE
        SYNTAX  SEQUENCE OF GnHptFarEndMonDayEntry
        ACCESS  not-accessible
        STATUS mandatory
        DESCRIPTION
        "This table maintains the counters of the far end HPT part
                of the MUX per 24 hours interval."
        ::= { gnHptMon 6 }

gnHptFarEndMonDayEntry OBJECT-TYPE
        SYNTAX GnHptFarEndMonDayEntry
        ACCESS  not-accessible
        STATUS mandatory
        DESCRIPTION
        "This is an entry in the far end HPT part of the MUX
         Counters Table. This table contains an interface index for every interface
         which type is PATH(50, according to RFC1573).
        This table is indexed by an interval index, between 1
        to 30 and representing each one 24 hours.
               The oldest is 30."
        INDEX {  ifIndex, gnHptFarEndMonDayIdx}
        ::= { gnHptFarEndMonDayTable 1 }

GnHptFarEndMonDayEntry ::=
            SEQUENCE {
        gnHptFarEndMonDayIdx
              INTEGER,
        gnHptFarEndMonDayES
             Gauge,
        gnHptFarEndMonDaySES
             Gauge,
        gnHptFarEndMonDayBBE
             Gauge,
        gnHptFarEndMonDayUAS
             Gauge
}

gnHptFarEndMonDayIdx OBJECT-TYPE
        SYNTAX INTEGER (1..30)
        ACCESS read-only
        STATUS mandatory
        DESCRIPTION
        "This table is indexed per interval number. Each interval
        is of 24 hours and the oldest is 30."
        ::= { gnHptFarEndMonDayEntry 1 }

gnHptFarEndMonDayES OBJECT-TYPE
        SYNTAX  Gauge
        ACCESS  read-only
        STATUS mandatory
        DESCRIPTION
        " The number of Errored Seconds per interval of 24 hours."
        ::= { gnHptFarEndMonDayEntry 2}

gnHptFarEndMonDaySES OBJECT-TYPE
        SYNTAX  Gauge
        ACCESS  read-only
        STATUS mandatory
        DESCRIPTION
        " The number of Severely Errored Seconds
         per interval of 24 hours."
        ::= { gnHptFarEndMonDayEntry 3}

gnHptFarEndMonDayBBE OBJECT-TYPE
        SYNTAX  Gauge
        ACCESS  read-only
        STATUS mandatory
        DESCRIPTION
        " The number of Background Block Errors
         per interval of 24 hours."
        ::= { gnHptFarEndMonDayEntry 4 }

gnHptFarEndMonDayUAS OBJECT-TYPE
        SYNTAX  Gauge
        ACCESS  read-only
        STATUS mandatory
        DESCRIPTION
        " The number of Unavailable Seconds
         per interval of 24 hours."
        ::= { gnHptFarEndMonDayEntry 5 }

-- LPT part of the MUX. All LPT tables are included for future development
-- and are not currently implemented.
gnLptCfgTable OBJECT-TYPE
        SYNTAX  SEQUENCE OF GnLptCfgEntry
        ACCESS  not-accessible
        STATUS mandatory
        DESCRIPTION
        "This table maintains the counters of the LPT part
                of the MUX."
        ::= { gnMux 10 }

gnLptCfgEntry OBJECT-TYPE
        SYNTAX GnLptCfgEntry
        ACCESS  not-accessible
        STATUS mandatory
        DESCRIPTION
        "This is an entry in the LPT part of the MUX
         Configuration Table. This table contains an interface index for every
        interface         which type is VT(51, according to RFC1573)."
        INDEX {  ifIndex }
        ::= { gnLptCfgTable 1 }

GnLptCfgEntry ::=
            SEQUENCE {
--        gnLptCfgTransmittedC2
--         INTEGER,
--        gnLptCfgExpectedC2
--           INTEGER,
--        gnLptCfgMismatchC2
--            INTEGER,
--        gnLptCfgTransmittedJ1
--            DisplayString,
--        gnLptCfgExpectedJ1
--             DisplayString,
--        gnLptCfgMismatchJ1
--             INTEGER,
        gnLptCfgEXCThresh
             INTEGER,
        gnLptCfgSDThresh
             INTEGER
}

--gnLptCfgTransmittedC2 OBJECT-TYPE
--        SYNTAX  INTEGER
--        ACCESS  read-write
--        STATUS mandatory
--        DESCRIPTION
--        "This is the C2 byte that would be sent."
--        DEFVAL { '02'H}
--        ::= { gnLptCfgEntry 1 }

--gnLptCfgExpectedC2 OBJECT-TYPE
--        SYNTAX  INTEGER
--        ACCESS  read-write
--        STATUS mandatory
--        DESCRIPTION
--        "This is the C2 byte that is expected to be received."
--        DEFVAL { '02'H}
--        ::= { gnLptCfgEntry 2 }

--gnLptCfgMismatchC2 OBJECT-TYPE
--        SYNTAX  INTEGER{
--                sendAIS(2),
--                doNotSendAIS(3)
--        }
--        ACCESS  read-write
--        STATUS mandatory
--        DESCRIPTION
--        " In case of  C2 mismatch  error, send or don't send AIS."
--        DEFVAL { sendAIS }
--        ::= { gnLptCfgEntry 3 }

--gnLptCfgTransmittedJ1 OBJECT-TYPE
--        SYNTAX  DisplayString(SIZE(0..63))
--        ACCESS  read-write
--        STATUS mandatory
--        DESCRIPTION
--        "This is the J1 string that would be sent."
--        DEFVAL { "" }
--        ::= { gnLptCfgEntry 4 }

--gnLptCfgExpectedJ1 OBJECT-TYPE
--        SYNTAX  DisplayString(SIZE(0..63))
--        ACCESS  read-write
--        STATUS mandatory
--        DESCRIPTION
--          "This is the J1 string that is expected to be received."
--        DEFVAL { "" }
--        ::= { gnLptCfgEntry 5 }

--gnLptCfgMismatchJ1 OBJECT-TYPE
--        SYNTAX INTEGER{
--                transparency(2),
--                sendAlarm(3),
--                sendAIS(4)
--        }
--        ACCESS  read-write
--        STATUS mandatory
--        DESCRIPTION
--          " In case of  J1 mismatch  error send or don't send AIS."
--        DEFVAL { transparency }
--        ::= { gnLptCfgEntry 6 }

-- NOT IMPLEMENTED (access):
gnLptCfgEXCThresh  OBJECT-TYPE
        SYNTAX  INTEGER {
                        tenExpMinus3(2),
                        tenExpMinus4(3),
                        tenExpMinus5(4)
        }
        ACCESS  read-write
        STATUS mandatory
        DESCRIPTION
        " If the bit error rate is higher than this threshold
         an alarm would be generated.
        EXC is for excessive."
        DEFVAL { tenExpMinus3}
        ::= { gnLptCfgEntry 1 }

gnLptCfgSDThresh  OBJECT-TYPE
        SYNTAX  INTEGER {
                        tenExpMinus6(3),
                        tenExpMinus7(4),
                        tenExpMinus8(5),
                        tenExpMinus9(6),
                        notActive(15)
        }
        ACCESS  read-write
        STATUS mandatory
        DESCRIPTION
        " If the bit error rate is higher than this threshold
         an alarm would be generated.
        SD is for Signal Degrade."
        DEFVAL { tenExpMinus6}
        ::= { gnLptCfgEntry 2 }

gnLptStatTable OBJECT-TYPE
        SYNTAX  SEQUENCE OF GnLptStatEntry
        ACCESS  not-accessible
        STATUS mandatory
        DESCRIPTION
        "This table defines the status of the LPT part
                of the MUX."
        ::= { gnMux 11 }

gnLptStatEntry OBJECT-TYPE
        SYNTAX GnLptStatEntry
        ACCESS  not-accessible
        STATUS mandatory
        DESCRIPTION
        "This is an entry in the LPT part of the MUX
         Status Table. This table contains an interface index for every interface
         which type is VT(51, according to RFC1573)."
        INDEX {  ifIndex }
        ::= { gnLptStatTable 1 }

GnLptStatEntry ::=
            SEQUENCE {
        gnLptStatReceivedJ2
             DisplayString,
        gnLptStatStatus
                OCTET STRING,
--        gnLptStatFarEndStatus
--                OCTET STRING,
        gnLptStatProtectionMode
                INTEGER,
        gnLptStatCurrentBer
                INTEGER,
        gnLptStatFarEndCurrentBer
                INTEGER,
        gnLptStatReceivedSignalLabel
             OCTET STRING,
        gnLptStatKLM
                INTEGER
}

gnLptStatReceivedJ2 OBJECT-TYPE
        SYNTAX  DisplayString(SIZE(0..15))
        ACCESS  read-only
        STATUS mandatory
        DESCRIPTION
        "This is the J2 string that was received."
        ::= { gnLptStatEntry 1 }

gnLptStatStatus OBJECT-TYPE
        SYNTAX OCTET STRING(SIZE(2))
        ACCESS  read-only
        STATUS mandatory
        DESCRIPTION
         "Alarm status byte. Bit 1 is MSB, bit=1 when alarm active.
          bit 4  = LOP
          bit 5  = RDI
          bit 6  = AIS
          bit 7  = TIM
          bit 8  = SLM/PLM
          bit 9  = SD
          bit 10 = EXC
          bit 12 = UNEQ"
        ::= { gnLptStatEntry 2 }

--gnLptStatFarEndStatus OBJECT-TYPE
--        SYNTAX OCTET STRING(SIZE(2))
--        ACCESS  read-only
--        STATUS mandatory
--        DESCRIPTION
--        "bit 5  = RDI"
--        ::= { gnLptStatEntry 3 }

gnLptStatProtectionMode OBJECT-TYPE
        SYNTAX  INTEGER {
                working(2),
        protect(3),
                passthrough(4),
                notActive(5)
        }
        ACCESS  read-only
        STATUS mandatory
        DESCRIPTION
        " "
        ::= { gnLptStatEntry 3 }

gnLptStatCurrentBer OBJECT-TYPE
        SYNTAX  INTEGER {
                        tenExpMinus3(2),
                        tenExpMinus4(3),
                        tenExpMinus5(4),
                        tenExpMinus6(5),
                        tenExpMinus7(6),
                        tenExpMinus8(7),
                        tenExpMinus9(8),
                        tenExpMinus10(9),
                        tenExpMinus11(10),
                        tenExpMinus12(11),
                        tenExpMinus13(12),
                        tenExpMinus14(13)
        }
        ACCESS  read-only
        STATUS mandatory
        DESCRIPTION
        " "
        ::= { gnLptStatEntry 4 }

gnLptStatFarEndCurrentBer OBJECT-TYPE
        SYNTAX  INTEGER {
                        tenExpMinus3(2),
                        tenExpMinus4(3),
                        tenExpMinus5(4),
                        tenExpMinus6(5),
                        tenExpMinus7(6),
                        tenExpMinus8(7),
                        tenExpMinus9(8),
                        tenExpMinus10(9),
                        tenExpMinus11(10),
                        tenExpMinus12(11),
                        tenExpMinus13(12),
                        tenExpMinus14(13)
        }
        ACCESS  read-only
        STATUS mandatory
        DESCRIPTION
        " "
        ::= { gnLptStatEntry 5 }

gnLptStatReceivedSignalLabel OBJECT-TYPE
        SYNTAX OCTET STRING(SIZE(1))
        ACCESS  read-only
        STATUS mandatory
        DESCRIPTION
        "These are bits 1..3 of the V5 string that was received
         (bit 0 is the lsb)."
        ::= { gnLptStatEntry 6 }

gnLptStatKLM OBJECT-TYPE
        SYNTAX  INTEGER
        ACCESS  read-only
        STATUS  mandatory
        DESCRIPTION
        " "
        ::= { gnLptStatEntry 7 }


gnLptMon OBJECT IDENTIFIER ::=  { gnMux 12 }

gnLptMonCurrTable OBJECT-TYPE
        SYNTAX  SEQUENCE OF GnLptMonCurrEntry
        ACCESS  not-accessible
        STATUS mandatory
        DESCRIPTION
        "This table maintains the counters of the LPT part
                of the MUX."
        ::= { gnLptMon 1 }

gnLptMonCurrEntry OBJECT-TYPE
        SYNTAX GnLptMonCurrEntry
        ACCESS  not-accessible
        STATUS mandatory
        DESCRIPTION
        "This is an entry in the LPT part of the MUX
         Counters Table. This table contains an interface index for every interface
         which type is VT(51, according to RFC1573)."
        INDEX {  ifIndex }
        ::= { gnLptMonCurrTable 1 }

GnLptMonCurrEntry ::=
            SEQUENCE {
        --gnLptMonCurrES rfc1595
        --     Counter,
        --gnLptMonCurrSES
        --     Counter,
        gnLptMonCurrBBE
             Gauge,
        gnLptMonCurrUAS
             Gauge,
        gnLptMonCurrLastDayES
             Gauge,
        gnLptMonCurrLastDaySES
             Gauge,
        gnLptMonCurrLastDayBBE
             Gauge,
        gnLptMonCurrLastDayUAS
             Gauge
}



gnLptMonCurrBBE OBJECT-TYPE
        SYNTAX  Gauge
        ACCESS  read-only
        STATUS mandatory
        DESCRIPTION
        " The current number of Background Block Errors
         starting  from the present 15 minutes period."
        ::= { gnLptMonCurrEntry 1}

gnLptMonCurrUAS OBJECT-TYPE
        SYNTAX  Gauge
        ACCESS  read-only
        STATUS mandatory
        DESCRIPTION
        " The current number of Unavailable Seconds
         starting from the present 15 minutes period."
        ::= { gnLptMonCurrEntry 2}


gnLptMonCurrLastDayES OBJECT-TYPE
        SYNTAX  Gauge
        ACCESS  read-only
        STATUS mandatory
        DESCRIPTION
        " The current number of Errored Seconds
         starting from the present 24 hours period."
        ::= { gnLptMonCurrEntry 3 }

gnLptMonCurrLastDaySES OBJECT-TYPE
        SYNTAX  Gauge
        ACCESS  read-only
        STATUS mandatory
        DESCRIPTION
        " The current number of Severely Errored Seconds
         starting from the present 24 hours period."
        ::= { gnLptMonCurrEntry 4 }

gnLptMonCurrLastDayBBE OBJECT-TYPE
        SYNTAX  Gauge
        ACCESS  read-only
        STATUS mandatory
        DESCRIPTION
        " The current number of Background Block Errors
         starting         from the present 24 hours period."
        ::= { gnLptMonCurrEntry 5 }

gnLptMonCurrLastDayUAS OBJECT-TYPE
        SYNTAX  Gauge
        ACCESS  read-only
        STATUS mandatory
        DESCRIPTION
        " The current number of Unavailable  Seconds
         starting         from the present 24 hours period."
        ::= { gnLptMonCurrEntry 6 }


gnLptMonIntervalTable OBJECT-TYPE
        SYNTAX  SEQUENCE OF GnLptMonIntervalEntry
        ACCESS  not-accessible
        STATUS mandatory
        DESCRIPTION
        "This table maintains the counters of the LPT part
                of the MUX per interval."
        ::= { gnLptMon 2 }

gnLptMonIntervalEntry OBJECT-TYPE
        SYNTAX GnLptMonIntervalEntry
        ACCESS  not-accessible
        STATUS mandatory
        DESCRIPTION
        "This is an entry in the LPT part of the MUX
         Counters Table. This table contains an interface index for every interface
         which type is VT(51, according to RFC1573).
        This table is indexed by an interval index, between 1
        to 96 and representing each one 15 minutes.
               The oldest is 96."
        INDEX {  ifIndex, gnLptMonIntervalIdx}
        ::= { gnLptMonIntervalTable 1 }

GnLptMonIntervalEntry ::=
            SEQUENCE {
        gnLptMonIntervalIdx
              INTEGER,
        --gnLptMonIntervalES
        --     Counter,
        --gnLptMonIntervalSES
        --     Counter,
        gnLptMonIntervalBBE
             Gauge,
        gnLptMonIntervalUAS
             Gauge
}

gnLptMonIntervalIdx OBJECT-TYPE
        SYNTAX INTEGER (1..96)
        ACCESS read-only
        STATUS mandatory
        DESCRIPTION
        "This table is indexed per interval number. Each interval
        is of 15 minutes and the oldest is 96."
        ::= { gnLptMonIntervalEntry 1 }

gnLptMonIntervalBBE OBJECT-TYPE
        SYNTAX  Gauge
        ACCESS  read-only
        STATUS mandatory
        DESCRIPTION
        " The number of Background Block Errors
        per interval."
        ::= { gnLptMonIntervalEntry 2}

gnLptMonIntervalUAS OBJECT-TYPE
        SYNTAX  Gauge
        ACCESS  read-only
        STATUS mandatory
        DESCRIPTION
        " The  number of Unavailable Seconds per interval."
        ::= { gnLptMonIntervalEntry 3}


gnLptMonDayTable OBJECT-TYPE
        SYNTAX  SEQUENCE OF GnLptMonDayEntry
        ACCESS  not-accessible
        STATUS mandatory
        DESCRIPTION
        "This table maintains the counters of the LPT part
                of the MUX per 24 hours interval."
        ::= { gnLptMon 3 }

gnLptMonDayEntry OBJECT-TYPE
        SYNTAX GnLptMonDayEntry
        ACCESS  not-accessible
        STATUS mandatory
        DESCRIPTION
        "This is an entry in the LPT part of the MUX
         Counters Table. This table contains four groups of rows,
        indexed by ifIndex= 1,2 for local IDU and
        ifIndex = 101 and 102 for remote IDU.
        This table is indexed by an interval index, between 1
        to 30 and representing each one 24 hours.
               The oldest is 30."
        INDEX {  ifIndex, gnLptMonDayIdx}
        ::= { gnLptMonDayTable 1 }

GnLptMonDayEntry ::=
            SEQUENCE {
        gnLptMonDayIdx
              INTEGER,
        gnLptMonDayES
             Gauge,
        gnLptMonDaySES
             Gauge,
        gnLptMonDayBBE
             Gauge,
        gnLptMonDayUAS
             Gauge
}

gnLptMonDayIdx OBJECT-TYPE
        SYNTAX INTEGER (1..30)
        ACCESS read-only
        STATUS mandatory
        DESCRIPTION
        "This table is indexed per interval number. Each interval
        is of 24 hours and the oldest is 30."
        ::= { gnLptMonDayEntry 1 }

gnLptMonDayES OBJECT-TYPE
        SYNTAX  Gauge
        ACCESS  read-only
        STATUS mandatory
        DESCRIPTION
        " The number of Errored Seconds per interval of 24 hours."
        ::= { gnLptMonDayEntry 2}

gnLptMonDaySES OBJECT-TYPE
        SYNTAX  Gauge
        ACCESS  read-only
        STATUS mandatory
        DESCRIPTION
        " The number of Severely Errored Seconds
         per interval of 24 hours."
        ::= { gnLptMonDayEntry 3}

gnLptMonDayBBE OBJECT-TYPE
        SYNTAX  Gauge
        ACCESS  read-only
        STATUS mandatory
        DESCRIPTION
        " The number of Background Block Errors
         per interval of 24 hours."
        ::= { gnLptMonDayEntry 4 }

gnLptMonDayUAS OBJECT-TYPE
        SYNTAX  Gauge
        ACCESS  read-only
        STATUS mandatory
        DESCRIPTION
        " The number of Unavailable Seconds
         per interval of 24 hours."
        ::= { gnLptMonDayEntry 5 }


gnLptFarEndMonCurrTable OBJECT-TYPE
        SYNTAX  SEQUENCE OF GnLptFarEndMonCurrEntry
        ACCESS  not-accessible
        STATUS mandatory
        DESCRIPTION
        "This table maintains the counters of the far end LPT part
                of the MUX."
        ::= { gnLptMon 4 }

gnLptFarEndMonCurrEntry OBJECT-TYPE
        SYNTAX GnLptFarEndMonCurrEntry
        ACCESS  not-accessible
        STATUS mandatory
        DESCRIPTION
        "This is an entry in the far end LPT part of the MUX
         Counters Table. This table contains an interface index for every interface
         which type is VT(51, according to RFC1573)."
        INDEX {  ifIndex }
        ::= { gnLptFarEndMonCurrTable 1 }

GnLptFarEndMonCurrEntry ::=
            SEQUENCE {
        --gnLptFarEndMonCurrES rfc1595
        --     Counter,
        --gnLptFarEndMonCurrSES
        --     Counter,
        gnLptFarEndMonCurrBBE
             Gauge,
        gnLptFarEndMonCurrUAS
             Gauge,
        gnLptFarEndMonCurrLastDayES
             Gauge,
        gnLptFarEndMonCurrLastDaySES
             Gauge,
        gnLptFarEndMonCurrLastDayBBE
             Gauge,
        gnLptFarEndMonCurrLastDayUAS
             Gauge
}



gnLptFarEndMonCurrBBE OBJECT-TYPE
        SYNTAX  Gauge
        ACCESS  read-only
        STATUS mandatory
        DESCRIPTION
        " The current number of Background Block Errors
         starting  from the present 15 minutes period."
        ::= { gnLptFarEndMonCurrEntry 1}

gnLptFarEndMonCurrUAS OBJECT-TYPE
        SYNTAX  Gauge
        ACCESS  read-only
        STATUS mandatory
        DESCRIPTION
        " The current number of Unavailable Seconds
         starting  from the present 15 minutes period."
        ::= { gnLptFarEndMonCurrEntry 2}


gnLptFarEndMonCurrLastDayES OBJECT-TYPE
        SYNTAX  Gauge
        ACCESS  read-only
        STATUS mandatory
        DESCRIPTION
        " The current number of Errored Seconds
         starting  from the present 24 hours period."
        ::= { gnLptFarEndMonCurrEntry 3 }

gnLptFarEndMonCurrLastDaySES OBJECT-TYPE
        SYNTAX  Gauge
        ACCESS  read-only
        STATUS mandatory
        DESCRIPTION
        " The current number of Severely Errored Seconds
         starting         from the present 24 hours period."
        ::= { gnLptFarEndMonCurrEntry 4 }

gnLptFarEndMonCurrLastDayBBE OBJECT-TYPE
        SYNTAX  Gauge
        ACCESS  read-only
        STATUS mandatory
        DESCRIPTION
        " The current number of Background Block Errors
         starting         from the present 24 hours period."
        ::= { gnLptFarEndMonCurrEntry 5 }

gnLptFarEndMonCurrLastDayUAS OBJECT-TYPE
        SYNTAX  Gauge
        ACCESS  read-only
        STATUS mandatory
        DESCRIPTION
        " The current number of Unavailable  Seconds
         starting         from the present 24 hours period."
        ::= { gnLptFarEndMonCurrEntry 6 }


gnLptFarEndMonIntervalTable OBJECT-TYPE
        SYNTAX  SEQUENCE OF GnLptFarEndMonIntervalEntry
        ACCESS  not-accessible
        STATUS mandatory
        DESCRIPTION
        "This table maintains the counters of the far end LPT part
                of the MUX per interval."
        ::= { gnLptMon 5 }

gnLptFarEndMonIntervalEntry OBJECT-TYPE
        SYNTAX GnLptFarEndMonIntervalEntry
        ACCESS  not-accessible
        STATUS mandatory
        DESCRIPTION
        "This is an entry in the far end LPT part of the MUX
         Counters Table. This table contains an interface index for every interface
         which type is VT(51, according to RFC1573).
        This table is indexed by an interval index, between 1
        to 96 and representing each one 15 minutes.
               The oldest is 96."
        INDEX {  ifIndex, gnLptFarEndMonIntervalIdx}
        ::= { gnLptFarEndMonIntervalTable 1 }

GnLptFarEndMonIntervalEntry ::=
            SEQUENCE {
        gnLptFarEndMonIntervalIdx
              INTEGER,
        --gnLptFarEndMonIntervalES
        --     Counter,
        --gnLptFarEndMonIntervalSES
        --     Counter,
        gnLptFarEndMonIntervalBBE
             Gauge,
        gnLptFarEndMonIntervalUAS
             Gauge
}

gnLptFarEndMonIntervalIdx OBJECT-TYPE
        SYNTAX INTEGER (1..96)
        ACCESS read-only
        STATUS mandatory
        DESCRIPTION
        "This table is indexed per interval number. Each interval
        is of 15 minutes and the oldest is 96."
        ::= { gnLptFarEndMonIntervalEntry 1 }

gnLptFarEndMonIntervalBBE OBJECT-TYPE
        SYNTAX  Gauge
        ACCESS  read-only
        STATUS mandatory
        DESCRIPTION
        " The number of Background Block Errors
        per interval."
        ::= { gnLptFarEndMonIntervalEntry 2}

gnLptFarEndMonIntervalUAS OBJECT-TYPE
        SYNTAX  Gauge
        ACCESS  read-only
        STATUS mandatory
        DESCRIPTION
        " The  number of Unavailable Seconds per interval."
        ::= { gnLptFarEndMonIntervalEntry 3}


gnLptFarEndMonDayTable OBJECT-TYPE
        SYNTAX  SEQUENCE OF GnLptFarEndMonDayEntry
        ACCESS  not-accessible
        STATUS mandatory
        DESCRIPTION
        "This table maintains the counters of the far end LPT part
                of the MUX per 24 hours interval."
        ::= { gnLptMon 6 }

gnLptFarEndMonDayEntry OBJECT-TYPE
        SYNTAX GnLptFarEndMonDayEntry
        ACCESS  not-accessible
        STATUS mandatory
        DESCRIPTION
        "This is an entry in the far end LPT part of the MUX
         Counters Table. This table contains an interface index for every interface
         which type is VT(51, according to RFC1573).
        This table is indexed by an interval index, between 1
        to 30 and representing each one 24 hours.
               The oldest is 30."
        INDEX {  ifIndex, gnLptFarEndMonDayIdx}
        ::= { gnLptFarEndMonDayTable 1 }

GnLptFarEndMonDayEntry ::=
            SEQUENCE {
        gnLptFarEndMonDayIdx
              INTEGER,
        gnLptFarEndMonDayES
             Gauge,
        gnLptFarEndMonDaySES
             Gauge,
        gnLptFarEndMonDayBBE
             Gauge,
        gnLptFarEndMonDayUAS
             Gauge
}

gnLptFarEndMonDayIdx OBJECT-TYPE
        SYNTAX INTEGER (1..30)
        ACCESS read-only
        STATUS mandatory
        DESCRIPTION
        "This table is indexed per interval number. Each interval
        is of 24 hours and the oldest is 30."
        ::= { gnLptFarEndMonDayEntry 1 }

gnLptFarEndMonDayES OBJECT-TYPE
        SYNTAX  Gauge
        ACCESS  read-only
        STATUS mandatory
        DESCRIPTION
        " The number of Errored Seconds per interval of 24 hours."
        ::= { gnLptFarEndMonDayEntry 2}

gnLptFarEndMonDaySES OBJECT-TYPE
        SYNTAX  Gauge
        ACCESS  read-only
        STATUS mandatory
        DESCRIPTION
        " The number of Severely Errored Seconds
         per interval of 24 hours."
        ::= { gnLptFarEndMonDayEntry 3}

gnLptFarEndMonDayBBE OBJECT-TYPE
        SYNTAX  Gauge
        ACCESS  read-only
        STATUS mandatory
        DESCRIPTION
        " The number of Background Block Errors
         per interval of 24 hours."
        ::= { gnLptFarEndMonDayEntry 4 }

gnLptFarEndMonDayUAS OBJECT-TYPE
        SYNTAX  Gauge
        ACCESS  read-only
        STATUS mandatory
        DESCRIPTION
        " The number of Unavailable Seconds
         per interval of 24 hours."
        ::= { gnLptFarEndMonDayEntry 5 }

gnMuxCfgXTable OBJECT-TYPE
        SYNTAX  SEQUENCE OF GnMuxCfgXEntry
        ACCESS  not-accessible
        STATUS mandatory
        DESCRIPTION
        "This table defines the configuration of the mux board."
        ::= { gnMux 13 }

gnMuxCfgXEntry OBJECT-TYPE
        SYNTAX GnMuxCfgXEntry
        ACCESS  not-accessible
        STATUS mandatory
        DESCRIPTION
        "This is an entry in the mux configuration table."
        INDEX {  gnMuxCfgXId }
        ::= { gnMuxCfgXTable 1 }

GnMuxCfgXEntry ::=
            SEQUENCE {
        gnMuxCfgXId
                INTEGER,
        gnMuxCfgXWsAdmin
                INTEGER,
        gnMuxCfgXWsLoopback
                INTEGER,
        gnMuxCfgXHwReset
                INTEGER,
        gnMUXCfgXTempLicenseEnable
                INTEGER,
        gnMUXCfgXTempLicenseTimer
                INTEGER
}

gnMuxCfgXId OBJECT-TYPE
        SYNTAX  INTEGER
        {
                mux1(3),
                mux2(4)
        }
    ACCESS  read-only
           STATUS mandatory
    DESCRIPTION
    "This value indicates which device is involved
        in the specific row."
    ::= { gnMuxCfgXEntry 1 }

gnMuxCfgXWsAdmin OBJECT-TYPE
        SYNTAX  INTEGER {
                enable(2),
                disable(3)
        }
        ACCESS  read-write
        STATUS mandatory
        DESCRIPTION
        " Enable Disable drawer wayside channel "
        DEFVAL { enable }
        ::= { gnMuxCfgXEntry 2 }

gnMuxCfgXWsLoopback OBJECT-TYPE
        SYNTAX  INTEGER {
                        noloopback(2),
                        waySideLoop(3)
        }
        ACCESS  read-write
        STATUS mandatory
        DESCRIPTION
        "This parameter controls the WAYSIDE channel loopback diagnostic operations."
        DEFVAL { noloopback }
        ::= { gnMuxCfgXEntry 3 }

gnMuxCfgXHwReset OBJECT-TYPE
                SYNTAX  INTEGER
                {
                        noOperation(2),
                        hwReset(3)
                }
                ACCESS  read-write
                STATUS mandatory
                DESCRIPTION
                "hwReset - Hardware reset for mux board."
                DEFVAL { noOperation }
                ::= { gnMuxCfgXEntry 4 }

gnMUXCfgXTempLicenseEnable OBJECT-TYPE
                SYNTAX  INTEGER
                {
                        enable(2),
                        disable(3)
                }
                ACCESS  read-write
                STATUS mandatory
                DESCRIPTION
                "Set temporary license enable or disable"
                DEFVAL { disable }
                ::= { gnMuxCfgXEntry 5 }

gnMUXCfgXTempLicenseTimer OBJECT-TYPE
				SYNTAX  INTEGER (0..65535)
                ACCESS  read-only
                STATUS mandatory
                DESCRIPTION
                "This value indicates the temporary license timer"
                DEFVAL { 0 }
                ::= { gnMuxCfgXEntry 6 }


 gnMuxStatXTable OBJECT-TYPE
        SYNTAX  SEQUENCE OF GnMuxStatXEntry
        ACCESS  not-accessible
        STATUS mandatory
        DESCRIPTION
        "This table defines the status of the mux board."
        ::= { gnMux 14 }

gnMuxStatXEntry OBJECT-TYPE
        SYNTAX GnMuxStatXEntry
        ACCESS  not-accessible
        STATUS mandatory
        DESCRIPTION
        "This is an entry in the mux configuration table."
        INDEX {  gnMuxStatXId }
        ::= { gnMuxStatXTable 1 }

GnMuxStatXEntry ::=
            SEQUENCE {
        gnMuxStatXId
                INTEGER,
        gnMuxStatXMuxSerialNumber
                DisplayString,
        gnMuxStatXIfLeds
                OCTET STRING,
        gnMuxStatXNumOfIfOnClass1
                INTEGER,
        gnMuxStatXNumOfIfOnClass2
                INTEGER,
        gnMuxStatXNumOfIfOnClass3
                INTEGER,
        gnMuxStatXAesAdmin
                INTEGER,
        gnMuxStatXMuxFWVer
          DisplayString,
        gnMuxStatXMuxFWPostVer
          DisplayString,
        gnMuxStatXBoardConnector
                INTEGER,
        gnMuxStatXBoardType
                INTEGER
}

gnMuxStatXId OBJECT-TYPE
        SYNTAX  INTEGER
        {
                mux1(3),
                mux2(4)
        }
    ACCESS  read-only
           STATUS mandatory
    DESCRIPTION
    "This value indicates which device is involved
        in the specific row."
    ::= { gnMuxStatXEntry 1 }

gnMuxStatXMuxSerialNumber OBJECT-TYPE
        SYNTAX  DisplayString(SIZE(0..20))
        ACCESS  read-only
        STATUS mandatory
        DESCRIPTION
        "This is the MUX serial number - up to 20 characters "
        ::= { gnMuxStatXEntry 2 }

gnMuxStatXIfLeds OBJECT-TYPE
        SYNTAX OCTET STRING(SIZE(4))
        ACCESS  read-only
        STATUS mandatory
        DESCRIPTION
        "The status of the Interface LEDs. For the management station use.
         Each two bits represents one led as follows: 00 - Gray, 01 - Green, 10 - Orange, 11 - Red.
         The led order: Led1 is msb 2 bits , after it led2, till led 16 - 2 lsb bits."
        ::= { gnMuxStatXEntry 3 }

        gnMuxStatXNumOfIfOnClass1 OBJECT-TYPE
        SYNTAX  INTEGER (0..65535)
        ACCESS  read-only
        STATUS mandatory
        DESCRIPTION
        "This value indicates the actual number of interfaces on class 1."
        DEFVAL { 0 }
        ::= { gnMuxStatXEntry 4 }

        gnMuxStatXNumOfIfOnClass2 OBJECT-TYPE
        SYNTAX  INTEGER (0..65535)
        ACCESS  read-only
        STATUS mandatory
        DESCRIPTION
        "This value indicates the actual number of interfaces on class 2."
        DEFVAL { 0 }
        ::= { gnMuxStatXEntry 5 }

        gnMuxStatXNumOfIfOnClass3 OBJECT-TYPE
        SYNTAX  INTEGER (0..65535)
        ACCESS  read-only
        STATUS mandatory
        DESCRIPTION
        "This value indicates the actual number of interfaces on class 3."
        DEFVAL { 0 }
        ::= { gnMuxStatXEntry 6 }

        gnMuxStatXAesAdmin OBJECT-TYPE
        SYNTAX  INTEGER {
                        enable(2),
                        disable(3),
                        notSupport(4),
                        systemFailure(5)
        }
        ACCESS  read-only
        STATUS mandatory
        DESCRIPTION
        "This parameter defines encryption admin mode."
        DEFVAL { disable }
        ::= { gnMuxStatXEntry 7 }

        gnMuxStatXMuxFWVer OBJECT-TYPE
                SYNTAX  DisplayString (SIZE(0..15))
                ACCESS  read-only
                STATUS mandatory
                DESCRIPTION
                "This is the Mux firmware version."
                ::= { gnMuxStatXEntry 8 }

        gnMuxStatXMuxFWPostVer OBJECT-TYPE
                SYNTAX  DisplayString (SIZE(0..15))
                ACCESS  read-only
                STATUS mandatory
                DESCRIPTION
                "This is the Mux post reset firmware version."
                ::= { gnMuxStatXEntry 9 }

        gnMuxStatXBoardConnector OBJECT-TYPE
        SYNTAX  INTEGER {
                noInterface(2),
                oneElectricalSTM1(3),
                oneFiberSTM1SingleMode(4),
                oneFiberSTM1MultiMode(5),
                twoElectricalSTM1(6),
                twoFiberSTM1SingleMode(7),
                twoFiberSTM1MultiMode(8),
                oneFEOnly(9),
                oneFEplus4E1(10),
                oneFEplus8E1(11),
                oneFEplus4T1(12),
                oneFEplus8T1(13),
                twoFEOnly(14),
                twoFEplus4E1(15),
                twoFEplus8E1(16),
                twoFEplus4T1(17),
                twoFEplus8T1(18),
                oneDS3(19),
                threeDS3(20),
                oneE3(21),
                threeE3(22),
                oneOpticalGBEOnly(23),
                oneOpticalGBEPlus8E1(24),
                oneOpticalGBEPlus8T1(25),
                  oneElectricalGBEOnly(26),
                oneElectricalGBEPlus8E1(27),
                oneElectricalGBEPlus8T1(28),
                oneFEplus64E1(29),
                oneFEplus64T1(30),
		        eightE1Only(31),
		        eightT1Only(32),
				oneStm1XC(33),
				twoStm1XC(34)

        }
        ACCESS  read-only
        STATUS mandatory
        DESCRIPTION
        "This parameter defines the connector of the mux board, for NMS use."
        DEFVAL { noInterface }
        ::= { gnMuxStatXEntry 10 }

        gnMuxStatXBoardType OBJECT-TYPE
        SYNTAX  INTEGER {
                        v1(2), -- phos
                        v2(3), -- summit
                        v3(4), -- avalon
                        v4(5)  -- phoenix
        }
        ACCESS  read-only
        STATUS mandatory
        DESCRIPTION
        "This parameter defines the type of the mux."
        DEFVAL { v1 }
        ::= { gnMuxStatXEntry 11 }


-- This group contains the parameters concerning the AUX
gnAux OBJECT IDENTIFIER ::=  { gnIDU 4 }

gnAuxGeneral OBJECT IDENTIFIER ::=  { gnAux 1 }

gnAuxGeneralTable OBJECT-TYPE
        SYNTAX  SEQUENCE OF GnAuxGeneralEntry
        ACCESS  not-accessible
        STATUS mandatory
        DESCRIPTION
        "This table defines the commands of the Auxiliary channel."
        ::= {gnAuxGeneral 1}

gnAuxGeneralEntry OBJECT-TYPE
        SYNTAX GnAuxGeneralEntry
        ACCESS  not-accessible
        STATUS mandatory
        DESCRIPTION
        "This is an entry in the Auxiliary channel command Table."
        INDEX {gnAuxGeneralId}
        ::= {gnAuxGeneralTable 1}

GnAuxGeneralEntry ::=
            SEQUENCE {
        gnAuxGeneralId
                        INTEGER,
        gnAuxGeneralSyncIdcDataBase
                        INTEGER
        }

gnAuxGeneralId OBJECT-TYPE
        SYNTAX  INTEGER
        {
                local(1)
        }
    ACCESS  read-only
           STATUS mandatory
                DESCRIPTION
              " "
    ::= { gnAuxGeneralEntry 1 }

gnAuxGeneralSyncIdcDataBase OBJECT-TYPE
        SYNTAX  INTEGER {
                        noOperation(2),
                        auxToIdc(3),
                        idcToAux(4)
        }
        ACCESS  read-write
        STATUS mandatory
        DESCRIPTION
        "This parameter synchronize between hardware and data base of auxiliary channel."
        DEFVAL { noOperation }
        ::= { gnAuxGeneralEntry 2 }

gnWsc OBJECT IDENTIFIER ::=  { gnAux 2 }

gnWscCfgTable OBJECT-TYPE
        SYNTAX  SEQUENCE OF GnWscCfgEntry
        ACCESS  not-accessible
        STATUS mandatory
        DESCRIPTION
        "This table defines the configuration of the Wayside channel."
        ::= { gnWsc 1 }

gnWscCfgEntry OBJECT-TYPE
        SYNTAX GnWscCfgEntry
        ACCESS  not-accessible
        STATUS mandatory
        DESCRIPTION
        "This is an entry in the Wayside channel part of the AUX Configuration Table."
        INDEX {gnWscCfgId, gnWscCfgChNumber}
        ::= { gnWscCfgTable 1 }

GnWscCfgEntry ::=
            SEQUENCE {
        gnWscCfgId
                        INTEGER,
        gnWscCfgChNumber
                        INTEGER,
        gnWscCfgRouting
                        INTEGER,
        gnWscCfgEnable
                        INTEGER,
        gnWscCfgBitRate
                        INTEGER,
        gnWscCfgType
                        INTEGER
        }

gnWscCfgId OBJECT-TYPE
        SYNTAX  INTEGER
        {
                local(1)
        }
    ACCESS  read-only
           STATUS mandatory
    DESCRIPTION
    " "
    ::= { gnWscCfgEntry 1 }

gnWscCfgChNumber OBJECT-TYPE
        SYNTAX  INTEGER
        {
                channel1(1),
                channel2(2)
        }
    ACCESS  read-only
           STATUS mandatory
    DESCRIPTION
    "Wayside channel number."
    ::= { gnWscCfgEntry 2 }

gnWscCfgRouting OBJECT-TYPE
        SYNTAX  INTEGER
        {
                drawer1(2),
                drawer2(3)
        }
    ACCESS  read-write
           STATUS mandatory
    DESCRIPTION
    "Wayside channel routing."
        DEFVAL { drawer1 }
    ::= { gnWscCfgEntry 3 }

gnWscCfgEnable OBJECT-TYPE
        SYNTAX  INTEGER
        {
                enable(2),
                disable(3)
        }
    ACCESS  read-write
           STATUS mandatory
    DESCRIPTION
    "Wayside channel enable\disable."
        DEFVAL { enable }
    ::= { gnWscCfgEntry 4 }

gnWscCfgBitRate OBJECT-TYPE
        SYNTAX  INTEGER
        {
                low(2),
                high(3)
        }
    ACCESS  read-write
           STATUS mandatory
    DESCRIPTION
    "Wayside channel bit rate."
        DEFVAL { low }
    ::= { gnWscCfgEntry 5 }

gnWscCfgType OBJECT-TYPE
        SYNTAX  INTEGER
        {
                e1(2),
                t1(3),
				fastEthernet(4)
        }
    ACCESS  read-write
           STATUS mandatory
    DESCRIPTION
    "Wayside channel bit rate."
        DEFVAL { e1 }
    ::= { gnWscCfgEntry 6 }

gnWscStatTable OBJECT-TYPE
        SYNTAX  SEQUENCE OF GnWscStatEntry
        ACCESS  not-accessible
        STATUS mandatory
        DESCRIPTION
        "This table defines the status of the Wayside channel."
        ::= { gnWsc 2 }

gnWscStatEntry OBJECT-TYPE
        SYNTAX GnWscStatEntry
        ACCESS  not-accessible
        STATUS mandatory
        DESCRIPTION
        "This is an entry in the Wayside channel part of the AUX Status Table."
        INDEX {gnWscStatId, gnWscStatChNumber}
        ::= { gnWscStatTable 1 }

GnWscStatEntry ::=
            SEQUENCE {
        gnWscStatId
                        INTEGER,
        gnWscStatChNumber
                        INTEGER,
        gnWscStatBitRateSupport
                        INTEGER
        }

gnWscStatId OBJECT-TYPE
        SYNTAX  INTEGER
        {
                local(1)
        }
    ACCESS  read-only
           STATUS mandatory
    DESCRIPTION
    " "
    ::= { gnWscStatEntry 1 }

gnWscStatChNumber OBJECT-TYPE
        SYNTAX  INTEGER
        {
                channel1(1),
                channel2(2)
        }
    ACCESS  read-only
           STATUS mandatory
    DESCRIPTION
    "Wayside channel number."
    ::= { gnWscStatEntry 2 }

gnWscStatBitRateSupport OBJECT-TYPE
        SYNTAX  INTEGER {
                supported(2),
                notSupported(3)
        }
        ACCESS  read-only
        STATUS mandatory
        DESCRIPTION
    "Indication for Wayside channel bit rate support."
        DEFVAL { notSupported }
        ::= {gnWscStatEntry 3}

gnEow OBJECT IDENTIFIER ::=  { gnAux 3 }

gnEowCfgTable OBJECT-TYPE
        SYNTAX  SEQUENCE OF GnEowCfgEntry
        ACCESS  not-accessible
        STATUS mandatory
        DESCRIPTION
        "This table defines the configuration of the EOW."
        ::= { gnEow 1 }

gnEowCfgEntry OBJECT-TYPE
        SYNTAX GnEowCfgEntry
        ACCESS  not-accessible
        STATUS mandatory
        DESCRIPTION
        "This is an entry in the EOW configuration Table."
        INDEX {gnEowCfgId}
        ::= { gnEowCfgTable 1 }

GnEowCfgEntry ::=
            SEQUENCE {
        gnEowCfgId
                        INTEGER,
        gnEowCfgEowLeftEnable
                        INTEGER,
        gnEowCfgEowRightEnable
                        INTEGER,
        gnEowCfgEowCascadeEnable
                        INTEGER
        }

gnEowCfgId OBJECT-TYPE
        SYNTAX  INTEGER
        {
                local(1)
        }
    ACCESS  read-only
           STATUS mandatory
    DESCRIPTION
    " "
    ::= { gnEowCfgEntry 1 }

gnEowCfgEowLeftEnable OBJECT-TYPE
        SYNTAX  INTEGER
        {
                enable(2),
                disable(3)
        }
    ACCESS  read-write
           STATUS mandatory
    DESCRIPTION
    "EOW enable\disable."
        DEFVAL { enable }
    ::= { gnEowCfgEntry 2 }

gnEowCfgEowRightEnable OBJECT-TYPE
        SYNTAX  INTEGER
        {
                enable(2),
                disable(3)
        }
    ACCESS  read-write
           STATUS mandatory
    DESCRIPTION
    "EOW enable\disable."
        DEFVAL { enable }
    ::= { gnEowCfgEntry 3 }

gnEowCfgEowCascadeEnable OBJECT-TYPE
        SYNTAX  INTEGER
        {
                enable(2),
                disable(3)
        }
    ACCESS  read-write
           STATUS mandatory
    DESCRIPTION
    "EOW cascade enable\disable."
        DEFVAL { disable }
    ::= { gnEowCfgEntry 4 }

gnEowStatTable OBJECT-TYPE
        SYNTAX  SEQUENCE OF GnEowStatEntry
        ACCESS  not-accessible
        STATUS mandatory
        DESCRIPTION
        "This table defines the status of the EOW."
        ::= { gnEow 2 }

gnEowStatEntry OBJECT-TYPE
        SYNTAX GnEowStatEntry
        ACCESS  not-accessible
        STATUS mandatory
        DESCRIPTION
        "This is an entry in the EOW status Table."
        INDEX {gnEowStatId}
        ::= { gnEowStatTable 1 }

GnEowStatEntry ::=
            SEQUENCE {
        gnEowStatId
                        INTEGER,
        gnEowStatEowLeftSupport
                        INTEGER,
        gnEowStatEowRightSupport
                        INTEGER
        }

gnEowStatId OBJECT-TYPE
        SYNTAX  INTEGER
        {
                local(1)
        }
    ACCESS  read-only
           STATUS mandatory
    DESCRIPTION
    " "
    ::= { gnEowStatEntry 1 }

gnEowStatEowLeftSupport OBJECT-TYPE
        SYNTAX  INTEGER {
                supported(2),
                notSupported(3)
        }
        ACCESS  read-only
        STATUS mandatory
        DESCRIPTION
    "Indication for EOW support."
        DEFVAL { supported }
        ::= {gnEowStatEntry 2}

gnEowStatEowRightSupport OBJECT-TYPE
        SYNTAX  INTEGER {
                supported(2),
                notSupported(3)
        }
        ACCESS  read-only
        STATUS mandatory
        DESCRIPTION
    "Indication for EOW support."
        DEFVAL { supported }
        ::= {gnEowStatEntry 3}

gnUc OBJECT IDENTIFIER ::=  { gnAux 4 }

gnUcCfgTable OBJECT-TYPE
        SYNTAX  SEQUENCE OF GnUcCfgEntry
        ACCESS  not-accessible
        STATUS mandatory
        DESCRIPTION
        "This table defines the configuration of the User channel."
        ::= { gnUc 1 }

gnUcCfgEntry OBJECT-TYPE
        SYNTAX GnUcCfgEntry
        ACCESS  not-accessible
        STATUS mandatory
        DESCRIPTION
        "This is an entry in the User channel part of the AUX Configuration Table."
        INDEX {gnUcCfgId, gnUcCfgChNumber}
        ::= { gnUcCfgTable 1 }

GnUcCfgEntry ::=
            SEQUENCE {
        gnUcCfgId
                        INTEGER,
        gnUcCfgChNumber
                        INTEGER,
        gnUcCfgRouting
                        INTEGER,
        gnUcCfgEnable
                        INTEGER,
        gnUcCfgType
                        INTEGER,
        gnUcCfgLoopback
                        INTEGER
        }

gnUcCfgId OBJECT-TYPE
        SYNTAX  INTEGER
        {
                local(1)
        }
    ACCESS  read-only
           STATUS mandatory
    DESCRIPTION
    " "
    ::= { gnUcCfgEntry 1 }

gnUcCfgChNumber OBJECT-TYPE
        SYNTAX  INTEGER
        {
                channel1(1),
                channel2(2)
        }
    ACCESS  read-only
           STATUS mandatory
    DESCRIPTION
    "User channel number."
    ::= { gnUcCfgEntry 2 }

gnUcCfgRouting OBJECT-TYPE
        SYNTAX  INTEGER
        {
                drawer1(2),
                drawer2(3)
        }
    ACCESS  read-write
           STATUS mandatory
    DESCRIPTION
    "User channel routing."
        DEFVAL { drawer1 }
    ::= { gnUcCfgEntry 3 }

gnUcCfgEnable OBJECT-TYPE
        SYNTAX  INTEGER
        {
                enable(2),
                disable(3)
        }
    ACCESS  read-write
           STATUS mandatory
    DESCRIPTION
    "User channel enable\disable."
        DEFVAL { disable }
    ::= { gnUcCfgEntry 4 }

gnUcCfgType OBJECT-TYPE
        SYNTAX  INTEGER
        {
                v11Asyn(2),
                rs232(3),
                v11SynCoDirectional(4),
                v11SynContraDirectional(5),
				ethernet(6)
        }
    ACCESS  read-write
           STATUS mandatory
    DESCRIPTION
    "User channel protocol type."
        DEFVAL { v11Asyn }
    ::= { gnUcCfgEntry 5 }

gnUcCfgLoopback OBJECT-TYPE
        SYNTAX  INTEGER
        {
                none(2),
                line(3)
        }
    ACCESS  read-write
           STATUS mandatory
    DESCRIPTION
    "User channel loopback activation."
        DEFVAL { none }
    ::= { gnUcCfgEntry 6 }

gnUcStatTable OBJECT-TYPE
        SYNTAX  SEQUENCE OF GnUcStatEntry
        ACCESS  not-accessible
        STATUS mandatory
        DESCRIPTION
        "This table defines the status of the user channel."
        ::= { gnUc 2 }

gnUcStatEntry OBJECT-TYPE
        SYNTAX GnUcStatEntry
        ACCESS  not-accessible
        STATUS mandatory
        DESCRIPTION
        "This is an entry in the user channel status Table."
        INDEX {gnUcStatId}
        ::= { gnUcStatTable 1 }

GnUcStatEntry ::=
            SEQUENCE {
        gnUcStatId
                        INTEGER,
        gnUcStatLeftMaxRouteChannel
                        INTEGER,
        gnUcStatRightMaxRouteChannel
                        INTEGER
        }

gnUcStatId OBJECT-TYPE
        SYNTAX  INTEGER
        {
                local(1)
        }
    ACCESS  read-only
           STATUS mandatory
    DESCRIPTION
    " "
    ::= { gnUcStatEntry 1 }

gnUcStatLeftMaxRouteChannel OBJECT-TYPE
        SYNTAX  INTEGER (0..15)
        ACCESS  read-only
        STATUS mandatory
        DESCRIPTION
    "Indication for NMS on the number of
     channels the right radio can passthrough."
        DEFVAL { 2 }
        ::= {gnUcStatEntry 2}

gnUcStatRightMaxRouteChannel OBJECT-TYPE
        SYNTAX  INTEGER (0..15)
        ACCESS  read-only
        STATUS mandatory
        DESCRIPTION
    "Indication for NMS on the number of
     channels the right radio can passthrough."
        DEFVAL { 2 }
        ::= {gnUcStatEntry 3}


-- /////  Protect start  ////////

gnProtect OBJECT IDENTIFIER ::=  { gnUnits 3 }

gnProtectCfgTable  OBJECT-TYPE
        SYNTAX  SEQUENCE OF GnProtectCfgEntry
        ACCESS  not-accessible
        STATUS mandatory
        DESCRIPTION
        "This table contains protection switch configuration
          per device; local and remote."
        ::= { gnProtect 1 }

gnProtectCfgEntry OBJECT-TYPE
        SYNTAX GnProtectCfgEntry
        ACCESS  not-accessible
        STATUS mandatory
        INDEX { gnProtectCfgId }
        ::= { gnProtectCfgTable 1 }

        GnProtectCfgEntry ::=
    SEQUENCE {
        gnProtectCfgId
                  INTEGER,
        gnProtectCfgSwitchRequest
                          INTEGER,
        gnProtectCfgBERSwitch
                          INTEGER,
        gnProtectCfgExtInSwitch
                          INTEGER,
        gnProtectCfgOption
                        OCTET STRING,
        gnProtectCfgUserCommand
                          INTEGER,
        gnProtectCfgType
                        INTEGER,
        gnProtectCfgProtectionLockout
                        INTEGER,
        gnProtectCfgSdBERSwitch
                          INTEGER
        }

gnProtectCfgId OBJECT-TYPE
        SYNTAX  INTEGER
        {
                local(1),
                remote(2)
        }
    ACCESS  read-only
           STATUS mandatory
    DESCRIPTION
    " This value indicates which device is involved
        in the specific row."
        ::= { gnProtectCfgEntry 1 }


gnProtectCfgSwitchRequest OBJECT-TYPE
        SYNTAX  INTEGER {
                noAction(2),
                userSwitchRequest(3),
                userForceSwitch(4)
        }
        ACCESS  read-write
        STATUS mandatory
        DESCRIPTION
        " Protection user switch request. "
        DEFVAL { noAction }
        ::= { gnProtectCfgEntry 2 }

gnProtectCfgBERSwitch OBJECT-TYPE
        SYNTAX  INTEGER {
                enable(2),
        disable(3)
        }
        ACCESS  read-write
        STATUS mandatory
        DESCRIPTION
        " Enable or disable automatic switch as a result of BER condition. "
        DEFVAL { enable }
        ::= { gnProtectCfgEntry 3 }

gnProtectCfgExtInSwitch OBJECT-TYPE
        SYNTAX  INTEGER {
                enable(2),
        disable(3)
        }
        ACCESS  read-write
        STATUS mandatory
        DESCRIPTION
        " Enable or disable automatic switch as a result of alarm
          on External Input No. 8. "
        DEFVAL { enable }
        ::= { gnProtectCfgEntry 4 }


gnProtectCfgOption OBJECT-TYPE
        SYNTAX  OCTET STRING (SIZE(1))
        ACCESS  read-write
        STATUS mandatory
        DESCRIPTION
         " bit 8 (lsb) = dual fiber input.
           bit 7           = protection disable
           bit 4 = 0 (default) for External protection ; 1 for Internal protection (between the drawers)
           bit 3 = 0 (default) for Full protection ; 1 for Radio protection. "
        ::= { gnProtectCfgEntry 5 }

gnProtectCfgUserCommand OBJECT-TYPE
        SYNTAX  INTEGER {
                noAction(2),
                copyConfToMate(3),
                copyLeftConfToRight(4), -- No Drawer number use right and left
        copyRightConfToLeft(5)
        }
        ACCESS  read-write
        STATUS mandatory
        DESCRIPTION
        " Copy All the configuration that should be equal in master and slave.
          The copy is made from the current unit to it's mate/Left drawer to right drawer or right drawer to left drawer."
        DEFVAL { noAction }
        ::= { gnProtectCfgEntry 6 }


gnProtectCfgType OBJECT-TYPE
        SYNTAX  INTEGER {
                none(2),
                internal(3),
                external(4),
                externalInternal(5)
        }
        ACCESS  read-write
        STATUS mandatory
        DESCRIPTION
        " ."
        DEFVAL { none }
        ::= { gnProtectCfgEntry 7 }


gnProtectCfgProtectionLockout OBJECT-TYPE
        SYNTAX  INTEGER {
                on(2),
                off(3)
        }
        ACCESS  read-write
        STATUS mandatory
        DESCRIPTION
        " ."
        DEFVAL { off }
        ::= { gnProtectCfgEntry 8 }

gnProtectCfgSdBERSwitch OBJECT-TYPE
        SYNTAX  INTEGER {
                enable(2),
        disable(3)
        }
        ACCESS  read-write
        STATUS mandatory
        DESCRIPTION
        " Enable or disable automatic switch as a result of signal degrade BER condition. "
        DEFVAL { enable }
        ::= { gnProtectCfgEntry 9 }

gnProtectUnitMode OBJECT-TYPE
        SYNTAX  INTEGER {
                slave(2),
                master(3)
        }
        ACCESS  read-only
        STATUS mandatory
        DESCRIPTION
        " This parameter indicates the unit mode: Master of Slave."
        DEFVAL { slave }
        ::= { gnProtect 2 }


gnHitLessCfgTable  OBJECT-TYPE
        SYNTAX  SEQUENCE OF GnHitLessCfgEntry
        ACCESS  not-accessible
        STATUS mandatory
        DESCRIPTION
        "This table contains hitless configuration
          per device; local and remote."
        ::= { gnProtect 3 }

gnHitLessCfgEntry OBJECT-TYPE
        SYNTAX GnHitLessCfgEntry
        ACCESS  not-accessible
        STATUS mandatory
        INDEX { gnHitLessCfgId }
        ::= { gnHitLessCfgTable 1 }

        GnHitLessCfgEntry ::=
    SEQUENCE {
        gnHitLessCfgId
                        INTEGER,
        gnHitLessCfgSwitchEnable
                  INTEGER,
        gnHitLessCfgDiversityType
                          INTEGER,
        gnHitLessCfgSwitchingMode
                          INTEGER,
        gnHitLessCfgRevertTime
                          INTEGER,
        gnHitLessCfgManualSwitch
                          INTEGER,
        gnHitLessCfgEventCounterCommand
                        INTEGER,
        gnHitLessCfgSwitchLock
                        INTEGER
        }

gnHitLessCfgId OBJECT-TYPE
        SYNTAX  INTEGER
        {
                local(1),
                remote(2),
                drawer1(3),
                drawer2(4)
        }
    ACCESS  read-only
           STATUS mandatory
    DESCRIPTION
    " This value indicates which device is involved
        in the specific row."
        ::= { gnHitLessCfgEntry 1 }

gnHitLessCfgSwitchEnable OBJECT-TYPE
        SYNTAX  INTEGER {
                enable(2),
        disable(3)
        }
        ACCESS  read-write
           STATUS mandatory
    DESCRIPTION
    " Enable or disable the Hitless feature."
        DEFVAL { enable }
        ::= { gnHitLessCfgEntry 2 }

gnHitLessCfgDiversityType OBJECT-TYPE
        SYNTAX  INTEGER {
                space(2),
                frequency(3),
                none(4)
        }
        ACCESS  read-write
           STATUS mandatory
    DESCRIPTION
    " Is the hitless feature working in space diversity mode
        or in frequency diversity mode."
        DEFVAL { space }
        ::= { gnHitLessCfgEntry 3 }

gnHitLessCfgSwitchingMode OBJECT-TYPE
        SYNTAX  INTEGER {
                revertive(2),
        nonRevertive(3)
        }
        ACCESS  read-write
           STATUS mandatory
    DESCRIPTION
    " "
        DEFVAL { revertive }
        ::= { gnHitLessCfgEntry 4 }

gnHitLessCfgRevertTime OBJECT-TYPE
        SYNTAX  INTEGER (0..15)
        ACCESS  read-write
           STATUS mandatory
    DESCRIPTION
    " This parameter indicates the revert time in seconds.
        Possible values: 0..15."
        DEFVAL { 0 }
        ::= { gnHitLessCfgEntry 5 }

gnHitLessCfgManualSwitch OBJECT-TYPE
        SYNTAX  INTEGER {
                noAction(2),
        activate(3)
        }
        ACCESS  read-write
           STATUS mandatory
    DESCRIPTION
    " Force manually switch between the hitless modems."
        DEFVAL { noAction }
        ::= { gnHitLessCfgEntry 6 }

gnHitLessCfgEventCounterCommand OBJECT-TYPE
        SYNTAX  INTEGER {
                noAction(2),
        clearCounter(3)
        }
        ACCESS  read-write
           STATUS mandatory
    DESCRIPTION
    " Clears the gnHitLessStatEventCounter."
        DEFVAL { noAction }
        ::= { gnHitLessCfgEntry 7 }

 gnHitLessCfgSwitchLock OBJECT-TYPE
        SYNTAX  INTEGER {
                off(2),
                left(3),
                right(4),
                self(5),
                mate(6)
        }
        ACCESS  read-write
           STATUS mandatory
    DESCRIPTION
    " ."
        DEFVAL { off }
        ::= { gnHitLessCfgEntry 8 }




gnHitLessStatTable  OBJECT-TYPE
        SYNTAX  SEQUENCE OF GnHitLessStatEntry
        ACCESS  not-accessible
        STATUS mandatory
        DESCRIPTION
        "This table contains hitless status
          per device; local and remote."
        ::= { gnProtect 4 }

gnHitLessStatEntry OBJECT-TYPE
        SYNTAX GnHitLessStatEntry
        ACCESS  not-accessible
        STATUS mandatory
        INDEX { gnHitLessStatId }
        ::= { gnHitLessStatTable 1 }

        GnHitLessStatEntry ::=
    SEQUENCE {
        gnHitLessStatId
                        INTEGER,
        gnHitLessStatReceiverStatus
                  INTEGER,
        gnHitLessStatModeStatus
                          INTEGER,
        gnHitLessStatEventCounter
                          INTEGER,
        gnHitLessStatAlarmStatus
                        OCTET STRING
        }

gnHitLessStatId OBJECT-TYPE
        SYNTAX  INTEGER
        {
                local(1),
                remote(2),
                drawer1(3),
                drawer2(4)
        }
    ACCESS  read-only
           STATUS mandatory
    DESCRIPTION
    " This value indicates which device is involved
        in the specific row."
        ::= { gnHitLessStatEntry 1 }

gnHitLessStatReceiverStatus OBJECT-TYPE
        SYNTAX  INTEGER {
                local(2),
                mate(3),
                leftRadio(4),
                rightRadio(5)
        }
        ACCESS  read-only
           STATUS mandatory
    DESCRIPTION
    " This parameter indicates which Modem is active:
        the Local or the mate."
        DEFVAL { local }
        ::= { gnHitLessStatEntry 2 }

gnHitLessStatModeStatus OBJECT-TYPE
        SYNTAX  INTEGER {
                hitlessOK(2),
        hitlessFailure(3)
        }
        ACCESS  read-only
           STATUS mandatory
    DESCRIPTION
    " This parameter indicates if the Hitless system
        is working properly."
        DEFVAL { hitlessFailure }
        ::= { gnHitLessStatEntry 3 }

gnHitLessStatEventCounter OBJECT-TYPE
        SYNTAX  INTEGER (0..65535)
        ACCESS  read-only
           STATUS mandatory
    DESCRIPTION
    " This counter counts the number of hitless switch events."
        DEFVAL { 0 }
        ::= { gnHitLessStatEntry 4 }

gnHitLessStatAlarmStatus OBJECT-TYPE
        SYNTAX  OCTET STRING (SIZE(2))
        ACCESS  read-only
           STATUS mandatory
    DESCRIPTION
    " bit 1 represent the MSB
        bits 1-7 are not in use
                bit 8 : Switch lock to right.
                bit 9 : Switch lock to left.
        bit 10: Protection config mismatch.
        bit 11: Diversity config mismatch.
        bit 12: Unused radio LOF.
        bit 13: Hitless Functionality Failure.
                bit 14:        Hitless Cable Disconnect.
        bit 15: Hitless Mate LOF.
        bit 16: Hitless Primary Radio LOF. "
        ::= { gnHitLessStatEntry 5 }


gnTribStmProtectCfg OBJECT IDENTIFIER ::= { gnProtect 5}

gnTribStmProtectType OBJECT-TYPE
        SYNTAX  INTEGER {
                none(2),
                msp(3),
                sncp(4)
        }
        ACCESS  read-write
        STATUS mandatory
        DESCRIPTION
        "."
        DEFVAL { none }
        ::= { gnTribStmProtectCfg 1 }

gnTribStmMspConnect OBJECT-TYPE
        SYNTAX  INTEGER {
                dualTribConnect(2),
                singleTribConnect(3)
        }
        ACCESS  read-write
        STATUS mandatory
        DESCRIPTION
        "."
        DEFVAL { dualTribConnect }
        ::= { gnTribStmProtectCfg 2 }

gnTribStmMspType OBJECT-TYPE
        SYNTAX  INTEGER {
                uniDirectional(2),
                biDirectional(3)
        }
        ACCESS  read-write
        STATUS mandatory
        DESCRIPTION
        "."
        DEFVAL { uniDirectional }
        ::= { gnTribStmProtectCfg 3 }

gnTribStmMspRevertiveMode OBJECT-TYPE
        SYNTAX  INTEGER {
                nonRevertive(2),
                revertive(3)
        }
        ACCESS  read-write
        STATUS mandatory
        DESCRIPTION
        "."
        DEFVAL { nonRevertive }
        ::= { gnTribStmProtectCfg 4 }

gnTribStmMspProtectRole OBJECT-TYPE
        SYNTAX  INTEGER {
                main(2),
                standBy(3)
        }
        ACCESS  read-write
        STATUS mandatory
        DESCRIPTION
        "."
        ::= { gnTribStmProtectCfg 5 }

gnTribStmMspWaitToRestoreTime OBJECT-TYPE
        SYNTAX  INTEGER (5..12)
        ACCESS  read-write
        STATUS mandatory
        DESCRIPTION
          "This is the wait-to-restore time in minutes.
         Possible values: 5..12. "
        DEFVAL {5}
        ::= { gnTribStmProtectCfg 6 }

gnTribStmMspUserCommand OBJECT-TYPE
        SYNTAX  INTEGER {
                                clear(2),
                lockOut(3),
                forceSwitch(4),
                manualSwitch(5),
                                exercise(6)
        }
        ACCESS  read-write
        STATUS mandatory
        DESCRIPTION
        "."
        DEFVAL { clear }
        ::= { gnTribStmProtectCfg 7 }



gnTribStmProtectStat OBJECT IDENTIFIER ::= { gnProtect 6}

gnTribStmProtectCurrentState OBJECT-TYPE
        SYNTAX  INTEGER {
                working(2),
                protecting(3)
        }
        ACCESS  read-only
        STATUS mandatory
        DESCRIPTION
        "."
        ::= { gnTribStmProtectStat 1 }

gnTribStmProtectCableStatus OBJECT-TYPE
        SYNTAX  INTEGER {
                ok(2),
                fault(3)
        }
        ACCESS  read-only
        STATUS mandatory
        DESCRIPTION
        "."
        ::= { gnTribStmProtectStat 2 }

gnProtectXTable  OBJECT-TYPE
        SYNTAX  SEQUENCE OF GnProtectXEntry
        ACCESS  not-accessible
        STATUS mandatory
        DESCRIPTION
        ""
        ::= { gnProtect 7 }

gnProtectXEntry OBJECT-TYPE
        SYNTAX GnProtectXEntry
        ACCESS  not-accessible
        STATUS mandatory
        INDEX { gnProtectXId }
        ::= { gnProtectXTable 1 }

        GnProtectXEntry ::=
    SEQUENCE {
        gnProtectXId
                        INTEGER,
        gnProtectXProtectUnitMode
                  INTEGER
        }

gnProtectXId OBJECT-TYPE
        SYNTAX  INTEGER
        {
                drawer1(3),
                drawer2(4)
        }
    ACCESS  read-only
           STATUS mandatory
    DESCRIPTION
    " "
        ::= { gnProtectXEntry 1 }

gnProtectXProtectUnitMode OBJECT-TYPE
        SYNTAX  INTEGER {
                slave(2),
                master(3)
        }
        ACCESS  read-only
        STATUS mandatory
        DESCRIPTION
        " This parameter indicates the unit mode: Master of Slave."
        DEFVAL { slave }
        ::= { gnProtectXEntry 2 }

gnLinkGroups OBJECT IDENTIFIER ::= { gnProtect 8 }

topologiesOptionsTable  OBJECT-TYPE
        SYNTAX  SEQUENCE OF TopologiesOptionsEntry
        ACCESS  not-accessible
        STATUS mandatory
        DESCRIPTION
        "This table indicates the Topologies options."
        ::= { gnLinkGroups 1 }

topologiesOptionsEntry OBJECT-TYPE
        SYNTAX TopologiesOptionsEntry
        ACCESS  not-accessible
        STATUS mandatory
          DESCRIPTION
          "Entry containing the Topologies options."
        INDEX { topologiesOptionsGroupTopology}
        ::= { topologiesOptionsTable 1 }

TopologiesOptionsEntry ::=
            SEQUENCE {
        topologiesOptionsGroupTopology
             INTEGER (1),
        topologiesOptionsMembersCarriers
             INTEGER (1),
        topologiesOptionsProtectingCarriers
             INTEGER (1),
    topologiesOptionsName
                    DisplayString (SIZE(0..20))
    }

topologiesOptionsGroupTopology OBJECT-TYPE
        SYNTAX  INTEGER (1)
        ACCESS  read-only
           STATUS mandatory
        DESCRIPTION
              "This value indicates a bitmap :
                           ----------------------------------------
                           | 15..12 | 11...........8 | 7........0 |
                           | Set Id | Group Topology | Group Size |
                            ---------------------------------------"
        ::= { topologiesOptionsEntry 1 }

topologiesOptionsMembersCarriers OBJECT-TYPE
        SYNTAX  INTEGER (1)
        ACCESS  read-only
           STATUS mandatory
        DESCRIPTION
              "This value indicates a bitmap, LSB = carrier #1, #2..... "
        ::= { topologiesOptionsEntry 2 }

topologiesOptionsProtectingCarriers OBJECT-TYPE
        SYNTAX  INTEGER (1)
        ACCESS  read-only
           STATUS mandatory
        DESCRIPTION
              "This value indicates a bitmap, LSB = carrier #1, #2..... "
        ::= { topologiesOptionsEntry 3 }

topologiesOptionsName OBJECT-TYPE
        SYNTAX  DisplayString (SIZE(0..20))
        ACCESS  read-only
           STATUS mandatory
        DESCRIPTION
              "This value indicates the name of the topology, HSB 1:1, Stand Alone, 2+1.... "
        ::= { topologiesOptionsEntry 4 }

linkGroupingTable  OBJECT-TYPE
        SYNTAX  SEQUENCE OF LinkGroupingEntry
        ACCESS  not-accessible
        STATUS mandatory
        DESCRIPTION
        "This table indicates the link grouping."
        ::= { gnLinkGroups 2 }

linkGroupingEntry OBJECT-TYPE
        SYNTAX LinkGroupingEntry
        ACCESS  not-accessible
        STATUS mandatory
          DESCRIPTION
          "Entry containing the link grouping."
        INDEX { linkGroupingGroupId}
        ::= { linkGroupingTable 1 }

LinkGroupingEntry ::=
            SEQUENCE {
        linkGroupingGroupId
             INTEGER (1..4),
        linkGroupingGroupAdmin
             INTEGER,
        linkGroupingGroupTopology
             INTEGER,
        linkGroupingExtraTrafficAdmin
             INTEGER,
    linkGroupingGroupName
                    DisplayString (SIZE(0..40))
    }

linkGroupingGroupId OBJECT-TYPE
        SYNTAX  INTEGER (1..4)
        ACCESS  read-write
           STATUS mandatory
        DESCRIPTION
              "This value indicates the group id "
        ::= { linkGroupingEntry 1 }

linkGroupingGroupAdmin OBJECT-TYPE
    SYNTAX  INTEGER
    {
                enable(2),
                disable(3)
    }
        ACCESS  read-write
           STATUS mandatory
        DESCRIPTION
              "This value indicates the groups admin "
        ::= { linkGroupingEntry 2 }

linkGroupingGroupTopology OBJECT-TYPE
        SYNTAX  INTEGER
        {
                topologyhsb1-1(1),
                topologyhsb2-2(2),
                topologystandalone(256),
                topology1plus1(513),
                topology2plus1(514),
                topology3plus1(515),
                topology4plus1(516),
                topology5plus1(517),
                topology6plus1(518),
                topology7plus1(519),
                topology8plus1(520),
                topology9plus1(521)
    }
        ACCESS  read-write
           STATUS mandatory
        DESCRIPTION
              "This value indicates a bitmap :
                           ----------------------------------------
                           | 15..12 | 11...........8 | 7........0 |
                           | Set Id | Group Topology | Group Size |
                            ---------------------------------------"
        ::= { linkGroupingEntry 3 }

linkGroupingExtraTrafficAdmin OBJECT-TYPE
    SYNTAX  INTEGER
    {
                enable(2),
                disable(3)
    }
        ACCESS  read-write
           STATUS mandatory
        DESCRIPTION
              "This value indicates the ET admin "
        ::= { linkGroupingEntry 4 }

linkGroupingGroupName OBJECT-TYPE
        SYNTAX  DisplayString (SIZE(0..40))
        ACCESS  read-write
           STATUS mandatory
        DESCRIPTION
              "This value indicates the groups name. "
        ::= { linkGroupingEntry 5 }

protectionTable  OBJECT-TYPE
        SYNTAX  SEQUENCE OF ProtectionEntry
        ACCESS  not-accessible
        STATUS mandatory
        DESCRIPTION
        "This table indicates the link grouping protection."
        ::= { gnLinkGroups 3 }

protectionEntry OBJECT-TYPE
        SYNTAX ProtectionEntry
        ACCESS  not-accessible
        STATUS mandatory
          DESCRIPTION
          "Entry containing the link grouping protection."
        INDEX { protectionGroupId}
        ::= { protectionTable 1 }

ProtectionEntry ::=
            SEQUENCE {
        protectionGroupId
             INTEGER (1..4),
        protectionGroupsProtectionAdmin
             INTEGER,
        protectionNplus1ProtectionMethod
             INTEGER,
        protectionProtectingCarrierId
             INTEGER (0..15)
    }

protectionGroupId OBJECT-TYPE
        SYNTAX  INTEGER (1..4)
        ACCESS  read-only
           STATUS mandatory
        DESCRIPTION
              "This value indicates the group id. "
        ::= { protectionEntry 1 }

protectionGroupsProtectionAdmin OBJECT-TYPE
    SYNTAX  INTEGER
    {
                enable(2),
                disable(3)
    }
        ACCESS  read-write
           STATUS mandatory
        DESCRIPTION
              "This value indicates the groups protection admin. "
        ::= { protectionEntry 2 }

protectionNplus1ProtectionMethod OBJECT-TYPE
    SYNTAX  INTEGER
    {
                standard(2),
                advanced(3)
    }
        ACCESS  read-write
           STATUS mandatory
        DESCRIPTION
              "This value indicates the N+1 protection method. "
        ::= { protectionEntry 3 }

protectionProtectingCarrierId OBJECT-TYPE
        SYNTAX  INTEGER (0..15)
        ACCESS  read-only
           STATUS mandatory
        DESCRIPTION
              "This value indicates the carrier id. "
        ::= { protectionEntry 4 }

standardProtectionTable  OBJECT-TYPE
        SYNTAX  SEQUENCE OF StandardProtectionEntry
        ACCESS  not-accessible
        STATUS mandatory
        DESCRIPTION
        "This table indicates the link grouping standard protection."
        ::= { gnLinkGroups 4 }

standardProtectionEntry OBJECT-TYPE
        SYNTAX StandardProtectionEntry
        ACCESS  not-accessible
        STATUS mandatory
          DESCRIPTION
          "Entry containing the link grouping standard protection."
        INDEX { standardProtectionGroupId}
        ::= { standardProtectionTable 1 }

StandardProtectionEntry ::=
            SEQUENCE {
        standardProtectionGroupId
             INTEGER (1..4),
        standardProtectionSwitchOnEarlyWarning
             INTEGER,
        standardProtectionHighPrioProtectionTh
             INTEGER,
        standardProtectionRevertiveLink
             INTEGER,
        standardProtectionRevertiveSwitchTimeOut
             INTEGER (1..15)
    }

standardProtectionGroupId OBJECT-TYPE
        SYNTAX  INTEGER (1..4)
        ACCESS  read-only
           STATUS mandatory
        DESCRIPTION
              "This value indicates the group id. "
        ::= { standardProtectionEntry 1 }

standardProtectionSwitchOnEarlyWarning OBJECT-TYPE
    SYNTAX  INTEGER
    {
                enable(2),
                disable(3)
    }
        ACCESS  read-write
           STATUS mandatory
        DESCRIPTION
              "This value indicates switch on early warning. "
        ::= { standardProtectionEntry 2 }

standardProtectionHighPrioProtectionTh OBJECT-TYPE
    SYNTAX  INTEGER
    {
                bblof(4),
                bbexb(5),
                bbsd(6),
                ew(7)
    }
        ACCESS  read-write
           STATUS mandatory
        DESCRIPTION
              "This value indicates the high priority protection. "
        ::= { standardProtectionEntry 3 }

standardProtectionRevertiveLink OBJECT-TYPE
    SYNTAX  INTEGER
    {
                carrier1(1),
                carrier2(2),
                carrier3(3),
                carrier4(4),
                carrier5(5),
                carrier6(6),
                carrier7(7),
                carrier8(8),
                carrier9(9),
                carrier10(10),
                carrier11(11),
                carrier12(12),
                carrier13(13),
                carrier14(14),
                carrier15(15),
                extraTraffic(256),
                none(257)
    }
        ACCESS  read-write
           STATUS mandatory
        DESCRIPTION
              "This value indicates the revertive link. "
        ::= { standardProtectionEntry 4 }

standardProtectionRevertiveSwitchTimeOut OBJECT-TYPE
        SYNTAX  INTEGER (1..15)
        ACCESS  read-write
           STATUS mandatory
        DESCRIPTION
              "This value indicates the revertive switch time out. "
        ::= { standardProtectionEntry 5 }

membersTable  OBJECT-TYPE
        SYNTAX  SEQUENCE OF MembersEntry
        ACCESS  not-accessible
        STATUS mandatory
        DESCRIPTION
        "This table indicates the link groups members."
        ::= { gnLinkGroups 5 }

membersEntry OBJECT-TYPE
        SYNTAX MembersEntry
        ACCESS  not-accessible
        STATUS mandatory
          DESCRIPTION
          "Entry containing the link groups members."
        INDEX { membersGroupId, membersCarrierId}
        ::= { membersTable 1 }

MembersEntry ::=
            SEQUENCE {
        membersGroupId
             INTEGER (1..4),
        membersCarrierId
             INTEGER (1..15),
        membersProtectionPriorityLevel
             INTEGER
    }

membersGroupId OBJECT-TYPE
        SYNTAX  INTEGER (1..4)
        ACCESS  read-only
           STATUS mandatory
        DESCRIPTION
              "This value indicates the group id. "
        ::= { membersEntry 1 }

membersCarrierId OBJECT-TYPE
        SYNTAX  INTEGER (1..15)
        ACCESS  read-only
           STATUS mandatory
        DESCRIPTION
              "This value indicates the carrier id. "
        ::= { membersEntry 2 }

membersProtectionPriorityLevel OBJECT-TYPE
    SYNTAX  INTEGER
    {
                void(2),
                normal(3),
                high(4)
    }
        ACCESS  read-write
           STATUS mandatory
        DESCRIPTION
              "This value indicates the protection priority level. "
        ::= { membersEntry 3 }

nplus1ProtectingTable  OBJECT-TYPE
        SYNTAX  SEQUENCE OF Nplus1ProtectingEntry
        ACCESS  not-accessible
        STATUS mandatory
        DESCRIPTION
        "This table indicates the link group N+1 protecting."
        ::= { gnLinkGroups 6 }

nplus1ProtectingEntry OBJECT-TYPE
        SYNTAX Nplus1ProtectingEntry
        ACCESS  not-accessible
        STATUS mandatory
          DESCRIPTION
          "Entry containing the link group N+1 protecting."
        INDEX { nplus1ProtectingGroupId}
        ::= { nplus1ProtectingTable 1 }

Nplus1ProtectingEntry ::=
            SEQUENCE {
        nplus1ProtectingGroupId
             INTEGER (1..4),
        nplus1ProtectingXCProtectionFraming
             INTEGER,
        nplus1ProtectingProtectedLinkTx
             INTEGER (0..15),
        nplus1ProtectingProtectedLinkRx
             INTEGER (0..15),
        nplus1ProtectingRequestedLinkTx
             INTEGER (0..15),
        nplus1ProtectingRequestedLinkRx
             INTEGER (0..15),
        nplus1ProtectingSwitchToProtectingCommand
             INTEGER
    }

nplus1ProtectingGroupId OBJECT-TYPE
        SYNTAX  INTEGER (1..4)
        ACCESS  read-only
           STATUS mandatory
        DESCRIPTION
              "This value indicates the group id. "
        ::= { nplus1ProtectingEntry 1 }

nplus1ProtectingXCProtectionFraming OBJECT-TYPE
    SYNTAX  INTEGER
    {
                na(2),
                lof(3),
                noPeer(4),
                clear(5)
    }
        ACCESS  read-only
           STATUS mandatory
        DESCRIPTION
              "This value indicates the XC protecting framing. "
        ::= { nplus1ProtectingEntry 2 }

nplus1ProtectingProtectedLinkTx OBJECT-TYPE
        SYNTAX  INTEGER (0..15)
        ACCESS  read-only
           STATUS mandatory
        DESCRIPTION
              "This value indicates the last known carrier num. 0 means no carrier."
        ::= { nplus1ProtectingEntry 3 }

nplus1ProtectingProtectedLinkRx OBJECT-TYPE
        SYNTAX  INTEGER (0..15)
        ACCESS  read-only
           STATUS mandatory
        DESCRIPTION
              "This value indicates the last known carrier num. 0 means no carrier."
        ::= { nplus1ProtectingEntry 4 }

nplus1ProtectingRequestedLinkTx OBJECT-TYPE
        SYNTAX  INTEGER (0..15)
        ACCESS  read-only
           STATUS mandatory
        DESCRIPTION
              "This value indicates the last known carrier num. 0 means no carrier."
        ::= { nplus1ProtectingEntry 5 }

nplus1ProtectingRequestedLinkRx OBJECT-TYPE
        SYNTAX  INTEGER (0..15)
        ACCESS  read-only
           STATUS mandatory
        DESCRIPTION
              "This value indicates the last known carrier num. 0 means no carrier."
        ::= { nplus1ProtectingEntry 6 }

nplus1ProtectingSwitchToProtectingCommand OBJECT-TYPE
    SYNTAX  INTEGER
    {
                noaction(256),
                lockout(512),
                force1(769),
                force2(770),
                force3(771),
                force4(772),
                force5(773),
                force6(774),
                force7(775),
                force8(776),
                force9(777),
                force10(778),
                force11(779),
                force12(780),
                force13(781),
                force14(782),
                force15(783),
                request1(1025),
                request2(1026),
                request3(1027),
                request4(1028),
                request5(1029),
                request6(1030),
                request7(1031),
                request8(1032),
                request9(1033),
                request10(1034),
                request11(1035),
                request12(1036),
                request13(1037),
                request14(1038),
                request15(1039)
    }
        ACCESS  read-write
           STATUS mandatory
        DESCRIPTION
              "This value indicates the switch to protecting command.
               The force switch command is Bi-directional."
        ::= { nplus1ProtectingEntry 7 }

carrierProtectionTable  OBJECT-TYPE
        SYNTAX  SEQUENCE OF CarrierProtectionEntry
        ACCESS  not-accessible
        STATUS mandatory
        DESCRIPTION
        "This table indicates the carrier protection."
        ::= { gnLinkGroups 7 }

carrierProtectionEntry OBJECT-TYPE
        SYNTAX CarrierProtectionEntry
        ACCESS  not-accessible
        STATUS mandatory
          DESCRIPTION
          "Entry containing the carrier protection."
        INDEX { carrierProtectionXCId, carrierProtectionCarrierId}
        ::= { carrierProtectionTable 1 }

CarrierProtectionEntry ::=
            SEQUENCE {
        carrierProtectionXCId
             INTEGER (1..6),
        carrierProtectionCarrierId
             INTEGER (1..15),
        carrierProtectionLinkGroupNum
             INTEGER,
        carrierProtectionServedByRemoteXC
             INTEGER,
        carrierProtectionRadioStatus
             INTEGER,
        carrierProtectionLineFraming
             INTEGER,
        carrierProtectionLoopback
             INTEGER,
        carrierProtectionLoopbackTimer
             INTEGER (0..1440)
    }

carrierProtectionXCId OBJECT-TYPE
        SYNTAX  INTEGER (1..6)
        ACCESS  read-only
           STATUS mandatory
        DESCRIPTION
              "This value indicates the XC id. "
        ::= { carrierProtectionEntry 1 }

carrierProtectionCarrierId OBJECT-TYPE
        SYNTAX  INTEGER (1..15)
        ACCESS  read-only
           STATUS mandatory
        DESCRIPTION
              "This value indicates the carrier id. "
        ::= { carrierProtectionEntry 2 }

carrierProtectionLinkGroupNum OBJECT-TYPE
    SYNTAX  INTEGER
    {
                standalone(2),
                group1(3),
                group2(4),
                group3(5),
                group4(6)
    }
        ACCESS  read-only
           STATUS mandatory
        DESCRIPTION
              "This value indicates the link group number. "
        ::= { carrierProtectionEntry 3 }

carrierProtectionServedByRemoteXC OBJECT-TYPE
    SYNTAX  INTEGER
    {
                na(2),
                yes(3),
                no(4)
    }
        ACCESS  read-only
           STATUS mandatory
        DESCRIPTION
              "This value indicates whether served by remote XC. "
        ::= { carrierProtectionEntry 4 }

carrierProtectionRadioStatus OBJECT-TYPE
    SYNTAX  INTEGER
    {
                na(2),
                off(3),
                bblof(4),
                bbexb(5),
                bbsd(6),
                ew(7),
                clear(8)
    }
        ACCESS  read-only
           STATUS mandatory
        DESCRIPTION
              "This value indicates the radio status. "
        ::= { carrierProtectionEntry 5 }

carrierProtectionLineFraming OBJECT-TYPE
    SYNTAX  INTEGER
    {
                na(2),
                lof(3),
                clear(4)
    }
        ACCESS  read-only
           STATUS mandatory
        DESCRIPTION
              "This value indicates the line framing. "
        ::= { carrierProtectionEntry 6 }

carrierProtectionLoopback OBJECT-TYPE
    SYNTAX  INTEGER
    {
                none(3),
                external(4)
    }
        ACCESS  read-write
           STATUS mandatory
        DESCRIPTION
              "This value indicates the loopback. "
        ::= { carrierProtectionEntry 7 }

carrierProtectionLoopbackTimer OBJECT-TYPE
    SYNTAX  INTEGER (0..1440)
        ACCESS  read-only
           STATUS mandatory
        DESCRIPTION
              "This variable indicates the remaining time (in minutes) till the loopback timer will be expired. "
        ::= { carrierProtectionEntry 8 }

nplus1StandardPMCurrTable  OBJECT-TYPE
        SYNTAX  SEQUENCE OF Nplus1StandardPMCurrEntry
        ACCESS  not-accessible
        STATUS mandatory
        DESCRIPTION
        "This table indicates the standard PM current."
        ::= { gnLinkGroups 8 }

nplus1StandardPMCurrEntry OBJECT-TYPE
        SYNTAX Nplus1StandardPMCurrEntry
        ACCESS  not-accessible
        STATUS mandatory
          DESCRIPTION
          "Entry containing the standard PM current."
        INDEX { nplus1StandardPMCurrCarrierId}
        ::= { nplus1StandardPMCurrTable 1 }

Nplus1StandardPMCurrEntry ::=
            SEQUENCE {
        nplus1StandardPMCurrCarrierId
             INTEGER (1..15),
        nplus1StandardPMCurrTimeElapsed
             INTEGER (1..900),
        nplus1StandardPMCurrValidIntervals
             INTEGER (1..96),
        nplus1StandardPMCurrLastDayIDF
             INTEGER,
        nplus1StandardPMCurrLastDayGroupNum
             INTEGER(-1..4),
        nplus1StandardPMCurrPSAC
             Gauge,
        nplus1StandardPMCurrFSRC
             Gauge,
        nplus1StandardPMCurrPSAD
             Gauge,
        nplus1StandardPMCurrFSRD
             Gauge,
        nplus1StandardPMCurrLastDayPSAC
             Gauge,
        nplus1StandardPMCurrLastDayFSRC
             Gauge,
        nplus1StandardPMCurrLastDayPSAD
             Gauge,
        nplus1StandardPMCurrLastDayFSRD
             Gauge
    }

nplus1StandardPMCurrCarrierId OBJECT-TYPE
        SYNTAX  INTEGER (1..15)
        ACCESS  read-only
           STATUS mandatory
        DESCRIPTION
              "This value indicates the carrier id. "
        ::= { nplus1StandardPMCurrEntry 1 }

nplus1StandardPMCurrTimeElapsed OBJECT-TYPE
        SYNTAX  INTEGER (1..900)
        ACCESS  read-only
           STATUS mandatory
        DESCRIPTION
              "This value indicates the time that elapsed. "
        ::= { nplus1StandardPMCurrEntry 2 }

nplus1StandardPMCurrValidIntervals OBJECT-TYPE
        SYNTAX  INTEGER (1..96)
        ACCESS  read-only
           STATUS mandatory
        DESCRIPTION
              "This value indicates the valid intervals. "
        ::= { nplus1StandardPMCurrEntry 3 }

nplus1StandardPMCurrLastDayIDF OBJECT-TYPE
        SYNTAX  INTEGER
        {
                off(2),
                on(3)
        }
        ACCESS  read-only
           STATUS mandatory
        DESCRIPTION
              "This value indicates the carrier id. "
        ::= { nplus1StandardPMCurrEntry 4 }

nplus1StandardPMCurrLastDayGroupNum OBJECT-TYPE
        SYNTAX  INTEGER (-1..4)
        ACCESS  read-only
           STATUS mandatory
        DESCRIPTION
              "This value indicates the group's number. "
        ::= { nplus1StandardPMCurrEntry 5 }

nplus1StandardPMCurrPSAC OBJECT-TYPE
        SYNTAX  Gauge
        ACCESS  read-only
           STATUS mandatory
        DESCRIPTION
              "This value indicates the PSAC value. "
        ::= { nplus1StandardPMCurrEntry 6 }

nplus1StandardPMCurrFSRC OBJECT-TYPE
        SYNTAX  Gauge
        ACCESS  read-only
           STATUS mandatory
        DESCRIPTION
              "This value indicates the FSRC value. "
        ::= { nplus1StandardPMCurrEntry 7 }

nplus1StandardPMCurrPSAD OBJECT-TYPE
        SYNTAX  Gauge
        ACCESS  read-only
           STATUS mandatory
        DESCRIPTION
              "This value indicates the PSAD value. "
        ::= { nplus1StandardPMCurrEntry 8 }

nplus1StandardPMCurrFSRD OBJECT-TYPE
        SYNTAX  Gauge
        ACCESS  read-only
           STATUS mandatory
        DESCRIPTION
              "This value indicates the FSRD value. "
        ::= { nplus1StandardPMCurrEntry 9 }

nplus1StandardPMCurrLastDayPSAC OBJECT-TYPE
        SYNTAX  Gauge
        ACCESS  read-only
           STATUS mandatory
        DESCRIPTION
              "This value indicates the last Day PSAC value. "
        ::= { nplus1StandardPMCurrEntry 10 }

nplus1StandardPMCurrLastDayFSRC OBJECT-TYPE
        SYNTAX  Gauge
        ACCESS  read-only
           STATUS mandatory
        DESCRIPTION
              "This value indicates the last Day FSRC value. "
        ::= { nplus1StandardPMCurrEntry 11 }

nplus1StandardPMCurrLastDayPSAD OBJECT-TYPE
        SYNTAX  Gauge
        ACCESS  read-only
           STATUS mandatory
        DESCRIPTION
              "This value indicates the last Day PSAD value. "
        ::= { nplus1StandardPMCurrEntry 12 }

nplus1StandardPMCurrLastDayFSRD OBJECT-TYPE
        SYNTAX  Gauge
        ACCESS  read-only
           STATUS mandatory
        DESCRIPTION
              "This value indicates the last Day FSRD value. "
        ::= { nplus1StandardPMCurrEntry 13 }

nplus1StandardPMIntervalTable  OBJECT-TYPE
        SYNTAX  SEQUENCE OF Nplus1StandardPMIntervalEntry
        ACCESS  not-accessible
        STATUS mandatory
        DESCRIPTION
        "This table indicates the standard PM interval. "
        ::= { gnLinkGroups 9 }

nplus1StandardPMIntervalEntry OBJECT-TYPE
        SYNTAX Nplus1StandardPMIntervalEntry
        ACCESS  not-accessible
        STATUS mandatory
          DESCRIPTION
          "Entry containing the standard PM interval. "
        INDEX { nplus1StandardPMIntervalCarrierId, nplus1StandardPMIntervalIdx}
        ::= { nplus1StandardPMIntervalTable 1 }

Nplus1StandardPMIntervalEntry ::=
            SEQUENCE {
        nplus1StandardPMIntervalCarrierId
             INTEGER (1..15),
        nplus1StandardPMIntervalIdx
             INTEGER (1..96),
        nplus1StandardPMIntervalIDF
             INTEGER,
        nplus1StandardPMIntervalGroupNum
             INTEGER (-1..4),
        nplus1StandardPMIntervalPSAC
             Gauge,
        nplus1StandardPMIntervalFSRC
             Gauge,
        nplus1StandardPMIntervalPSAD
             Gauge,
        nplus1StandardPMIntervalFSRD
             Gauge
    }

nplus1StandardPMIntervalCarrierId OBJECT-TYPE
        SYNTAX  INTEGER (1..15)
        ACCESS  read-only
           STATUS mandatory
        DESCRIPTION
              "This value indicates the carrier id. "
        ::= { nplus1StandardPMIntervalEntry 1 }

nplus1StandardPMIntervalIdx OBJECT-TYPE
        SYNTAX  INTEGER (1..96)
        ACCESS  read-only
           STATUS mandatory
        DESCRIPTION
              "This value indicates the index. "
        ::= { nplus1StandardPMIntervalEntry 2 }


nplus1StandardPMIntervalIDF OBJECT-TYPE
        SYNTAX  INTEGER
        {
                off(2),
                on(3)
        }
        ACCESS  read-only
           STATUS mandatory
        DESCRIPTION
              "This value is an invalid data flag. "
        ::= { nplus1StandardPMIntervalEntry 3 }

nplus1StandardPMIntervalGroupNum OBJECT-TYPE
        SYNTAX  INTEGER (-1..4)
        ACCESS  read-only
           STATUS mandatory
        DESCRIPTION
              "This value indicates the group's number. "
        ::= { nplus1StandardPMIntervalEntry 4 }

nplus1StandardPMIntervalPSAC OBJECT-TYPE
        SYNTAX  Gauge
        ACCESS  read-only
           STATUS mandatory
        DESCRIPTION
              "This value indicates the PSAC value. "
        ::= { nplus1StandardPMIntervalEntry 5 }

nplus1StandardPMIntervalFSRC OBJECT-TYPE
        SYNTAX  Gauge
        ACCESS  read-only
           STATUS mandatory
        DESCRIPTION
              "This value indicates the FSRC value. "
        ::= { nplus1StandardPMIntervalEntry 6 }

nplus1StandardPMIntervalPSAD OBJECT-TYPE
        SYNTAX  Gauge
        ACCESS  read-only
           STATUS mandatory
        DESCRIPTION
              "This value indicates the PSAD value. "
        ::= { nplus1StandardPMIntervalEntry 7 }

nplus1StandardPMIntervalFSRD OBJECT-TYPE
        SYNTAX  Gauge
        ACCESS  read-only
           STATUS mandatory
        DESCRIPTION
              "This value indicates the FSRD value. "
        ::= { nplus1StandardPMIntervalEntry 8 }

nplus1StandardPMDayTable  OBJECT-TYPE
        SYNTAX  SEQUENCE OF Nplus1StandardPMDayEntry
        ACCESS  not-accessible
        STATUS mandatory
        DESCRIPTION
        "This table indicates the standard PM day table. "
        ::= { gnLinkGroups 10 }

nplus1StandardPMDayEntry OBJECT-TYPE
        SYNTAX Nplus1StandardPMDayEntry
        ACCESS  not-accessible
        STATUS mandatory
          DESCRIPTION
          "Entry containing the standard PM day table. "
        INDEX { nplus1StandardPMDayCarrierId, nplus1StandardPMDayIdx}
        ::= { nplus1StandardPMDayTable 1 }

Nplus1StandardPMDayEntry ::=
            SEQUENCE {
        nplus1StandardPMDayCarrierId
             INTEGER (1..15),
        nplus1StandardPMDayIdx
             INTEGER (1..30),
        nplus1StandardPMDayIDF
             INTEGER,
        nplus1StandardPMDayGroupNum
             INTEGER (-1..4),
        nplus1StandardPMDayPSAC
             Gauge,
        nplus1StandardPMDayFSRC
             Gauge,
        nplus1StandardPMDayPSAD
             Gauge,
        nplus1StandardPMDayFSRD
             Gauge
    }

nplus1StandardPMDayCarrierId OBJECT-TYPE
        SYNTAX  INTEGER (1..15)
        ACCESS  read-only
           STATUS mandatory
        DESCRIPTION
              "This value indicates the carrier id. "
        ::= { nplus1StandardPMDayEntry 1 }

nplus1StandardPMDayIdx OBJECT-TYPE
        SYNTAX  INTEGER (1..30)
        ACCESS  read-only
           STATUS mandatory
        DESCRIPTION
              "This value indicates the index. "
        ::= { nplus1StandardPMDayEntry 2 }

nplus1StandardPMDayIDF OBJECT-TYPE
        SYNTAX  INTEGER
        {
                off(2),
                on(3)
        }
        ACCESS  read-only
           STATUS mandatory
        DESCRIPTION
              "This value is an invalid data flag. "
        ::= { nplus1StandardPMDayEntry 3 }

nplus1StandardPMDayGroupNum OBJECT-TYPE
        SYNTAX  INTEGER (-1..4)
        ACCESS  read-only
           STATUS mandatory
        DESCRIPTION
              "This value indicates the group's number. "
        ::= { nplus1StandardPMDayEntry 4 }

nplus1StandardPMDayPSAC OBJECT-TYPE
        SYNTAX  Gauge
        ACCESS  read-only
           STATUS mandatory
        DESCRIPTION
              "This value indicates the PSAC value. "
        ::= { nplus1StandardPMDayEntry 5 }

nplus1StandardPMDayFSRC OBJECT-TYPE
        SYNTAX  Gauge
        ACCESS  read-only
           STATUS mandatory
        DESCRIPTION
              "This value indicates the FSRC value. "
        ::= { nplus1StandardPMDayEntry 6 }

nplus1StandardPMDayPSAD OBJECT-TYPE
        SYNTAX  Gauge
        ACCESS  read-only
           STATUS mandatory
        DESCRIPTION
              "This value indicates the PSAD value. "
        ::= { nplus1StandardPMDayEntry 7 }

nplus1StandardPMDayFSRD OBJECT-TYPE
        SYNTAX  Gauge
        ACCESS  read-only
           STATUS mandatory
        DESCRIPTION
              "This value indicates the FSRD value. "
        ::= { nplus1StandardPMDayEntry 8 }

-- /////  Protect end  ////////////

gnSSM OBJECT IDENTIFIER ::=  { gnUnits 4 }

gnSSMCfg OBJECT IDENTIFIER ::=  { gnSSM 1 }

gnSSMCfgSSMMode OBJECT-TYPE
        SYNTAX  INTEGER {
        enabled(2),
        disabled(3)
        }
        ACCESS  read-write
        STATUS mandatory
        DESCRIPTION
        " "
        DEFVAL { disabled }
        ::= { gnSSMCfg  1 }

gnSSMCfgPrimaryClockSource OBJECT-TYPE
        SYNTAX  INTEGER {
                                internalClock(2),
                external2MB(3),
                radioClock(4),
                fiberClock(5),
                external2MHz(6),
                external1AndHalfMB(7),
                                tributaryClock1(8),
                                tributaryClock2(9),
                                tributaryClock3(10),
                                tributaryClock4(11),
                                tributaryClock5(12),
                                tributaryClock6(13),
                                tributaryClock7(14),
                                tributaryClock8(15),
                                tributaryClock9(16),
                                tributaryClock10(17),
                                tributaryClock11(18),
                                tributaryClock12(19),
                                tributaryClock13(20),
                                tributaryClock14(21),
                                tributaryClock15(22),
                                tributaryClock16(23),
                                tribSTM1(24)
        }
        ACCESS  read-write
        STATUS mandatory
        DESCRIPTION
        "The primary clock source, configurable for ACCESS radios only."
        DEFVAL { internalClock }
        ::= { gnSSMCfg 2 }

gnSSMCfgPrimaryClockQuality OBJECT-TYPE
        SYNTAX  INTEGER (1..6)
        ACCESS  read-write
        STATUS mandatory
        DESCRIPTION
        " This parameter indicates the primary clock quality.
        Possible values for SDH:
        PRC(1), SSUT(2), SSUL(3), SEC(4), STU(5).
        Possible values for Sonet:
        PRS(1), STU(2), ST2(3), ST3(4), SMC(5), ST4(6).        "
        ::= { gnSSMCfg  3 }

gnSSMCfgSecondaryClockSource OBJECT-TYPE
        SYNTAX  INTEGER {
                                internalClock(2),
                external2MB(3),
                radioClock(4),
                fiberClock(5),
                external2MHz(6),
                external1AndHalfMB(7),
                                tributaryClock1(8),
                                tributaryClock2(9),
                                tributaryClock3(10),
                                tributaryClock4(11),
                                tributaryClock5(12),
                                tributaryClock6(13),
                                tributaryClock7(14),
                                tributaryClock8(15),
                                tributaryClock9(16),
                                tributaryClock10(17),
                                tributaryClock11(18),
                                tributaryClock12(19),
                                tributaryClock13(20),
                                tributaryClock14(21),
                                tributaryClock15(22),
                                tributaryClock16(23),
                                tribSTM1(24)
        }
        ACCESS  read-write
        STATUS mandatory
        DESCRIPTION
        "The secondary clock source, configurable for ACCESS radios only."
        DEFVAL { internalClock }
        ::= { gnSSMCfg 4 }


gnSSMCfgSecondaryClockQuality OBJECT-TYPE
        SYNTAX  INTEGER (1..6)
        ACCESS  read-write
        STATUS mandatory
        DESCRIPTION
        " This parameter indicates the secondary clock quality.
        Possible values for SDH:
        PRC(1), SSUT(2), SSUL(3), SEC(4), STU(5).
        Possible values for Sonet:
        PRS(1), STU(2), ST2(3), ST3(4), SMC(5), ST4(6).        "
        ::= { gnSSMCfg  5 }


gnSSMCfgClockUserCommand OBJECT-TYPE
        SYNTAX  INTEGER {
                                noAction(2),
                switchToPrimaryClock(3),
                switchToSecondaryClock(4),
                switchToInternalClock(5)
        }
        ACCESS  read-write
        STATUS mandatory
        DESCRIPTION
        "The clock user command.
         Switch is possible only when the SSM mode is disable."
        DEFVAL { noAction }
        ::= { gnSSMCfg 6 }

gnSSMCfgClockOutputMute OBJECT-TYPE
        SYNTAX  INTEGER { on(2), off(3) }
        ACCESS  read-write
        STATUS mandatory
        DESCRIPTION
        "This parameter indicates if clock output will be in mute state.
            (Mute on -> don't transmit) "
        DEFVAL { 2 }
        ::= { gnSSMCfg 7 }


gnSSMStat OBJECT IDENTIFIER ::=  { gnSSM 2 }

gnSSMStatStatus OBJECT-TYPE
        SYNTAX OCTET STRING(SIZE(2))
        ACCESS  read-only
        STATUS mandatory
        DESCRIPTION
        " Alarm status of SSM. Bit 1 is MSB, bit=1 when alarm active.
          bit 1  = Unlock
          bit 2  = Out Of Range
            bit 3 = Primary Clock Source Failure
          bit 4 = Secondary Clock Source Failure "
        ::= { gnSSMStat  1 }

gnSSMStatCurrentClock OBJECT-TYPE
        SYNTAX INTEGER {
                primary(2),
                secondary(3),
                internal(4),
                holdOver(5)
        }
        ACCESS  read-only
        STATUS mandatory
        DESCRIPTION
        " "
        ::= { gnSSMStat  2 }

gnSSMStatCurrentClockQuality OBJECT-TYPE
        SYNTAX  INTEGER (1..7)
        ACCESS  read-only
        STATUS mandatory
        DESCRIPTION
        " This parameter indicates the current clock quality.
        SDH values: PRC(1), SSUT(2), SSUL(3), SEC(4), STU(5), DNU(6).
        Sonet values: PRS(1), STU(2), ST2(3), ST3(4), SMC(5), ST4(6), DUS(7)."
        ::= { gnSSMStat  3 }

gnSSMStatClockUnitType OBJECT-TYPE
        SYNTAX INTEGER {
                noClockUnit(2),
                smc(3),
                sec(4),
                st3(5),
                st3e(6)
        }
        ACCESS  read-only
        STATUS mandatory
        DESCRIPTION
        "  "
        ::= { gnSSMStat  4 }

gnSSMStatHoldoverPeriod OBJECT-TYPE
        SYNTAX INTEGER (0..2880)
        ACCESS  read-only
        STATUS mandatory
        DESCRIPTION
        "This parameter indicates the minutes time period in holdover state. "
        DEFVAL { 0 }
        ::= { gnSSMStat  5 }


gnAccess OBJECT IDENTIFIER ::= { ceragon 4 }
gnAccessCfg OBJECT IDENTIFIER ::= { gnAccess 1 }
gnAccessCfgTable OBJECT-TYPE
        SYNTAX  SEQUENCE OF GnAccessCfgEntry
        ACCESS  not-accessible
        STATUS mandatory
        DESCRIPTION
        "This table defines the configuration and status of the access ports."
        ::= { gnAccessCfg 1 }

gnAccessCfgEntry OBJECT-TYPE
        SYNTAX GnAccessCfgEntry
        ACCESS  not-accessible
        STATUS mandatory
        DESCRIPTION
        "Entry for the table containing an interface index for every interface
         which type is DS3 (30, according to RFC1573)."
        INDEX {  ifIndex }
        ::= { gnAccessCfgTable 1 }

GnAccessCfgEntry ::=
            SEQUENCE {
        gnAccessCfgLongCableOption
             INTEGER,
        gnAccessCfgLoopbackOption
             INTEGER,
        gnAccessCfgRunPrbs
             INTEGER,
        gnAccessCfgEXCThresh
                INTEGER,
        gnAccessCfgSDThresh
                INTEGER,
        gnAccessCfgTest
                INTEGER,
        gnAccessCfgLineCoding
                INTEGER
}


gnAccessCfgLongCableOption OBJECT-TYPE
        SYNTAX  INTEGER {
        ds3ShortCable(2),
        ds3LongCable(3),
        t1From0to133ft(4),
        t1From133to266ft(5),
        t1From266to399ft(6),
        t1From399to533ft(7),
        t1From533to655ft(8),
        anyLength(9),
        t1FA640From0to110ft(10),
        t1FA640From110to220ft(11),
        t1FA640From220to330ft(12),
        t1FA640From330to440ft(13),
        t1FA640From440to550ft(14)
        }
        ACCESS  read-write
        STATUS mandatory
        DESCRIPTION
        " This parameter defines the line build-out option.
        Possible values:
        For DS3: ds3ShortCable, ds3LongCable.
        For T1: t1From0to133ft..t1From533to655ft.
        For E1/E3: anyLength. 
        For T1 in FIBEAIR 640 systems: t1FA640From0to110ft..t1FA640From440to550ft."
        DEFVAL { t1From0to133ft }
        ::= { gnAccessCfgEntry  1 }

gnAccessCfgLoopbackOption OBJECT-TYPE
        SYNTAX  INTEGER {
                noloopback(2),
                interfaceInterLoop(3),
                interfaceExterLoop(4)
                }
        ACCESS  read-write
        STATUS mandatory
        DESCRIPTION
        " This parameter enable the user to launch a loopback."
        ::= { gnAccessCfgEntry  2 }

gnAccessCfgRunPrbs OBJECT-TYPE
        SYNTAX  INTEGER {
                noOperation(2),
                lineOnRadioOnRcvLine(3),
                lineOnRadioOnRcvRadio(4),
                lineOnRadioOffRcvLine(5),
                lineOnRadioOffRcvRadio(6),
                lineOffRadioOnRcvLine(7),
                lineOffRadioOnRcvRadio(8),
                lineOffRadioOffRcvLine(9),
                lineOffRadioOffRcvRadio(10),
                lineOnRadioOnRcvOff(11),
                lineOffRadioOnRcvOff(12),
                lineOnRadioOffRcvOff(13)
                }

        ACCESS  read-write
        STATUS mandatory
        DESCRIPTION
        "This parameter enables launching a PRBS test."
        ::= { gnAccessCfgEntry  3 }

gnAccessCfgEXCThresh OBJECT-TYPE
        SYNTAX  INTEGER {
                        tenExpMinus3(2),
                        tenExpMinus4(3),
                        tenExpMinus5(4)
        }
        ACCESS  read-write
        STATUS mandatory
        DESCRIPTION
        " If the bit error rate is higher than this threshold
         an EXC alarm would be generated.
        EXC is for excessive."
        DEFVAL { tenExpMinus3}
        ::= { gnAccessCfgEntry 4 }

gnAccessCfgSDThresh OBJECT-TYPE
        SYNTAX  INTEGER {
                        tenExpMinus6(3),
                        tenExpMinus7(4),
                        tenExpMinus8(5),
                        tenExpMinus9(6)
        }
        ACCESS  read-write
        STATUS mandatory
        DESCRIPTION
        " If the bit error rate is higher than this threshold
         a SD alarm would be generated.
        SD is for Signal Degrade."
        DEFVAL { tenExpMinus6}
        ::= { gnAccessCfgEntry 5 }

gnAccessCfgTest OBJECT-TYPE
        SYNTAX  INTEGER {
                        noAction(2),
                        sendAIS(3)
        }
        ACCESS  read-write
        STATUS mandatory
        DESCRIPTION
        "This parameter controls the action to send AIS or not."
        ::= { gnAccessCfgEntry 6 }

gnAccessCfgLineCoding OBJECT-TYPE
        SYNTAX  INTEGER {
                        ami(2),
                        b8zs(3),
                        hdb3(4),
                        b3zs(5)
        }
        ACCESS  read-write
        STATUS mandatory
        DESCRIPTION
        "The line coding possible values:
         For T1: B7ZS(ami), B8ZS.
         For E1 & E3: HDB3.
         For DS3: B3ZS"
        ::= { gnAccessCfgEntry 7 }

---------------
gnAccessStat OBJECT IDENTIFIER ::= { gnAccess 2 }
gnAccessStatTable OBJECT-TYPE
        SYNTAX  SEQUENCE OF GnAccessStatEntry
        ACCESS  not-accessible
        STATUS mandatory
        DESCRIPTION
        "This table defines the status of the access ports."
        ::= { gnAccessStat 1 }

gnAccessStatEntry OBJECT-TYPE
        SYNTAX GnAccessStatEntry
        ACCESS  not-accessible
        STATUS mandatory
        DESCRIPTION
        "Entry for the table containing an interface index for every interface
         which type is DS3 (30, according to RFC1573)."
        INDEX {  ifIndex }
        ::= { gnAccessStatTable 1 }

GnAccessStatEntry ::=
            SEQUENCE {
        gnAccessStatInterfaceBer
           INTEGER,
        gnAccessStatStatus
           OCTET STRING,
        gnAccessStatPrbsBer
           INTEGER,
        gnAccessStatValidIntervals
           INTEGER
}
gnAccessStatInterfaceBer OBJECT-TYPE
        SYNTAX  INTEGER {
                        tenExpMinus3(2),
                        tenExpMinus4(3),
                        tenExpMinus5(4),
                        tenExpMinus6(5),
                        tenExpMinus7(6),
                        tenExpMinus8(7),
                        tenExpMinus9(8),
                        tenExpMinus10(9),
                        tenExpMinus11(10),
                        tenExpMinus12(11),
                        tenExpMinus13(12),
                        tenExpMinus14(13)
        }
        ACCESS  read-only
        STATUS mandatory
        DESCRIPTION
        " Current Bit Error Rate. "
        ::= { gnAccessStatEntry  1 }

gnAccessStatStatus OBJECT-TYPE
        SYNTAX OCTET STRING(SIZE(2))
        ACCESS  read-only
        STATUS mandatory
        DESCRIPTION
        " Alarm status of an ACCESS radio. Bit 1 is MSB, bit=1 when alarm active.
          bit 2  = LOS
          bit 6  = AIS
          bit 9  = SD
          bit 10 = EXC
          bit 11 = Unexpected signal -- when disabled, will rise if detect data.
          bit 14 = Out Of Lock "
        ::= { gnAccessStatEntry 2 }

gnAccessStatPrbsBer OBJECT-TYPE
        SYNTAX  INTEGER {
                        tenExpMinus3(2),
                        tenExpMinus4(3),
                        tenExpMinus5(4),
                        tenExpMinus6(5),
                        tenExpMinus7(6),
                        tenExpMinus8(7),
                        tenExpMinus9(8),
                        tenExpMinus10(9),
                        tenExpMinus11(10),
                        tenExpMinus12(11),
                        tenExpMinus13(12),
                        tenExpMinus14(13)
        }
        ACCESS  read-only
        STATUS mandatory
        DESCRIPTION
        "Current PRBS Errors of the operation set
        in the mib variable gnAccessCfgRunPrbs,
        use this variable to clear the error counter."
        ::= { gnAccessStatEntry  3 }

gnAccessStatValidIntervals OBJECT-TYPE
        SYNTAX INTEGER (0..96)
        ACCESS  read-only
        STATUS mandatory
        DESCRIPTION
        "The number of previous valid intervals for which valid data has been stored
         for the specific interface."
        ::= { gnAccessStatEntry 4 }

----
gnFastEthernetCfg OBJECT IDENTIFIER ::= { gnAccess 3 }
gnFastEthernetCfgTable OBJECT-TYPE
        SYNTAX  SEQUENCE OF GnFastEthernetCfgEntry
        ACCESS  not-accessible
        STATUS mandatory
        DESCRIPTION
        "This table defines the configuration of the Fast Ethernet ports."
        ::= { gnFastEthernetCfg 1 }

gnFastEthernetCfgEntry OBJECT-TYPE
        SYNTAX GnFastEthernetCfgEntry
        ACCESS  not-accessible
        STATUS mandatory
        DESCRIPTION
        "This is an entry in the Fast Ethernet configuration table."
        INDEX {  ifIndex }
        ::= { gnFastEthernetCfgTable 1 }

GnFastEthernetCfgEntry ::=
            SEQUENCE {
        gnFastEthernetCfgAutoNegotiation
             INTEGER,
        gnFastEthernetCfgForceSpeed
             INTEGER,
        gnFastEthernetCfgDynamicBand
                INTEGER,
        gnFastEthernetCfgGigabitEthernet
                INTEGER,
        gnFastEthernetCfgDuplexMode
             INTEGER,
        gnFastEthernetCfgQueuingScheme
             INTEGER
}

gnFastEthernetCfgAutoNegotiation OBJECT-TYPE
        SYNTAX  INTEGER { on(2), off(3) }
        ACCESS  read-write
        STATUS mandatory
        DESCRIPTION
        " This parameter defines if auto negotiations protocol is active."
        ::= { gnFastEthernetCfgEntry  1 }

gnFastEthernetCfgForceSpeed OBJECT-TYPE
        SYNTAX  INTEGER {
                tenBased(2),
                hundredBased(3)
                }
        ACCESS  read-write
        STATUS mandatory
        DESCRIPTION
        "This parameter force speed when auto negotiation is off."
        ::= { gnFastEthernetCfgEntry  2 }

gnFastEthernetCfgDynamicBand OBJECT-TYPE
        SYNTAX  INTEGER {
                        notActive(2),
                        dynamic(3),
                        leftPreferred(4),
                        vlanPriority(5),
                    ipPriority(6)
        }
        ACCESS  read-write
        STATUS mandatory
        DESCRIPTION
        "Dynamic bandwidth allocation:
        dynamic means that the two Fast Ethernet ports have the same priority.
        LeftPreferred indicates that left Fast Ethernet card priority is higher."
        ::= { gnFastEthernetCfgEntry 3 }

gnFastEthernetCfgGigabitEthernet OBJECT-TYPE
        SYNTAX  INTEGER {
                        disable(2),
                        enable(3)
        }
        ACCESS  read-write
        STATUS mandatory
        DESCRIPTION
        " Gigabit Ethernet option.
        This parameter will be changed after reset. "
        ::= { gnFastEthernetCfgEntry 4 }

gnFastEthernetCfgDuplexMode OBJECT-TYPE
        SYNTAX  INTEGER {
                halfDuplex(2),
                fullDuplex(3)
                }
        ACCESS  read-write
        STATUS mandatory
        DESCRIPTION
        "This parameter force duplex mode when auto negotiation is off."
        ::= { gnFastEthernetCfgEntry  5 }

gnFastEthernetCfgQueuingScheme OBJECT-TYPE
        SYNTAX  INTEGER {
                fixedPriority(2),
                weightedFair(3)
                }
        ACCESS  read-write
        STATUS mandatory
        DESCRIPTION
        "This parameter set the Queuing algorithm."
        ::= { gnFastEthernetCfgEntry  6 }

----
gnFastEthernetStat OBJECT IDENTIFIER ::= { gnAccess 4 }
gnFastEthernetStatTable OBJECT-TYPE
        SYNTAX  SEQUENCE OF GnFastEthernetStatEntry
        ACCESS  not-accessible
        STATUS mandatory
        DESCRIPTION
        "The Fast Ethernet status table."
        ::= { gnFastEthernetStat 1 }

gnFastEthernetStatEntry OBJECT-TYPE
        SYNTAX GnFastEthernetStatEntry
        ACCESS  not-accessible
        STATUS mandatory
        DESCRIPTION
        "This is an entry in the Fast Ethernet status table."
        INDEX {  ifIndex }
        ::= { gnFastEthernetStatTable 1 }

GnFastEthernetStatEntry ::=
            SEQUENCE {
        gnFastEthernetStatStatus
           OCTET STRING
}

gnFastEthernetStatStatus OBJECT-TYPE
        SYNTAX OCTET STRING(SIZE(2))
        ACCESS  read-only
        STATUS mandatory
        DESCRIPTION
        " Alarm status of an FE radio. Bit 1 is MSB, bit=1 when alarm active.
          bit 2 = Loss of Carrier"
        ::= { gnFastEthernetStatEntry 1 }

----
-- Statistics(PM) For PDH (NB DS3). All PDH tables are included for future
-- development and are not currently implemented.
gnPdhMon OBJECT IDENTIFIER ::=  { gnAccess 5 }

gnPdhMonCurrTable OBJECT-TYPE
        SYNTAX  SEQUENCE OF GnPdhMonCurrEntry
        ACCESS  not-accessible
        STATUS mandatory
        DESCRIPTION
        "This table maintains the counters for the PDH table. "
        ::= { gnPdhMon 1 }

gnPdhMonCurrEntry OBJECT-TYPE
        SYNTAX GnPdhMonCurrEntry
        ACCESS  not-accessible
        STATUS mandatory
        DESCRIPTION
        "This is an entry in the PDH
         Counters Table. This table contains an interface index for every interface
         which type is DS3(30, according to RFC1573)."
        INDEX {  ifIndex }
        ::= { gnPdhMonCurrTable 1 }

GnPdhMonCurrEntry ::=
            SEQUENCE {
        gnPdhMonCurrES
             Gauge,
        gnPdhMonCurrSES
             Gauge,
        gnPdhMonCurrBBE
             Gauge,
        gnPdhMonCurrUAS
             Gauge,
        gnPdhMonCurrCV
             Gauge,
        gnPdhMonCurrLastDayES
             Gauge,
        gnPdhMonCurrLastDaySES
             Gauge,
        gnPdhMonCurrLastDayBBE
             Gauge,
        gnPdhMonCurrLastDayUAS
             Gauge,
        gnPdhMonCurrLastDayCV
             Gauge,
		gnPdhMonCurrLastDayIDF
			 INTEGER	
}

gnPdhMonCurrES OBJECT-TYPE
        SYNTAX  Gauge
        ACCESS  read-only
        STATUS mandatory
        DESCRIPTION
        "The current number of errored seconds starting from the present 15 minute
period.  ."
        ::= { gnPdhMonCurrEntry 1}

gnPdhMonCurrSES OBJECT-TYPE
        SYNTAX  Gauge
        ACCESS  read-only
        STATUS mandatory
        DESCRIPTION
        "The current number of severely errored seconds, starting from the present
15 minute period."
        ::= { gnPdhMonCurrEntry 2}


gnPdhMonCurrBBE OBJECT-TYPE
        SYNTAX  Gauge
        ACCESS  read-only
        STATUS mandatory
        DESCRIPTION
        " The current number of Background Block Errors
         starting from the present 15 minutes period."
        ::= { gnPdhMonCurrEntry 3}

gnPdhMonCurrUAS OBJECT-TYPE
        SYNTAX  Gauge
        ACCESS  read-only
        STATUS mandatory
        DESCRIPTION
        " The current number of Unavailable Seconds
         starting         from the present 15 minutes period."
        ::= { gnPdhMonCurrEntry 4}

gnPdhMonCurrCV OBJECT-TYPE
        SYNTAX  Gauge
        ACCESS  read-only
        STATUS mandatory
        DESCRIPTION
        " The current number of CV
         starting from the present 15 minutes period."
        ::= { gnPdhMonCurrEntry 5}

gnPdhMonCurrLastDayES OBJECT-TYPE
        SYNTAX  Gauge
        ACCESS  read-only
        STATUS mandatory
        DESCRIPTION
        " The current number of Errored Seconds
         starting from the present 24 hours period."
        ::= { gnPdhMonCurrEntry 6 }

gnPdhMonCurrLastDaySES OBJECT-TYPE
        SYNTAX  Gauge
        ACCESS  read-only
        STATUS mandatory
        DESCRIPTION
        " The current number of Severely Errored Seconds
         starting from the present 24 hours period."
        ::= { gnPdhMonCurrEntry 7 }

gnPdhMonCurrLastDayBBE OBJECT-TYPE
        SYNTAX  Gauge
        ACCESS  read-only
        STATUS mandatory
        DESCRIPTION
        " The current number of Background Block Errors
         starting         from the present 24 hours period."
        ::= { gnPdhMonCurrEntry 8 }

gnPdhMonCurrLastDayUAS OBJECT-TYPE
        SYNTAX  Gauge
        ACCESS  read-only
        STATUS mandatory
        DESCRIPTION
        " The current number of Unavailable  Seconds
         starting         from the present 24 hours period."
        ::= { gnPdhMonCurrEntry 9 }

gnPdhMonCurrLastDayCV OBJECT-TYPE
        SYNTAX  Gauge
        ACCESS  read-only
        STATUS mandatory
        DESCRIPTION
        "The current number of CV, starting from the present 24-hour period."
        ::= { gnPdhMonCurrEntry 10}

gnPdhMonCurrLastDayIDF OBJECT-TYPE
        SYNTAX  INTEGER {
                        off(2),
                        on(3)
        }
        ACCESS read-only
        STATUS mandatory
        DESCRIPTION
        "IDF = Invalid Data Flag."
        DEFVAL { off }
        ::= { gnPdhMonCurrEntry 11 }

gnPdhMonIntervalTable OBJECT-TYPE
        SYNTAX  SEQUENCE OF GnPdhMonIntervalEntry
        ACCESS  not-accessible
        STATUS mandatory
        DESCRIPTION
        "This table maintains the counters of the PDH per interval."
        ::= { gnPdhMon 2 }


gnPdhMonIntervalEntry OBJECT-TYPE
        SYNTAX GnPdhMonIntervalEntry
        ACCESS  not-accessible
        STATUS mandatory
        DESCRIPTION
        "This is an entry in the PDH
         Counters Table. This table contains an interface index for every interface
         which type is DS3(30, according to RFC1573).
        This table is indexed by an interval index, between 1
        to 96 and representing each one 15 minutes.
               The oldest is 96."
        INDEX {  ifIndex, gnPdhMonIntervalIdx}
        ::= { gnPdhMonIntervalTable 1 }

GnPdhMonIntervalEntry ::=
            SEQUENCE {
        gnPdhMonIntervalIdx
              INTEGER,
        gnPdhMonIntervalES
             Gauge,
        gnPdhMonIntervalSES
             Gauge,
        gnPdhMonIntervalBBE
             Gauge,
        gnPdhMonIntervalUAS
             Gauge,
        gnPdhMonIntervalCV
             Gauge,
        gnPdhMonIntervalIDF
                 INTEGER

}

gnPdhMonIntervalIdx OBJECT-TYPE
        SYNTAX INTEGER (1..96)
        ACCESS read-only
        STATUS mandatory
        DESCRIPTION
        "This table is indexed per interval number. Each interval
        is of 15 minutes and the oldest is 96."
        ::= { gnPdhMonIntervalEntry 1 }

gnPdhMonIntervalES OBJECT-TYPE
        SYNTAX  Gauge
        ACCESS  read-only
        STATUS mandatory
        DESCRIPTION
        "The number of errored seconds per interval."
        ::= { gnPdhMonIntervalEntry 2}

gnPdhMonIntervalSES OBJECT-TYPE
        SYNTAX  Gauge
        ACCESS  read-only
        STATUS mandatory
        DESCRIPTION
        "The number of severely errored seconds per interval."
        ::= { gnPdhMonIntervalEntry 3}

gnPdhMonIntervalBBE OBJECT-TYPE
        SYNTAX  Gauge
        ACCESS  read-only
        STATUS mandatory
        DESCRIPTION
        " The number of Background Block Errors
        per interval."
        ::= { gnPdhMonIntervalEntry 4}

gnPdhMonIntervalUAS OBJECT-TYPE
        SYNTAX  Gauge
        ACCESS  read-only
        STATUS mandatory
        DESCRIPTION
        " The  number of Unavailable Seconds per interval."
        ::= { gnPdhMonIntervalEntry 5}

gnPdhMonIntervalCV OBJECT-TYPE
        SYNTAX  Gauge
        ACCESS  read-only
        STATUS mandatory
        DESCRIPTION
        "The number of CV per interval."
        ::= { gnPdhMonIntervalEntry 6}

gnPdhMonIntervalIDF OBJECT-TYPE
        SYNTAX  INTEGER {
                        off(2),
                        on(3)
        }
        ACCESS read-only
        STATUS mandatory
        DESCRIPTION
        "IDF = Invalid Data Flag."
        DEFVAL { off }
        ::= { gnPdhMonIntervalEntry 7 }


gnPdhMonDayTable OBJECT-TYPE
        SYNTAX  SEQUENCE OF GnPdhMonDayEntry
        ACCESS  not-accessible
        STATUS mandatory
        DESCRIPTION
        "This table maintains the counters of the PDH per 24 hours interval."
        ::= { gnPdhMon 3 }

gnPdhMonDayEntry OBJECT-TYPE
        SYNTAX GnPdhMonDayEntry
        ACCESS  not-accessible
        STATUS mandatory
        DESCRIPTION
        "This is an entry in the PDH
         Counters Table. This table contains an interface index for every interface
         which type is DS3(30, according to RFC1573).
        This table is indexed by an interval index, between 1
        to 30 and representing each one 24 hours.
               The oldest is 30."
        INDEX {  ifIndex, gnPdhMonDayIdx}
        ::= { gnPdhMonDayTable 1 }

GnPdhMonDayEntry ::=
            SEQUENCE {
        gnPdhMonDayIdx
              INTEGER,
        gnPdhMonDayES
             Gauge,
        gnPdhMonDaySES
             Gauge,
        gnPdhMonDayBBE
             Gauge,
        gnPdhMonDayUAS
             Gauge,
        gnPdhMonDayCV
             Gauge,
        gnPdhMonDayIDF
             INTEGER
}

gnPdhMonDayIdx OBJECT-TYPE
        SYNTAX INTEGER (1..30)
        ACCESS read-only
        STATUS mandatory
        DESCRIPTION
        "This table is indexed per interval number. Each interval
        is of 24 hours and the oldest is 30."
        ::= { gnPdhMonDayEntry 1 }

gnPdhMonDayES OBJECT-TYPE
        SYNTAX  Gauge
        ACCESS  read-only
        STATUS mandatory
        DESCRIPTION
        " The number of Errored Seconds per interval of 24 hours."
        ::= { gnPdhMonDayEntry 2}

gnPdhMonDaySES OBJECT-TYPE
        SYNTAX  Gauge
        ACCESS  read-only
        STATUS mandatory
        DESCRIPTION
        " The number of Severely Errored Seconds
         per interval of 24 hours."
        ::= { gnPdhMonDayEntry 3}

gnPdhMonDayBBE OBJECT-TYPE
        SYNTAX  Gauge
        ACCESS  read-only
        STATUS mandatory
        DESCRIPTION
        " The number of Background Block Errors
         per interval of 24 hours."
        ::= { gnPdhMonDayEntry 4 }

gnPdhMonDayUAS OBJECT-TYPE
        SYNTAX  Gauge
        ACCESS  read-only
        STATUS mandatory
        DESCRIPTION
        " The number of Unavailable Seconds
         per interval of 24 hours."
        ::= { gnPdhMonDayEntry 5 }

gnPdhMonDayCV OBJECT-TYPE
        SYNTAX  Gauge
        ACCESS  read-only
        STATUS mandatory
        DESCRIPTION
        " The number of Code Violation Seconds
         per interval of 24 hours."
        ::= { gnPdhMonDayEntry 6}

gnPdhMonDayIDF OBJECT-TYPE
        SYNTAX  INTEGER {
                        off(2),
                        on(3)
        }
        ACCESS read-only
        STATUS mandatory
        DESCRIPTION
        "IDF = Invalid Data Flag."
        DEFVAL { off }
        ::= { gnPdhMonDayEntry 7 }
----

-- ADI: FE Statistics

gnFastEthernetMon OBJECT IDENTIFIER ::= { gnAccess 6 }

gnFastEthernetMonPrivateTable OBJECT-TYPE
        SYNTAX  SEQUENCE OF GnFastEthernetMonPrivateEntry
        ACCESS  not-accessible
        STATUS mandatory
        DESCRIPTION
        "The Fast Ethernet Private Statistics Table."
        ::= { gnFastEthernetMon 1 }

gnFastEthernetMonPrivateEntry OBJECT-TYPE
        SYNTAX GnFastEthernetMonPrivateEntry
        ACCESS  not-accessible
        STATUS mandatory
        DESCRIPTION
        "This is an entry in the Fast Ethernet private statistics table."
        INDEX {  ifIndex }
        ::= { gnFastEthernetMonPrivateTable 1 }

GnFastEthernetMonPrivateEntry ::=
            SEQUENCE {
    gnFastEthernetMonPrivateAlignmentErrors
        Counter,
    gnFastEthernetMonPrivateFcsErrors
        Counter,
    gnFastEthernetMonPrivateFrameTooLongs
        Counter
}

gnFastEthernetMonPrivateAlignmentErrors OBJECT-TYPE
              SYNTAX  Counter
              ACCESS  read-only
              STATUS  mandatory
              DESCRIPTION
                      " The number of received packets with an alignment
                                            error (Received frame length is not a multiple
                                                of 8 bits, and an FCS error had occurred). "
        ::= { gnFastEthernetMonPrivateEntry 1 }

gnFastEthernetMonPrivateFcsErrors OBJECT-TYPE
              SYNTAX  Counter
              ACCESS  read-only
              STATUS  mandatory
              DESCRIPTION
                      " Total number of received packets with a frame check
                                            sequence (FCS) or Cycle Redundancy Check (CRC) error. "
        ::= { gnFastEthernetMonPrivateEntry 2 }

gnFastEthernetMonPrivateFrameTooLongs OBJECT-TYPE
              SYNTAX  Counter
              ACCESS  read-only
              STATUS  mandatory
              DESCRIPTION
                      " Total number of received frames with an illegal
                                            packet length (>1518 bytes). "
        ::= { gnFastEthernetMonPrivateEntry 3 }

---------------

gnFastEthernetMonStdHiTable OBJECT-TYPE
        SYNTAX  SEQUENCE OF GnFastEthernetMonStdHiEntry
        ACCESS  not-accessible
        STATUS mandatory
        DESCRIPTION
        "This table contains the 32 high bits (MSB) of RFC1213 statistics
         for Fast Ethernet."
        ::= { gnFastEthernetMon 2 }

gnFastEthernetMonStdHiEntry OBJECT-TYPE
        SYNTAX GnFastEthernetMonStdHiEntry
        ACCESS  not-accessible
        STATUS mandatory
        DESCRIPTION
        "This is an entry in the Fast Ethernet
         Standard Statistics Table."
        INDEX {  ifIndex }
        ::= { gnFastEthernetMonStdHiTable 1 }

GnFastEthernetMonStdHiEntry ::=
            SEQUENCE {
    gnFastEthernetMonStdHiInOctetsHC
                Counter,
        gnFastEthernetMonStdHiInUcastPktsHC
        Counter,
    gnFastEthernetMonStdHiInNUcastPktsHC
        Counter,
    gnFastEthernetMonStdHiOutOctetsHC
        Counter,
    gnFastEthernetMonStdHiOutUcastPktsHC
        Counter,
    gnFastEthernetMonStdHiOutNUcastPktsHC
        Counter
}

gnFastEthernetMonStdHiInOctetsHC OBJECT-TYPE
              SYNTAX  Counter
              ACCESS  read-only
              STATUS  mandatory
              DESCRIPTION
                      "The 32 MSB of The total number of octets received
                                           on the interface, including framing characters."
        ::= { gnFastEthernetMonStdHiEntry 1 }

gnFastEthernetMonStdHiInUcastPktsHC OBJECT-TYPE
              SYNTAX  Counter
              ACCESS  read-only
              STATUS  mandatory
              DESCRIPTION
                      "The 32 MSB of The number of subnetwork-unicast
                                           packets delivered to a higher-layer protocol."
        ::= { gnFastEthernetMonStdHiEntry 2 }

gnFastEthernetMonStdHiInNUcastPktsHC OBJECT-TYPE
              SYNTAX  Counter
              ACCESS  read-only
              STATUS  mandatory
              DESCRIPTION
                      "The 32 MSB of The number of non-unicast
                                           (i.e., subnetwork- broadcast or subnetwork-multicast)
                                           packets delivered to a higher-layer protocol."
        ::= { gnFastEthernetMonStdHiEntry 3 }

gnFastEthernetMonStdHiOutOctetsHC OBJECT-TYPE
              SYNTAX  Counter
              ACCESS  read-only
              STATUS  mandatory
              DESCRIPTION
                      "The 32 MSB of The total number of octets transmitted
                                           out of the interface, including framing characters."
        ::= { gnFastEthernetMonStdHiEntry 4 }

gnFastEthernetMonStdHiOutUcastPktsHC OBJECT-TYPE
              SYNTAX  Counter
              ACCESS  read-only
              STATUS  mandatory
              DESCRIPTION
                      "The 32 MSB of The total number of packets that
                                           higher-level protocols requested be transmitted
                                           to a subnetwork-unicast address, including those
                                           that were discarded or not sent."
        ::= { gnFastEthernetMonStdHiEntry 5 }

gnFastEthernetMonStdHiOutNUcastPktsHC OBJECT-TYPE
              SYNTAX  Counter
              ACCESS  read-only
              STATUS  mandatory
              DESCRIPTION
                      "The 32 MSB of The total number of packets that
                                           higher-level protocols requested be transmitted
                                           to a non- unicast (i.e., a subnetwork-broadcast
                                           or subnetwork-multicast) address, including those
                       that were discarded or not sent."
        ::= { gnFastEthernetMonStdHiEntry 6 }

gnTrailCfg OBJECT IDENTIFIER ::= { gnAccess 7 }
gnTrailCfgTable OBJECT-TYPE
        SYNTAX  SEQUENCE OF GnTrailCfgEntry
        ACCESS  not-accessible
        STATUS mandatory
        DESCRIPTION
        "This table defines the configuration of the trail ports."
        ::= { gnTrailCfg 1 }

gnTrailCfgEntry OBJECT-TYPE
        SYNTAX GnTrailCfgEntry
        ACCESS  not-accessible
        STATUS mandatory
        INDEX { ifIndex }
        ::= { gnTrailCfgTable 1 }

GnTrailCfgEntry ::=
            SEQUENCE {
        gnTrailCfgTrailName
                DisplayString,
        gnTrailCfgProtection
                INTEGER,
        gnTrailCfgLowPathIndex
                INTEGER,
        gnTrailCfgLowPathSide
                INTEGER,
        gnTrailCfgProtectionOptions
                INTEGER,
        gnTrailCfgMismatchJ2
            INTEGER,
        gnTrailCfgTransmittedJ2
            DisplayString,
        gnTrailCfgExpectedJ2
            DisplayString,
        gnTrailCfgReversionMode
                INTEGER,
        gnTrailCfgProtectionUserCommand
                INTEGER,
        gnTrailCfgHoldOffTime
                INTEGER,
        gnTrailCfgOscillationGuardTime
                INTEGER,
        gnTrailCfgWaitToRestoreTime
                INTEGER,
        gnTrailCfgSignalLabelMismatch
                INTEGER,
        gnTrailCfgBERConsAction
                INTEGER
}

gnTrailCfgTrailName OBJECT-TYPE
        SYNTAX  DisplayString(SIZE(0..40))
        ACCESS  read-write
        STATUS mandatory
        DESCRIPTION
        ""
        ::= { gnTrailCfgEntry 1 }

gnTrailCfgProtection OBJECT-TYPE
        SYNTAX  INTEGER {
                protected(2),
                unprotected(3)
        }
        ACCESS  read-write
        STATUS mandatory
        DESCRIPTION
        ""
        DEFVAL { protected}
        ::= { gnTrailCfgEntry 2 }

gnTrailCfgLowPathIndex OBJECT-TYPE
        SYNTAX  INTEGER
        ACCESS  read-write
        STATUS mandatory
        DESCRIPTION
        "This parameter indicates the K.L.M index.
        It includes 3 digits:
        K - most significant digit, L - next digit,
        M - last significant digit.
        For E1 ports (SDH):   K=1..3 ; L=1..7 ; M=1..3.
        For T1 ports (Sonet): K=1..3 ; L=1..7 ; M=1..4.
        For DS3/E3:                   K=1..3 ; L=M=0.
        If there is no K.L.M index: K=L=M=0.
        Example: for mapping an E1 port to K.L.M = 2.5.3, write 253."
        ::= { gnTrailCfgEntry 3 }

gnTrailCfgLowPathSide OBJECT-TYPE
        SYNTAX  INTEGER {
                                east(2),
                     west(3)
                }
        ACCESS  read-write
        STATUS mandatory
            DEFVAL        {east}
        ::= { gnTrailCfgEntry 4 }

gnTrailCfgProtectionOptions OBJECT-TYPE
        SYNTAX  INTEGER {
                                inhibit(2),
                     auto(3)
                }
        ACCESS  read-write
        STATUS mandatory
            DEFVAL        {auto}
        ::= { gnTrailCfgEntry 5 }

gnTrailCfgMismatchJ2 OBJECT-TYPE
        SYNTAX  INTEGER{
                sendAlarm(2),
                sendAIS(3),
                ignoreAlarm(4)
        }
        ACCESS  read-write
        STATUS mandatory
        DESCRIPTION
        "In case of  J2 mismatch  error, send alarm or send AIS."
        DEFVAL { sendAlarm }
        ::= { gnTrailCfgEntry 6 }

gnTrailCfgTransmittedJ2 OBJECT-TYPE
        SYNTAX  DisplayString(SIZE(0..15))
        ACCESS  read-write
        STATUS mandatory
        DESCRIPTION
        "This is the J2 string that would be sent."
        DEFVAL { "J2 J2 J2 J2 J2 " }
        ::= { gnTrailCfgEntry 7 }

gnTrailCfgExpectedJ2 OBJECT-TYPE
                SYNTAX  DisplayString(SIZE(0..15))
                ACCESS  read-write
                STATUS mandatory
                DESCRIPTION
                  "This is the J2 string that is expected to be received."
                DEFVAL { "J2 J2 J2 J2 J2 " }
                ::= { gnTrailCfgEntry 8 }

gnTrailCfgReversionMode OBJECT-TYPE
        SYNTAX  INTEGER {
                                revertive(2),
                     nonRevertive(3)
                }
        ACCESS  read-write
        STATUS mandatory
            DEFVAL        {nonRevertive}
        ::= { gnTrailCfgEntry 9 }


gnTrailCfgProtectionUserCommand OBJECT-TYPE
        SYNTAX  INTEGER {
                                noAction(2),
                     switchToProtection(3),
                                switchToWorking(4)
                }
        ACCESS  read-write
        STATUS mandatory
            DEFVAL        {noAction}
        ::= { gnTrailCfgEntry 10 }

gnTrailCfgHoldOffTime OBJECT-TYPE
        SYNTAX  INTEGER (0..20000)
        ACCESS  read-write
        STATUS mandatory
                DESCRIPTION
                  "This is the hold-off time in milliseconds.
                 Possible values: 0..20000, 100 mSec steps. "
            DEFVAL        {0}
        ::= { gnTrailCfgEntry 11 }


gnTrailCfgOscillationGuardTime OBJECT-TYPE
        SYNTAX  INTEGER (0..60)
        ACCESS  read-write
        STATUS mandatory
                DESCRIPTION
                  "This is the oscillation guard time in seconds.
                 Possible values: 0..60. "
            DEFVAL        {0}
        ::= { gnTrailCfgEntry 12 }


gnTrailCfgWaitToRestoreTime OBJECT-TYPE
        SYNTAX  INTEGER (5..12)
        ACCESS  read-write
        STATUS mandatory
                DESCRIPTION
                  "This is the wait-to-restore time in minutes.
                 Possible values: 5..12. "
            DEFVAL        {5}
        ::= { gnTrailCfgEntry 13 }

gnTrailCfgSignalLabelMismatch OBJECT-TYPE
        SYNTAX  INTEGER{
                sendAlarm(2),
                sendAIS(3)
        }
        ACCESS  read-write
        STATUS mandatory
                DESCRIPTION
                  " In case of a V5 mismatch error, send or don't send AIS."
            DEFVAL        { sendAlarm }
        ::= { gnTrailCfgEntry 14 }

gnTrailCfgBERConsAction OBJECT-TYPE
        SYNTAX  INTEGER{
                sendAlarm(2),
                sendAISDoPathProtection(3),
                doPathProtection(4)
        }
        ACCESS  read-write
        STATUS mandatory
                DESCRIPTION
                  "  "
            DEFVAL        { doPathProtection }
        ::= { gnTrailCfgEntry 15 }


gnTribCfg OBJECT IDENTIFIER ::= { gnAccess 8 }
gnTribCfgTable OBJECT-TYPE
        SYNTAX  SEQUENCE OF GnTribCfgEntry
        ACCESS  not-accessible
        STATUS mandatory
        DESCRIPTION
        "This table defines the configuration of the virtual trails in the Trib STM-1."
        ::= { gnTribCfg 1 }

gnTribCfgEntry OBJECT-TYPE
        SYNTAX GnTribCfgEntry
        ACCESS  not-accessible
        STATUS mandatory
        INDEX { ifIndex }
        ::= { gnTribCfgTable 1 }

GnTribCfgEntry ::=
            SEQUENCE {
        gnTribCfgLowPathIndex
                INTEGER,
        gnTribCfgLowPathSide
                INTEGER,
        gnTribCfgProtection
                INTEGER,
        gnTribCfgProtectionOptions
                INTEGER,
        gnTribCfgReversionMode
                INTEGER,
        gnTribCfgProtectionUserCommand
                INTEGER,
        gnTribCfgHoldOffTime
                INTEGER,
        gnTribCfgOscillationGuardTime
                INTEGER,
        gnTribCfgWaitToRestoreTime
                INTEGER,
        gnTribCfgKLM
                INTEGER
--        gnTribCfgBERConsAction                        ask Shuki if we need this
--                INTEGER
}

gnTribCfgLowPathIndex OBJECT-TYPE
        SYNTAX  INTEGER
        ACCESS  read-write
        STATUS mandatory
        DESCRIPTION
        "This parameter indicates the K.L.M index.
        It includes 3 digits:
        K - most significant digit, L - next digit,
        M - last significant digit.
        For E1 ports (SDH):   K=1..3 ; L=1..7 ; M=1..3.
        For T1 ports (Sonet): K=1..3 ; L=1..7 ; M=1..4.
        For DS3/E3:                   K=1..3 ; L=M=0.
        If there is no K.L.M index: K=L=M=0.
        Example: for mapping an E1 port to K.L.M = 2.5.3, write 253."
        ::= { gnTribCfgEntry 1 }

gnTribCfgLowPathSide OBJECT-TYPE
        SYNTAX  INTEGER {
                                east(2),
                     west(3)
                }
        ACCESS  read-write
        STATUS mandatory
            DEFVAL        {east}
        ::= { gnTribCfgEntry 2 }


gnTribCfgProtection OBJECT-TYPE
        SYNTAX  INTEGER {
                protected(2),
                unprotected(3)
        }
        ACCESS  read-write
        STATUS mandatory
        DESCRIPTION
        ""
        DEFVAL { protected}
        ::= { gnTribCfgEntry 3 }

gnTribCfgProtectionOptions OBJECT-TYPE
        SYNTAX  INTEGER {
                                inhibit(2),
                     auto(3)
                }
        ACCESS  read-write
        STATUS mandatory
            DEFVAL        {auto}
        ::= { gnTribCfgEntry 4 }

gnTribCfgReversionMode OBJECT-TYPE
        SYNTAX  INTEGER {
                                revertive(2),
                     nonRevertive(3)
                }
        ACCESS  read-write
        STATUS mandatory
            DEFVAL        {nonRevertive}
        ::= { gnTribCfgEntry 5 }


gnTribCfgProtectionUserCommand OBJECT-TYPE
        SYNTAX  INTEGER {
                                noAction(2),
                     switchToProtection(3),
                                switchToWorking(4)
                }
        ACCESS  read-write
        STATUS mandatory
            DEFVAL        {noAction}
        ::= { gnTribCfgEntry 6 }

gnTribCfgHoldOffTime OBJECT-TYPE
        SYNTAX  INTEGER (0..20000)
        ACCESS  read-write
        STATUS mandatory
                DESCRIPTION
                  "This is the hold-off time in milliseconds.
                 Possible values: 0..20000, 100 mSec steps. "
            DEFVAL        {0}
        ::= { gnTribCfgEntry 7 }


gnTribCfgOscillationGuardTime OBJECT-TYPE
        SYNTAX  INTEGER (0..60)
        ACCESS  read-write
        STATUS mandatory
                DESCRIPTION
                  "This is the oscillation guard time in seconds.
                 Possible values: 0..60. "
            DEFVAL        {0}
        ::= { gnTribCfgEntry 8 }


gnTribCfgWaitToRestoreTime OBJECT-TYPE
        SYNTAX  INTEGER (5..12)
        ACCESS  read-write
        STATUS mandatory
                DESCRIPTION
                  "This is the wait-to-restore time in minutes.
                 Possible values: 5..12. "
            DEFVAL        {5}
        ::= { gnTribCfgEntry 9 }

gnTribCfgKLM OBJECT-TYPE
                SYNTAX  INTEGER
        ACCESS  read-write
        STATUS mandatory
                DESCRIPTION
                  " "
        ::= { gnTribCfgEntry 10 }

-- gnTribCfgBERConsAction OBJECT-TYPE
--        SYNTAX  INTEGER{
--                sendAlarm(2),
--                sendAISDoPathProtection(3),
--                doPathProtection(4)
--        }
--        ACCESS  read-write
--        STATUS mandatory
--                DESCRIPTION
--                  "  "
--            DEFVAL        { doPathProtection }
--        ::= { gnTribCfgEntry 15 }
------

gnTrailPassThrough OBJECT IDENTIFIER ::= { gnAccess 9 }
gnTrailPassThroughTable OBJECT-TYPE
        SYNTAX  SEQUENCE OF GnTrailPassThroughEntry
        ACCESS  not-accessible
        STATUS mandatory
        DESCRIPTION
        "This table defines the configuration of the virtual trails in the Trib STM-1. It is applicable for ADM"
        ::= { gnTrailPassThrough 1 }

gnTrailPassThroughEntry OBJECT-TYPE
        SYNTAX GnTrailPassThroughEntry
        ACCESS  not-accessible
        STATUS mandatory
        INDEX { gnTrailPassThroughIndex }
        ::= { gnTrailPassThroughTable 1 }

GnTrailPassThroughEntry ::=
            SEQUENCE {
        gnTrailPassThroughIndex
                INTEGER,
        gnTrailPassThroughName
                DisplayString
        }

gnTrailPassThroughIndex OBJECT-TYPE
        SYNTAX  INTEGER (1..84)
        ACCESS  read-only
           STATUS mandatory
    DESCRIPTION
    "This is the index of Trail Pass-Through Table. SDH(1-63), Sonet (1-84)."
    ::= { gnTrailPassThroughEntry 1 }

gnTrailPassThroughName OBJECT-TYPE
        SYNTAX  DisplayString(SIZE(0..40))
        ACCESS  read-write
        STATUS mandatory
        DESCRIPTION
        "for NMS use"
        ::= { gnTrailPassThroughEntry 2 }

gnGigabitEthernetCfg OBJECT IDENTIFIER ::= { gnAccess 10 }
gnGigabitEthernetCfgTable OBJECT-TYPE
        SYNTAX  SEQUENCE OF GnGigabitEthernetCfgEntry
        ACCESS  not-accessible
        STATUS mandatory
        DESCRIPTION
        "This table defines the configuration of the Gigabit Ethernet port."
        ::= { gnGigabitEthernetCfg 1 }

gnGigabitEthernetCfgEntry OBJECT-TYPE
        SYNTAX GnGigabitEthernetCfgEntry
        ACCESS  not-accessible
        STATUS mandatory
        DESCRIPTION
        "This is an entry in the Gigabit Ethernet configuration table."
        INDEX {  ifIndex }
        ::= { gnGigabitEthernetCfgTable 1 }

GnGigabitEthernetCfgEntry ::=
            SEQUENCE {
        gnGigabitEthernetCfgFlowControl
                INTEGER,
        gnGigabitEthernetCfgMuteOnExcError
             INTEGER,
        gnGigabitEthernetCfgMuteOnSd
             INTEGER,
        gnGigabitEthernetCfgMuteOnRemoteRadioFault
                INTEGER
}

gnGigabitEthernetCfgFlowControl OBJECT-TYPE
        SYNTAX  INTEGER { enable(2), disable(3) }
        ACCESS  read-write
        STATUS mandatory
        DESCRIPTION
        " This parameter defines if flow control protocol is active."
        ::= { gnGigabitEthernetCfgEntry  1 }

gnGigabitEthernetCfgMuteOnExcError OBJECT-TYPE
        SYNTAX  INTEGER { enable(2), disable(3) }
        ACCESS  read-write
        STATUS mandatory
        DESCRIPTION
        " This parameter defines whether to mute GBE Tx on excessive BER."
        ::= { gnGigabitEthernetCfgEntry  2 }

gnGigabitEthernetCfgMuteOnSd OBJECT-TYPE
        SYNTAX  INTEGER { enable(2), disable(3) }
        ACCESS  read-write
        STATUS mandatory
        DESCRIPTION
        " This parameter defines whether to mute GBE Tx port on signal degrade."
        ::= { gnGigabitEthernetCfgEntry  3 }

gnGigabitEthernetCfgMuteOnRemoteRadioFault OBJECT-TYPE
        SYNTAX  INTEGER { enable(2), disable(3) }
        ACCESS  read-write
        STATUS mandatory
        DESCRIPTION
        " This parameter defines whether to mute GBE Tx port on exe error."
        ::= { gnGigabitEthernetCfgEntry  4 }

gnLastDummy OBJECT IDENTIFIER ::= { ceragon 9 }

gnLastDummyParam OBJECT-TYPE
        SYNTAX  INTEGER
        ACCESS  read-only
        STATUS mandatory
        DESCRIPTION
        " This parameter specifies the end of CERAGON's MIB."
        ::= { gnLastDummy 1 }


























-- Traps
gnODUTrap TRAP-TYPE
      ENTERPRISE  ceragon
      VARIABLES  {gnGenCfgTrapSeverity , gnGenCfgAlarmText ,
gnGenStatDeviceODUStatus,gnGenCfgIDUSerialNumber }
      DESCRIPTION
          "The trap is sent every time an alarm occurs in the ODU."
      ::= 1


gnIDUTrap TRAP-TYPE
      ENTERPRISE  ceragon
      VARIABLES  {gnGenCfgTrapSeverity , gnGenCfgAlarmText ,
gnGenDrawerXDeviceIDUStatus,gnGenCfgIDUSerialNumber}
      DESCRIPTION
          "The trap is sent every time an alarm occurs in the IDU."
      ::= 2

gnSDHTrap TRAP-TYPE
      ENTERPRISE  ceragon
      VARIABLES  {gnGenCfgTrapSeverity , gnGenCfgAlarmText ,
gnGenStatDeviceRSTStatus,gnGenCfgIDUSerialNumber}
      DESCRIPTION
          "The trap is sent every time an alarm occurs in the Regenerator section
in
           the SONET/SDH."
      ::= 3

gnACCESSTrap TRAP-TYPE
      ENTERPRISE  ceragon
      VARIABLES  {gnGenCfgTrapSeverity , gnGenCfgAlarmText ,
gnGenCfgIDUSerialNumber}
      DESCRIPTION
          "The trap is sent every time an alarm occurs in an Access line."
      ::= 4

gnODUTrapCleared TRAP-TYPE
      ENTERPRISE  ceragon
      VARIABLES  {gnGenCfgTrapSeverity , gnGenCfgAlarmText , gnGenStatDeviceODUStatus,gnGenCfgIDUSerialNumber }
      DESCRIPTION
          "The trap is sent every time an alarm occurs in the ODU."
      ::= 5

gnIDUTrapCleared TRAP-TYPE
      ENTERPRISE  ceragon
      VARIABLES  {gnGenCfgTrapSeverity , gnGenCfgAlarmText , gnGenDrawerXDeviceIDUStatus,gnGenCfgIDUSerialNumber}
      DESCRIPTION
          "The trap is sent every time an alarm occurs in the IDU."
      ::= 6

gnSDHTrapCleared TRAP-TYPE
      ENTERPRISE  ceragon
      VARIABLES  {gnGenCfgTrapSeverity , gnGenCfgAlarmText , gnGenStatDeviceRSTStatus,gnGenCfgIDUSerialNumber}
      DESCRIPTION
          "The trap is sent every time an alarm occurs in the Regenerator section in
           the SONET/SDH."
      ::= 7

gnAccessTrapCleared TRAP-TYPE
      ENTERPRISE  ceragon
      VARIABLES  {gnGenCfgTrapSeverity , gnGenCfgAlarmText , gnGenCfgIDUSerialNumber}
      DESCRIPTION
          "The trap is sent every time an alarm occurs in an Access line."
      ::= 8


-- Event Traps

gnLODUPowerFailTrap TRAP-TYPE
      ENTERPRISE  ceragon
      VARIABLES  {gnGenCfgTrapSeverity , gnGenCfgAlarmText , gnOduStatusPowerSupply,gnGenCfgCLLI}
      DESCRIPTION
          "This Trap is sent every time a Local ODU Power fault occurs. "
      ::= 10

gnLODUSynthUnLockTrap TRAP-TYPE
      ENTERPRISE  ceragon
      VARIABLES  {gnGenCfgTrapSeverity , gnGenCfgAlarmText , gnOduStatusSynthesizerVCOLock,gnGenCfgCLLI}
      DESCRIPTION
          "This Trap is sent every time a Local ODU Hardware fault occurs ."
      ::= 11
gnLODUTxLevelOutOfRangeTrap TRAP-TYPE
      ENTERPRISE  ceragon
      VARIABLES  {gnGenCfgTrapSeverity , gnGenCfgAlarmText , gnOduStatusTransmitLevel,gnGenCfgCLLI}
      DESCRIPTION
          "This Trap is sent every time a Local ODU TX signal is out of range. "
      ::= 12

gnLODURxLevelOutOfRangeTrap TRAP-TYPE
      ENTERPRISE  ceragon
      VARIABLES  {gnGenCfgTrapSeverity , gnGenCfgAlarmText , gnOduStatusReceiveLevel,gnGenCfgCLLI}
      DESCRIPTION
          "This Trap is sent every time a Local ODU RX signal is out of range. "
      ::= 13

gnLODUExtremeTempTrap TRAP-TYPE
      ENTERPRISE  ceragon
      VARIABLES  {gnGenCfgTrapSeverity , gnGenCfgAlarmText , gnOduStatusFahrenheitTemp,gnGenCfgCLLI}
      DESCRIPTION
          "This Trap is sent every time a Local ODU extreme temperature event occurs. "
      ::= 14

gnLIDUPowerFailTrap TRAP-TYPE
      ENTERPRISE  ceragon
      VARIABLES  {gnGenCfgTrapSeverity , gnGenCfgAlarmText , gnGenStatDevicePowerSupply,gnGenCfgCLLI}
      DESCRIPTION
          "This Trap is sent every time a Local IDU Power fault occurs. "
      ::= 15

gnLCableFaultTrap TRAP-TYPE
      ENTERPRISE  ceragon
      VARIABLES  {gnGenCfgTrapSeverity , gnGenCfgAlarmText , gnGenStatDeviceCable,gnGenCfgCLLI}
      DESCRIPTION
          "This Trap is sent every time a Local IDU-ODU cable fault occurs."
      ::= 16

gnLModemFailTrap TRAP-TYPE
      ENTERPRISE  ceragon
      VARIABLES  {gnGenCfgTrapSeverity , gnGenCfgAlarmText , gnGenCfgCLLI}
      DESCRIPTION
          "This Trap is sent every time a Local Modem faults occurs."
      ::= 17

gnLIDUExtremeTempTrap TRAP-TYPE
      ENTERPRISE  ceragon
      VARIABLES  {gnGenCfgTrapSeverity , gnGenCfgAlarmText , gnGenStatDeviceFahrenheitTemp,gnGenCfgCLLI}
      DESCRIPTION
          "This Trap is sent every time a Local IDU extreme temperature event occurs. "
      ::=  18

gnLLoopbackOnTrap TRAP-TYPE
      ENTERPRISE  ceragon
      VARIABLES  {gnGenCfgTrapSeverity , gnGenCfgAlarmText , gnGenCfgCLLI}
      DESCRIPTION
          "This Trap is sent every time a Local Loopback is activated."
      ::=  19

gnLRemoteCommFaultTrap TRAP-TYPE
      ENTERPRISE  ceragon
      VARIABLES  {gnGenCfgTrapSeverity , gnGenCfgAlarmText , gnGenCfgCLLI}
      DESCRIPTION
          "This Trap is sent every time the remote communication is disconnected. "
      ::=  20

gnLTestRunningTrap TRAP-TYPE
      ENTERPRISE  ceragon
      VARIABLES  {gnGenCfgTrapSeverity , gnGenCfgAlarmText , gnRstCfgTestActivate,gnGenCfgCLLI}
      DESCRIPTION
          "This Trap is sent every time a Local SDH/SONET test is activated. "
      ::=  21

gnLLOFTrap TRAP-TYPE
      ENTERPRISE  ceragon
      VARIABLES  {ifIndex, gnGenCfgTrapSeverity , gnGenCfgAlarmText , gnGenCfgCLLI}
      DESCRIPTION
          "This Trap is sent every time a Local Loss of Frame alarm occurs."
      ::=  22

gnLLOSTrap TRAP-TYPE
      ENTERPRISE  ceragon
      VARIABLES  {ifIndex, gnGenCfgTrapSeverity , gnGenCfgAlarmText , gnGenCfgCLLI}
      DESCRIPTION
          "This Trap is sent every time a Local Loss of signal alarm occurs."
      ::=  23

gnLTIMTrap TRAP-TYPE
      ENTERPRISE  ceragon
      VARIABLES  {ifIndex, gnGenCfgTrapSeverity , gnGenCfgAlarmText , gnGenCfgCLLI}
      DESCRIPTION
          "This Trap is sent every time a Local Trace Identifier Mismatch alarm occurs."
      ::=  24

gnLEXCTrap TRAP-TYPE
      ENTERPRISE  ceragon
      VARIABLES  {ifIndex, gnGenCfgTrapSeverity , gnGenCfgAlarmText , gnRstStatBERCur ,gnGenCfgCLLI}
      DESCRIPTION
          "This Trap is sent every time a Local Excessive BER alarm is raised. "
      ::= 25

gnLSDTrap TRAP-TYPE
      ENTERPRISE  ceragon
      VARIABLES  {ifIndex, gnGenCfgTrapSeverity , gnGenCfgAlarmText , gnRstStatBERCur,gnGenCfgCLLI}
      DESCRIPTION
          "This Trap is sent every time a Local Signal Degrade alarm is raised."
      ::= 26

gnLRcvAisTrap TRAP-TYPE
      ENTERPRISE  ceragon
      VARIABLES  {ifIndex, gnGenCfgTrapSeverity , gnGenCfgAlarmText , gnGenCfgCLLI}
      DESCRIPTION
          "This Trap is sent every time the local terminal receives an Alarm Indication Signal (AIS)."
      ::= 27

gnLUnExpTrap TRAP-TYPE
      ENTERPRISE  ceragon
      VARIABLES  {ifIndex, gnGenCfgTrapSeverity , gnGenCfgAlarmText , gnGenCfgCLLI}
      DESCRIPTION
          "This Trap is sent every time a Local terminal receives an unexpected signal."
      ::= 28

gnLLocTrap TRAP-TYPE
      ENTERPRISE  ceragon
      VARIABLES  {ifIndex, gnGenCfgTrapSeverity , gnGenCfgAlarmText , gnGenCfgCLLI}
      DESCRIPTION
          "This Trap is sent every time a Local Loss of Clock alarm occurs."
      ::= 29

---
gnLLopTrap TRAP-TYPE
      ENTERPRISE  ceragon
      VARIABLES  {ifIndex, gnGenCfgTrapSeverity , gnGenCfgAlarmText , gnGenCfgCLLI}
      DESCRIPTION
          "This Trap is sent every time a Local Loss of pointer alarm occurs."
      ::= 30

gnLRdiTrap TRAP-TYPE
      ENTERPRISE  ceragon
      VARIABLES  {ifIndex, gnGenCfgTrapSeverity , gnGenCfgAlarmText , gnGenCfgCLLI}
      DESCRIPTION
          "This Trap is sent every time the local terminal receives a Remote Defect Identifier signal (RDI). "
      ::= 31

gnLSlmTrap TRAP-TYPE
      ENTERPRISE  ceragon
      VARIABLES  {ifIndex, gnGenCfgTrapSeverity , gnGenCfgAlarmText , gnGenCfgCLLI}
      DESCRIPTION
          "This Trap is sent every time a Local Signal (Payload) Label Mismatch alarm occurs."
      ::= 32

gnLUnqTrap TRAP-TYPE
      ENTERPRISE  ceragon
      VARIABLES  {ifIndex, gnGenCfgTrapSeverity , gnGenCfgAlarmText , gnGenCfgCLLI}
      DESCRIPTION
          "This Trap is sent every time a Local unequipped signal is received. "
      ::= 33

---
gnLExternalAlarm1OnTrap TRAP-TYPE
      ENTERPRISE  ceragon
      VARIABLES  {gnGenCfgTrapSeverity , gnGenCfgAlarmText , gnGenStatDeviceDryContact,gnGenCfgCLLI}
      DESCRIPTION
          "This Trap is sent every time a Local External alarm 1 is raised. "
      ::= 34

gnLExternalAlarm2OnTrap TRAP-TYPE
      ENTERPRISE  ceragon
      VARIABLES  {gnGenCfgTrapSeverity , gnGenCfgAlarmText , gnGenStatDeviceDryContact,gnGenCfgCLLI}
      DESCRIPTION
          "This Trap is sent every time a Local External alarm 2 is raised. "
      ::= 35

gnLExternalAlarm3OnTrap TRAP-TYPE
      ENTERPRISE  ceragon
      VARIABLES  {gnGenCfgTrapSeverity , gnGenCfgAlarmText , gnGenStatDeviceDryContact,gnGenCfgCLLI}
      DESCRIPTION
          "This Trap is sent every time a Local External alarm 3 is raised. "
      ::= 36

gnLExternalAlarm4OnTrap TRAP-TYPE
      ENTERPRISE  ceragon
      VARIABLES  {gnGenCfgTrapSeverity , gnGenCfgAlarmText , gnGenStatDeviceDryContact,gnGenCfgCLLI}
      DESCRIPTION
          "This Trap is sent every time a Local External alarm 4 is raised. "
      ::= 37

gnLExternalAlarm5OnTrap TRAP-TYPE
      ENTERPRISE  ceragon
      VARIABLES  {gnGenCfgTrapSeverity , gnGenCfgAlarmText , gnGenStatDeviceDryContact,gnGenCfgCLLI}
      DESCRIPTION
          "This Trap is sent every time a Local External alarm 5 is raised. "
      ::= 38

gnLExternalAlarm6OnTrap TRAP-TYPE
      ENTERPRISE  ceragon
      VARIABLES  {gnGenCfgTrapSeverity , gnGenCfgAlarmText , gnGenStatDeviceDryContact,gnGenCfgCLLI}
      DESCRIPTION
          "This Trap is sent every time a Local External alarm 6 is raised. "
      ::= 39

gnLExternalAlarm7OnTrap TRAP-TYPE
      ENTERPRISE  ceragon
      VARIABLES  {gnGenCfgTrapSeverity , gnGenCfgAlarmText , gnGenStatDeviceDryContact,gnGenCfgCLLI}
      DESCRIPTION
          "This Trap is sent every time a Local External alarm 7 is raised. "
      ::= 40

gnLExternalAlarm8OnTrap TRAP-TYPE
      ENTERPRISE  ceragon
      VARIABLES  {gnGenCfgTrapSeverity , gnGenCfgAlarmText , gnGenStatDeviceDryContact,gnGenCfgCLLI}
      DESCRIPTION
          "This Trap is sent every time a Local External alarm 8 is raised. "
      ::= 41


gnLSystemFaultTrap TRAP-TYPE
      ENTERPRISE  ceragon
      VARIABLES  {gnGenCfgTrapSeverity , gnGenCfgAlarmText , gnGenDrawerXInternalCommunication,gnGenCfgCLLI}
      DESCRIPTION
          "This Trap is sent every time a Local System fault occurs."
      ::= 42

gnLTftpFaultTrap TRAP-TYPE
      ENTERPRISE  ceragon
      VARIABLES  {gnGenCfgTrapSeverity , gnGenCfgAlarmText , gnGenCfgCLLI}
      DESCRIPTION
          "This Trap is sent every time a Local TFTP Download fails."
      ::= 43

gnLInternalDownloadFaultTrap TRAP-TYPE
      ENTERPRISE  ceragon
      VARIABLES  {gnGenCfgTrapSeverity , gnGenCfgAlarmText , gnGenCfgCLLI}
      DESCRIPTION
          "This Trap is sent every time a Local internal Download fails."
      ::= 44

gnLIntralinkFaultTrap TRAP-TYPE
      ENTERPRISE  ceragon
      VARIABLES  {gnGenCfgTrapSeverity , gnGenCfgAlarmText , gnGenCfgCLLI}
      DESCRIPTION
          "This Trap is sent every time a Local intra-link download fails."
      ::= 45

gnLConfMismatchTrap TRAP-TYPE
      ENTERPRISE  ceragon
      VARIABLES  {gnGenCfgTrapSeverity , gnGenCfgAlarmText , gnGenCfgCLLI}
      DESCRIPTION
          "This Trap is sent every time a Local configuration mismatch fault occurs."
      ::= 46

gnLProtectSwitchFaultTrap TRAP-TYPE
      ENTERPRISE  ceragon
      VARIABLES  {gnGenCfgTrapSeverity , gnGenCfgAlarmText , gnGenCfgCLLI}
      DESCRIPTION
          "This Trap is sent every time a Local Protection fault is raised."
      ::= 47

gnLProtectCableFaultTrap TRAP-TYPE
      ENTERPRISE  ceragon
      VARIABLES  {gnGenCfgTrapSeverity , gnGenCfgAlarmText , gnGenCfgCLLI}
      DESCRIPTION
          "This Trap is sent every time a Local protection cable fault is raised."
      ::= 48

gnLHeartBeatTrap  TRAP-TYPE
      ENTERPRISE  ceragon
      VARIABLES  {gnGenCfgTrapSeverity , gnGenCfgAlarmText , gnGenCfgCLLI}
      DESCRIPTION
          "This Trap is a periodic heart beat trap."
      ::= 49

gnLLomTrap TRAP-TYPE
      ENTERPRISE  ceragon
      VARIABLES  {ifIndex, gnGenCfgTrapSeverity , gnGenCfgAlarmText , gnGenCfgCLLI}
      DESCRIPTION
          "This Trap is sent every time a Local Loss of Multi-frame alarm occurs."
      ::= 50

gnLHitlessProblemTrap TRAP-TYPE
      ENTERPRISE  ceragon
      VARIABLES  {gnGenCfgTrapSeverity , gnGenCfgAlarmText , gnGenCfgCLLI}
      DESCRIPTION
          "This Trap is sent every time a Local Hitless fault occurs."
      ::= 51

gnLHitlessRadioLofTrap TRAP-TYPE
      ENTERPRISE  ceragon
      VARIABLES  {gnGenCfgTrapSeverity , gnGenCfgAlarmText , gnGenCfgCLLI}
      DESCRIPTION
          "This Trap is sent every time a Local Hitless RadioLOF fault occurs."
      ::= 52

gnLHitlessCableDisconnectTrap TRAP-TYPE
      ENTERPRISE  ceragon
      VARIABLES  {gnGenCfgTrapSeverity , gnGenCfgAlarmText , gnGenCfgCLLI}
      DESCRIPTION
          "This Trap is sent every time a Local Hitless cable fault is raised. "
      ::= 53


gnLPamTrap TRAP-TYPE
      ENTERPRISE  ceragon
      VARIABLES  {ifIndex, gnGenCfgTrapSeverity , gnGenCfgAlarmText , gnGenCfgCLLI}
      DESCRIPTION
          "This Trap is sent when system in MSP Protection Architecture Mismatch."
      ::=  54

gnLScmTrap TRAP-TYPE
      ENTERPRISE  ceragon
      VARIABLES  {ifIndex, gnGenCfgTrapSeverity , gnGenCfgAlarmText , gnGenCfgCLLI}
      DESCRIPTION
          "This Trap is sent when there is a MSP Selector Channel Mismatch (K1,K2)."
      ::=  55

gnLInvTrap TRAP-TYPE
      ENTERPRISE  ceragon
      VARIABLES  {ifIndex, gnGenCfgTrapSeverity , gnGenCfgAlarmText , gnGenCfgCLLI}
      DESCRIPTION
          "This Trap indicates that the received K1 byte is invalid (MSP)."
      ::=  56

gnLInbandTrap TRAP-TYPE
      ENTERPRISE  ceragon
      VARIABLES  {ifIndex, gnGenCfgTrapSeverity , gnGenCfgAlarmText , gnGenCfgCLLI}
      DESCRIPTION
          "This Trap is sent when the Inband PPP link goes down."
      ::=  57

gnWSLOSTrap TRAP-TYPE
      ENTERPRISE  ceragon
      VARIABLES  {gnGenCfgTrapSeverity , gnGenCfgAlarmText , gnGenCfgCLLI}
      DESCRIPTION
          "This Trap is sent when the Wayside channel is in LOS state."
      ::=  58

gnODUtoODUCableFaultTrap TRAP-TYPE
      ENTERPRISE  ceragon
      VARIABLES  {gnGenCfgTrapSeverity , gnGenCfgAlarmText , gnGenCfgCLLI}
      DESCRIPTION
          "This Trap is sent when there is a problem with the ODU to ODU cable - for XPIC topology only."
      ::=  59

gnNoSignalReceivedFromODUTrap TRAP-TYPE
      ENTERPRISE  ceragon
      VARIABLES  {gnGenCfgTrapSeverity , gnGenCfgAlarmText , gnGenCfgCLLI}
      DESCRIPTION
          "This Trap is sent when no signal is received from the ODU."
      ::=  60

gnProtectionLockoutConfiguredTrap TRAP-TYPE
      ENTERPRISE  ceragon
      VARIABLES  {gnGenCfgTrapSeverity , gnGenCfgAlarmText , gnGenCfgCLLI}
      DESCRIPTION
          "This Trap is sent when Protection lockout is configured."
      ::=  61

gnRFUPowerFailureTrap TRAP-TYPE
      ENTERPRISE  ceragon
      VARIABLES  {gnGenCfgTrapSeverity , gnGenCfgAlarmText , gnGenCfgCLLI}
      DESCRIPTION
          "This Trap is sent in case of 12V/-5V/1.5V/6V/Vdrain power supply failure ."
      ::=  62

gnRFURxLevelPathOutOfRangeTrap TRAP-TYPE
      ENTERPRISE  ceragon
      VARIABLES  {gnGenCfgTrapSeverity , gnGenCfgAlarmText , gnGenCfgCLLI}
      DESCRIPTION
          "This Trap is sent in case of RSL of Main/Diversity channel is very low(typically below -80dBm) ."
      ::=  63

gnRFUExtremeTemperatureTrap TRAP-TYPE
      ENTERPRISE  ceragon
      VARIABLES  {gnGenCfgTrapSeverity , gnGenCfgAlarmText , gnGenCfgCLLI}
      DESCRIPTION
          "This Trap is sent in case of RFU temperature is too high/low ."
      ::=  64

gnRFUFanFailureTrap TRAP-TYPE
      ENTERPRISE  ceragon
      VARIABLES  {gnGenCfgTrapSeverity , gnGenCfgAlarmText , gnGenCfgCLLI}
      DESCRIPTION
          "This Trap is sent in case of fan failure detection by RFU ."
      ::=  65

gnLowSignalToRFUTrap TRAP-TYPE
      ENTERPRISE  ceragon
      VARIABLES  {gnGenCfgTrapSeverity , gnGenCfgAlarmText , gnGenCfgCLLI}
      DESCRIPTION
          "This Trap is sent in case of low IDM signal reception (350MHz) ."
      ::=  66

gnRFUXPICClockFailureTrap TRAP-TYPE
      ENTERPRISE  ceragon
      VARIABLES  {gnGenCfgTrapSeverity , gnGenCfgAlarmText , gnGenCfgCLLI}
      DESCRIPTION
          "This Trap is sent in case of XPIC clock failure ."
      ::=  67

gnRFUDelayCalibrationFailure1Trap TRAP-TYPE
      ENTERPRISE  ceragon
      VARIABLES  {gnGenCfgTrapSeverity , gnGenCfgAlarmText , gnGenCfgCLLI}
      DESCRIPTION
          "This Trap is sent if RX AGC is not locked (-10dBm) ."
      ::=  68

gnRFUDelayCalibrationFailure2Trap TRAP-TYPE
      ENTERPRISE  ceragon
      VARIABLES  {gnGenCfgTrapSeverity , gnGenCfgAlarmText , gnGenCfgCLLI}
      DESCRIPTION
          "This Trap is sent if calibration cannot be done since the notch is too wide/deep ."
      ::=  69

gnLSFPFaultTrap TRAP-TYPE
      ENTERPRISE  ceragon
      VARIABLES  {ifIndex, gnGenCfgTrapSeverity , gnGenCfgAlarmText , gnGenCfgCLLI}
      DESCRIPTION
          "This Trap is sent every time a Gigabit ethernet SFP fault occurs."
      ::=  70

gnEncryptionFaultTrap TRAP-TYPE
      ENTERPRISE  ceragon
      VARIABLES  {ifIndex, gnGenCfgTrapSeverity , gnGenCfgAlarmText , gnGenCfgCLLI}
      DESCRIPTION
          "This Trap is sent every time a Encryption fault occurs."
      ::=  71

gnEncryptionSyncLosTrap TRAP-TYPE
      ENTERPRISE  ceragon
      VARIABLES  {ifIndex, gnGenCfgTrapSeverity , gnGenCfgAlarmText , gnGenCfgCLLI}
      DESCRIPTION
          "This Trap is sent every time a Encryption synchhronization loss occurs."
      ::=  72

gnEncryptionKepTimout TRAP-TYPE
      ENTERPRISE  ceragon
      VARIABLES  {ifIndex, gnGenCfgTrapSeverity , gnGenCfgAlarmText , gnGenCfgCLLI}
      DESCRIPTION
          "This Trap is sent every time a Encryption KEP Timout fault occurs."
      ::=  73

gnEncryptionSkTimerElapsed TRAP-TYPE
      ENTERPRISE  ceragon
      VARIABLES  {ifIndex, gnGenCfgTrapSeverity , gnGenCfgAlarmText , gnGenCfgCLLI}
      DESCRIPTION
          "This Trap is sent every time a Encryption Session Key Timer elapsed."
      ::=  74

gnEncryptionPowerUpSelfTestFail TRAP-TYPE
      ENTERPRISE  ceragon
      VARIABLES  {ifIndex, gnGenCfgTrapSeverity , gnGenCfgAlarmText , gnGenCfgCLLI}
      DESCRIPTION
          "This Trap is sent every time a Encryption Power Up Self Test fault occurs."
      ::=  75

gnEncryptionConditionalTestFail TRAP-TYPE
      ENTERPRISE  ceragon
      VARIABLES  {ifIndex, gnGenCfgTrapSeverity , gnGenCfgAlarmText , gnGenCfgCLLI}
      DESCRIPTION
          "This Trap is sent every time a Encryption Conditional Test fault occurs."
      ::=  76

gnEncryptionWillTurnOffOnNextRest TRAP-TYPE
      ENTERPRISE  ceragon
      VARIABLES  {ifIndex, gnGenCfgTrapSeverity , gnGenCfgAlarmText , gnGenCfgCLLI}
      DESCRIPTION
          "This Trap is sent every time a Encryption will be turned off on the next reset occurs."
      ::=  77

gnEncryptionEventReport TRAP-TYPE
      ENTERPRISE  ceragon
      VARIABLES  {ifIndex, gnGenCfgTrapSeverity , gnGenCfgAlarmText , gnGenCfgCLLI}
      DESCRIPTION
          "This Trap is sent every time a Encryption event report occurs."
      ::=  78

gnEncryptionTechCardWasDetected TRAP-TYPE
      ENTERPRISE  ceragon
      VARIABLES  {ifIndex, gnGenCfgTrapSeverity , gnGenCfgAlarmText , gnGenCfgCLLI}
      DESCRIPTION
          "This Trap is sent every time Encryption Technician card is detected."
      ::=  79

gnAdminPasswordInDefaultState TRAP-TYPE
      ENTERPRISE  ceragon
      VARIABLES  {ifIndex, gnGenCfgTrapSeverity , gnGenCfgAlarmText , gnGenCfgCLLI}
      DESCRIPTION
          "This Trap is sent every time a admin password is in default state."
      ::=  80

gnLinkGroupingProtectionFaultTrap TRAP-TYPE
      ENTERPRISE  ceragon
      VARIABLES  {gnGenCfgTrapSeverity , gnGenCfgAlarmText , gnGenCfgCLLI}
      DESCRIPTION
          "This Trap is sent in case of Link Grouping Protection Fault."
      ::=  81

gnLossOfProtectionTrap TRAP-TYPE
      ENTERPRISE  ceragon
      VARIABLES  {gnGenCfgTrapSeverity , gnGenCfgAlarmText , gnGenCfgCLLI}
      DESCRIPTION
          "This Trap is sent in case of Loss of Protection."
      ::=  82

gnTempLicenseTrap TRAP-TYPE
      ENTERPRISE  ceragon
      VARIABLES  {gnGenCfgTrapSeverity , gnGenCfgAlarmText , gnGenCfgCLLI}
      DESCRIPTION
          "This Trap is sent in case of Temp License is Enable."
      ::=  83

gnMUXCfgXTempLicenseTrap TRAP-TYPE
      ENTERPRISE  ceragon
      VARIABLES  {gnGenCfgTrapSeverity , gnGenCfgAlarmText , gnGenCfgCLLI}
      DESCRIPTION
          "This Trap is sent in case of Temp License is Enable."
      ::=  84

-- ********************

gnLODUPowerOkTrap TRAP-TYPE
      ENTERPRISE  ceragon
      VARIABLES  {gnGenCfgTrapSeverity , gnGenCfgAlarmText , gnOduStatusPowerSupply,gnGenCfgCLLI}
      DESCRIPTION
          "This Trap is sent every time a Local ODU Power fault cleared."
      ::= 110

gnLODUSynthLockTrap TRAP-TYPE
      ENTERPRISE  ceragon
      VARIABLES  {gnGenCfgTrapSeverity , gnGenCfgAlarmText , gnOduStatusSynthesizerVCOLock,gnGenCfgCLLI}
      DESCRIPTION
          "This Trap is sent every time a Local ODU Hardware fault is cleared."
      ::= 111
gnLODUTxLevelInRangeTrap TRAP-TYPE
      ENTERPRISE  ceragon
      VARIABLES  {gnGenCfgTrapSeverity , gnGenCfgAlarmText , gnOduStatusTransmitLevel,gnGenCfgCLLI}
      DESCRIPTION
          "This Trap is sent every time a Local ODU TX signal is in range. "
      ::= 112

gnLODURxLevelInRangeTrap TRAP-TYPE
      ENTERPRISE  ceragon
      VARIABLES  {gnGenCfgTrapSeverity , gnGenCfgAlarmText , gnOduStatusReceiveLevel,gnGenCfgCLLI}
      DESCRIPTION
          "This Trap is sent every time a Local ODU RX signal is in range. "
      ::= 113

gnLODUNormalTempTrap TRAP-TYPE
      ENTERPRISE  ceragon
      VARIABLES  {gnGenCfgTrapSeverity , gnGenCfgAlarmText , gnOduStatusFahrenheitTemp,gnGenCfgCLLI}
      DESCRIPTION
          "This Trap is sent every time a Local ODU returns to normal temperature."
      ::= 114

gnLIDUPowerOkTrap TRAP-TYPE
      ENTERPRISE  ceragon
      VARIABLES  {gnGenCfgTrapSeverity , gnGenCfgAlarmText , gnGenStatDevicePowerSupply,gnGenCfgCLLI}
      DESCRIPTION
          "This Trap is sent every time a Local IDU Power fault is cleared."
      ::= 115


gnLCableOkTrap TRAP-TYPE
      ENTERPRISE  ceragon
      VARIABLES  {gnGenCfgTrapSeverity , gnGenCfgAlarmText , gnGenStatDeviceCable,gnGenCfgCLLI}
      DESCRIPTION
          "This Trap is sent every time a Local IDU-ODU cable fault is cleared."
      ::= 116

gnLModemOkTrap TRAP-TYPE
      ENTERPRISE  ceragon
      VARIABLES  {gnGenCfgTrapSeverity , gnGenCfgAlarmText , gnGenCfgCLLI}
      DESCRIPTION
          "This Trap is sent every time a Local Modem faults is cleared. "
      ::= 117


gnLIDUNormalTempTrap TRAP-TYPE
      ENTERPRISE  ceragon
      VARIABLES  {gnGenCfgTrapSeverity , gnGenCfgAlarmText , gnGenStatDeviceFahrenheitTemp,gnGenCfgCLLI}
      DESCRIPTION
          "This Trap is sent every time a Local IDU returns to normal temperature."
      ::= 118

gnLLoopbackOffTrap TRAP-TYPE
      ENTERPRISE  ceragon
      VARIABLES  {gnGenCfgTrapSeverity , gnGenCfgAlarmText , gnGenCfgCLLI}
      DESCRIPTION
          "This Trap is sent every time a Local Loopback is cleared."
      ::= 119

gnLRemoteCommOkTrap TRAP-TYPE
      ENTERPRISE  ceragon
      VARIABLES  {gnGenCfgTrapSeverity , gnGenCfgAlarmText , gnGenCfgCLLI}
      DESCRIPTION
          "This Trap is sent every time the remote communication is re-connected."
      ::=  120

gnLNoTestRunningTrap TRAP-TYPE
      ENTERPRISE  ceragon
      VARIABLES  {gnGenCfgTrapSeverity , gnGenCfgAlarmText , gnRstCfgTestActivate,gnGenCfgCLLI}
      DESCRIPTION
          "This Trap is sent every time a Local SDH/SONET test is cleared."
      ::= 121

gnLNoLOFTrap TRAP-TYPE
      ENTERPRISE  ceragon
      VARIABLES  {ifIndex, gnGenCfgTrapSeverity , gnGenCfgAlarmText , gnGenCfgCLLI}
      DESCRIPTION
          "This Trap is sent every time a Local Loss of Frame alarm is cleared."
      ::=  122

gnLNoLOSTrap TRAP-TYPE
      ENTERPRISE  ceragon
      VARIABLES  {ifIndex, gnGenCfgTrapSeverity , gnGenCfgAlarmText , gnGenCfgCLLI}
      DESCRIPTION
          "This Trap is sent every time a Local Loss of Signal alarm is cleared."
      ::=  123

gnLNoTIMTrap TRAP-TYPE
      ENTERPRISE  ceragon
      VARIABLES  {ifIndex, gnGenCfgTrapSeverity , gnGenCfgAlarmText , gnGenCfgCLLI}
      DESCRIPTION
          "This Trap is sent every time a Local Trace Identifier Mismatch alarm is cleared."
      ::= 124

gnLNoEXCTrap TRAP-TYPE
      ENTERPRISE  ceragon
      VARIABLES  {ifIndex, gnGenCfgTrapSeverity , gnGenCfgAlarmText , gnRstStatBERCur,gnGenCfgCLLI}
      DESCRIPTION
          "This Trap is sent every time a Local Excessive BER alarm is cleared. "
      ::= 125

gnLNoSDTrap TRAP-TYPE
      ENTERPRISE  ceragon
      VARIABLES  {ifIndex, gnGenCfgTrapSeverity , gnGenCfgAlarmText , gnRstStatBERCur,gnGenCfgCLLI}
      DESCRIPTION
          "This Trap is sent every time a Local Signal Degrade alarm is cleared."
      ::= 126

gnLNoAisTrap TRAP-TYPE
      ENTERPRISE  ceragon
      VARIABLES  {ifIndex, gnGenCfgTrapSeverity , gnGenCfgAlarmText , gnGenCfgCLLI}
      DESCRIPTION
          "This Trap is sent every time the local terminal stops receiving an Alarm Indication Signal (AIS)."
      ::= 127

gnLNoUnExpTrap TRAP-TYPE
      ENTERPRISE  ceragon
      VARIABLES  {ifIndex, gnGenCfgTrapSeverity , gnGenCfgAlarmText , gnGenCfgCLLI}
      DESCRIPTION
          "This Trap is sent every time a Local terminal stops receiving an unexpected signal."
      ::= 128

gnLNoLocTrap TRAP-TYPE
      ENTERPRISE  ceragon
      VARIABLES  {ifIndex, gnGenCfgTrapSeverity , gnGenCfgAlarmText , gnGenCfgCLLI}
      DESCRIPTION
          "This Trap is sent every time a Local Loss of Carrier (On the FE interfaces) alarm is cleared."
      ::= 129

---
gnLNoLopTrap TRAP-TYPE
      ENTERPRISE  ceragon
      VARIABLES  {ifIndex, gnGenCfgTrapSeverity , gnGenCfgAlarmText , gnGenCfgCLLI}
      DESCRIPTION
          "This Trap is sent every time a Local Loss of pointer alarm is cleared."
      ::= 130

gnLNoRdiTrap TRAP-TYPE
      ENTERPRISE  ceragon
      VARIABLES  {ifIndex, gnGenCfgTrapSeverity , gnGenCfgAlarmText , gnGenCfgCLLI}
      DESCRIPTION
          "This Trap is sent every time the local terminal stops receiving a Remote Defect Identifier signal (RDI)."
      ::= 131

gnLNoSlmTrap TRAP-TYPE
      ENTERPRISE  ceragon
      VARIABLES  {ifIndex, gnGenCfgTrapSeverity , gnGenCfgAlarmText , gnGenCfgCLLI}
      DESCRIPTION
          "This Trap is sent every time a Local Signal (Payload) Label Mismatch alarm is cleared. "
      ::= 132

gnLNoUnqTrap TRAP-TYPE
      ENTERPRISE  ceragon
      VARIABLES  {ifIndex, gnGenCfgTrapSeverity , gnGenCfgAlarmText , gnGenCfgCLLI}
      DESCRIPTION
          "This Trap is sent every time a Local terminal start receiving an equipped signal. "
      ::= 133

---

gnLExternalAlarm1OffTrap TRAP-TYPE
      ENTERPRISE  ceragon
      VARIABLES  {gnGenCfgTrapSeverity , gnGenCfgAlarmText , gnGenStatDeviceDryContact,gnGenCfgCLLI}
      DESCRIPTION
          "This Trap is sent every time a Local External alarm 1 is cleared. "
      ::= 134


gnLExternalAlarm2OffTrap TRAP-TYPE
      ENTERPRISE  ceragon
      VARIABLES  {gnGenCfgTrapSeverity , gnGenCfgAlarmText , gnGenStatDeviceDryContact,gnGenCfgCLLI}
      DESCRIPTION
          "This Trap is sent every time a Local External alarm 2 is cleared. "
      ::= 135


gnLExternalAlarm3OffTrap TRAP-TYPE
      ENTERPRISE  ceragon
      VARIABLES  {gnGenCfgTrapSeverity , gnGenCfgAlarmText , gnGenStatDeviceDryContact,gnGenCfgCLLI}
      DESCRIPTION
          "This Trap is sent every time a Local External alarm 3 is cleared. "
      ::= 136


gnLExternalAlarm4OffTrap TRAP-TYPE
      ENTERPRISE  ceragon
      VARIABLES  {gnGenCfgTrapSeverity , gnGenCfgAlarmText , gnGenStatDeviceDryContact,gnGenCfgCLLI}
      DESCRIPTION
          "This Trap is sent every time a Local External alarm 4 is cleared. "
      ::= 137


gnLExternalAlarm5OffTrap TRAP-TYPE
      ENTERPRISE  ceragon
      VARIABLES  {gnGenCfgTrapSeverity , gnGenCfgAlarmText , gnGenStatDeviceDryContact,gnGenCfgCLLI}
      DESCRIPTION
          "This Trap is sent every time a Local External alarm 5 is cleared. "
      ::= 138


gnLExternalAlarm6OffTrap TRAP-TYPE
      ENTERPRISE  ceragon
      VARIABLES  {gnGenCfgTrapSeverity , gnGenCfgAlarmText , gnGenStatDeviceDryContact,gnGenCfgCLLI}
      DESCRIPTION
          "This Trap is sent every time a Local External alarm 6 is cleared. "
      ::= 139


gnLExternalAlarm7OffTrap TRAP-TYPE
      ENTERPRISE  ceragon
      VARIABLES  {gnGenCfgTrapSeverity , gnGenCfgAlarmText , gnGenStatDeviceDryContact,gnGenCfgCLLI}
      DESCRIPTION
          "This Trap is sent every time a Local External alarm 7 is cleared. "
      ::= 140


gnLExternalAlarm8OffTrap TRAP-TYPE
      ENTERPRISE  ceragon
      VARIABLES  {gnGenCfgTrapSeverity , gnGenCfgAlarmText , gnGenStatDeviceDryContact,gnGenCfgCLLI}
      DESCRIPTION
          "This Trap is sent every time a Local External alarm 8 is cleared."
      ::= 141

gnLSystemOkTrap TRAP-TYPE
      ENTERPRISE  ceragon
      VARIABLES  {gnGenCfgTrapSeverity , gnGenCfgAlarmText , gnGenDrawerXInternalCommunication,gnGenCfgCLLI}
      DESCRIPTION
          "This Trap is sent every time a Local System fault is cleared."
      ::= 142

gnLTftpOkTrap TRAP-TYPE
      ENTERPRISE  ceragon
      VARIABLES  {gnGenCfgTrapSeverity , gnGenCfgAlarmText , gnGenCfgCLLI}
      DESCRIPTION
          "This Trap is sent every time a Local TFTP Download succeeded."
      ::= 143

gnLInternalDownloadOkTrap TRAP-TYPE
      ENTERPRISE  ceragon
      VARIABLES  {gnGenCfgTrapSeverity , gnGenCfgAlarmText , gnGenCfgCLLI}
      DESCRIPTION
          "This Trap is sent every time a Local internal Download succeeded."
      ::= 144

gnLIntralinkOkTrap TRAP-TYPE
      ENTERPRISE  ceragon
      VARIABLES  {gnGenCfgTrapSeverity , gnGenCfgAlarmText , gnGenCfgCLLI}
      DESCRIPTION
          "This Trap is sent every time a Local intra-link download succeeded."
      ::= 145

gnLNoConfMismatchTrap TRAP-TYPE
      ENTERPRISE  ceragon
      VARIABLES  {gnGenCfgTrapSeverity , gnGenCfgAlarmText , gnGenCfgCLLI}
      DESCRIPTION
          "This Trap is sent every time a Local configuration mismatch fault is cleared."
      ::= 146

gnLProtectSwitchOkTrap TRAP-TYPE
     ENTERPRISE  ceragon
     VARIABLES  {gnGenCfgTrapSeverity , gnGenCfgAlarmText , gnGenCfgCLLI}
     DESCRIPTION
         "Never sent. "
     ::= 147

gnLProtectCableOkTrap TRAP-TYPE
      ENTERPRISE  ceragon
      VARIABLES  {gnGenCfgTrapSeverity , gnGenCfgAlarmText , gnGenCfgCLLI}
      DESCRIPTION
          "This Trap is sent every time a Local protection cable fault is cleared."
      ::= 148

gnLLomOkTrap TRAP-TYPE
      ENTERPRISE  ceragon
      VARIABLES  {ifIndex, gnGenCfgTrapSeverity , gnGenCfgAlarmText , gnGenCfgCLLI}
      DESCRIPTION
          "This Trap is sent every time a Local Loss of Multi-frame alarm is cleared."
      ::= 150

gnLHitlessProblemOKTrap TRAP-TYPE
      ENTERPRISE  ceragon
      VARIABLES  {gnGenCfgTrapSeverity , gnGenCfgAlarmText , gnGenCfgCLLI}
      DESCRIPTION
          "This Trap is sent every time a Local Hitless fault is cleared."
      ::= 151

gnLHitlessRadioLofOKTrap TRAP-TYPE
      ENTERPRISE  ceragon
      VARIABLES  {gnGenCfgTrapSeverity , gnGenCfgAlarmText , gnGenCfgCLLI}
      DESCRIPTION
          "This Trap is sent every time a Local Hitless RadioLOF fault is cleared."
      ::= 152

gnLHitlessCableDisconnectOKTrap TRAP-TYPE
      ENTERPRISE  ceragon
      VARIABLES  {gnGenCfgTrapSeverity , gnGenCfgAlarmText , gnGenCfgCLLI}
      DESCRIPTION
          "This Trap is sent every time a Local Hitless cable fault is cleared."
      ::= 153

gnLPamOkTrap TRAP-TYPE
      ENTERPRISE  ceragon
      VARIABLES  {ifIndex, gnGenCfgTrapSeverity , gnGenCfgAlarmText , gnGenCfgCLLI}
      DESCRIPTION
          "This Trap is sent when system in MSP Protection Architecture Mismatch."
      ::=  154

gnLScmOkTrap TRAP-TYPE
      ENTERPRISE  ceragon
      VARIABLES  {ifIndex, gnGenCfgTrapSeverity , gnGenCfgAlarmText , gnGenCfgCLLI}
      DESCRIPTION
                  "This Trap is sent when there is a MSP Selector Channel Mismatch (K1,K2)."
      ::=  155

gnLInvOkTrap TRAP-TYPE
      ENTERPRISE  ceragon
      VARIABLES  {ifIndex, gnGenCfgTrapSeverity , gnGenCfgAlarmText , gnGenCfgCLLI}
      DESCRIPTION
          "This Trap indicates that the received K1 byte is invalid (MSP)."
      ::=  156

gnLInbandOkTrap TRAP-TYPE
      ENTERPRISE  ceragon
      VARIABLES  {ifIndex, gnGenCfgTrapSeverity , gnGenCfgAlarmText , gnGenCfgCLLI}
      DESCRIPTION
          "This Trap is sent when the Inband PPP link goes up."
      ::=  157

gnWSNoLOSTrap TRAP-TYPE
      ENTERPRISE  ceragon
      VARIABLES  { gnGenCfgTrapSeverity , gnGenCfgAlarmText , gnGenCfgCLLI}
      DESCRIPTION
          "This Trap is sent when the Wayside channel is in LOS state."
      ::=  158

gnODUtoODUCableOkTrap TRAP-TYPE
      ENTERPRISE  ceragon
      VARIABLES  {gnGenCfgTrapSeverity , gnGenCfgAlarmText , gnGenCfgCLLI}
      DESCRIPTION
          "This Trap is sent when there is a problem with the ODU to ODU cable - for XPIC topology only."
      ::=  159

gnSignalReceivedFromODUTrap TRAP-TYPE
      ENTERPRISE  ceragon
      VARIABLES  {gnGenCfgTrapSeverity , gnGenCfgAlarmText , gnGenCfgCLLI}
      DESCRIPTION
          "This Trap is sent when a signal is received from the ODU."
      ::=  160

gnProtectionLockoutClearededTrap TRAP-TYPE
      ENTERPRISE  ceragon
      VARIABLES  {gnGenCfgTrapSeverity , gnGenCfgAlarmText , gnGenCfgCLLI}
      DESCRIPTION
          " This Trap is sent when Protection lockout is cleared."
      ::=  161

gnRFUPowerFailureClearedTrap TRAP-TYPE
      ENTERPRISE  ceragon
      VARIABLES  {gnGenCfgTrapSeverity , gnGenCfgAlarmText , gnGenCfgCLLI}
      DESCRIPTION
          "This Trap is sent in case of 12V/-5V/1.5V/6V/Vdrain power supply failure is cleared."
      ::=  162

gnRFURxLevelPathOutOfRangeClearedTrap TRAP-TYPE
      ENTERPRISE  ceragon
      VARIABLES  {gnGenCfgTrapSeverity , gnGenCfgAlarmText , gnGenCfgCLLI}
      DESCRIPTION
          "This Trap is sent in case of RSL of Main/Diversity channel is not very low ."
      ::=  163

gnRFUExtremeTemperatureClearedTrap TRAP-TYPE
      ENTERPRISE  ceragon
      VARIABLES  {gnGenCfgTrapSeverity , gnGenCfgAlarmText , gnGenCfgCLLI}
      DESCRIPTION
          "This Trap is sent in case of RFU temperature is not too high/low ."
      ::=  164

gnRFUFanFailureClearedTrap TRAP-TYPE
      ENTERPRISE  ceragon
      VARIABLES  {gnGenCfgTrapSeverity , gnGenCfgAlarmText , gnGenCfgCLLI}
      DESCRIPTION
          "This Trap is sent when fan failure is cleared ."
      ::=  165

gnLowSignalToRFUClearedTrap TRAP-TYPE
      ENTERPRISE  ceragon
      VARIABLES  {gnGenCfgTrapSeverity , gnGenCfgAlarmText , gnGenCfgCLLI}
      DESCRIPTION
          "This Trap is sent in case of not low IDM signal reception ."
      ::=  166

gnRFUXPICClockFailureClearedTrap TRAP-TYPE
      ENTERPRISE  ceragon
      VARIABLES  {gnGenCfgTrapSeverity , gnGenCfgAlarmText , gnGenCfgCLLI}
      DESCRIPTION
          "This Trap is sent in case of XPIC clock failure is cleared ."
      ::=  167

gnRFUDelayCalibrationFailure1ClearedTrap TRAP-TYPE
      ENTERPRISE  ceragon
      VARIABLES  {gnGenCfgTrapSeverity , gnGenCfgAlarmText , gnGenCfgCLLI}
      DESCRIPTION
          "This Trap is sent if RX AGC is locked ."
      ::=  168

gnRFUDelayCalibrationFailure2ClearedTrap TRAP-TYPE
      ENTERPRISE  ceragon
      VARIABLES  {gnGenCfgTrapSeverity , gnGenCfgAlarmText , gnGenCfgCLLI}
      DESCRIPTION
          "This Trap is sent if calibration can be done ."
      ::=  169

gnLSFPOkTrap TRAP-TYPE
      ENTERPRISE  ceragon
      VARIABLES  {ifIndex, gnGenCfgTrapSeverity , gnGenCfgAlarmText , gnGenCfgCLLI}
      DESCRIPTION
          "This Trap is sent every time a Gigabit ethernet SFP fault clears."
      ::=  170

gnEncryptionFaultClearedTrap TRAP-TYPE
      ENTERPRISE  ceragon
      VARIABLES  {ifIndex, gnGenCfgTrapSeverity , gnGenCfgAlarmText , gnGenCfgCLLI}
      DESCRIPTION
          "This Trap is sent every time a Encryption fault clears."
      ::=  171

gnEncryptionSyncLosClearedTrap TRAP-TYPE
      ENTERPRISE  ceragon
      VARIABLES  {ifIndex, gnGenCfgTrapSeverity , gnGenCfgAlarmText , gnGenCfgCLLI}
      DESCRIPTION
          "This Trap is sent every time a Encryption synchronization loss fault clears."
      ::=  172

gnEncryptionKepTimoutCleared TRAP-TYPE
      ENTERPRISE  ceragon
      VARIABLES  {ifIndex, gnGenCfgTrapSeverity , gnGenCfgAlarmText , gnGenCfgCLLI}
      DESCRIPTION
          "This Trap is sent every time a Encryption KEP timout fault clears."
      ::=  173

gnEncryptionSkTimerElapsedCleared TRAP-TYPE
      ENTERPRISE  ceragon
      VARIABLES  {ifIndex, gnGenCfgTrapSeverity , gnGenCfgAlarmText , gnGenCfgCLLI}
      DESCRIPTION
          "This Trap is sent every time a encryption Encryption Session Key Timer elapsed fault clears."
      ::=  174

gnEncryptionPowerUpSelfTestFailCleared TRAP-TYPE
      ENTERPRISE  ceragon
      VARIABLES  {ifIndex, gnGenCfgTrapSeverity , gnGenCfgAlarmText , gnGenCfgCLLI}
      DESCRIPTION
          "This Trap is sent every time a Encryption Power Up Self Test fault clears."
      ::=  175

gnEncryptionConditionalTestFailCleared TRAP-TYPE
      ENTERPRISE  ceragon
      VARIABLES  {ifIndex, gnGenCfgTrapSeverity , gnGenCfgAlarmText , gnGenCfgCLLI}
      DESCRIPTION
          "This Trap is sent every time a Encryption Conditional Test fault clears."
      ::=  176

gnEncryptionWillTurnOffOnNextRestCleared TRAP-TYPE
      ENTERPRISE  ceragon
      VARIABLES  {ifIndex, gnGenCfgTrapSeverity , gnGenCfgAlarmText , gnGenCfgCLLI}
      DESCRIPTION
          "This Trap is sent every time a Encryption will be turned off on the next reset clears."
      ::=  177

gnEncryptionEventReportCleared TRAP-TYPE
      ENTERPRISE  ceragon
      VARIABLES  {ifIndex, gnGenCfgTrapSeverity , gnGenCfgAlarmText , gnGenCfgCLLI}
      DESCRIPTION
          "This Trap is sent every time a Encryption event report fault clears."
      ::=  178

gnEncryptionTechCardWasDetectedCleared TRAP-TYPE
      ENTERPRISE  ceragon
      VARIABLES  {ifIndex, gnGenCfgTrapSeverity , gnGenCfgAlarmText , gnGenCfgCLLI}
      DESCRIPTION
          "This Trap is sent every time a  Encryption Technician card is detected clears."
      ::=  179

gnAdminPasswordInDefaultStateCleared TRAP-TYPE
      ENTERPRISE  ceragon
      VARIABLES  {ifIndex, gnGenCfgTrapSeverity , gnGenCfgAlarmText , gnGenCfgCLLI}
      DESCRIPTION
          "This Trap is sent every time a admin password is in default state clears."
      ::=  180

gnLinkGroupingProtectionFaultClearedTrap TRAP-TYPE
      ENTERPRISE  ceragon
      VARIABLES  {gnGenCfgTrapSeverity , gnGenCfgAlarmText , gnGenCfgCLLI}
      DESCRIPTION
          "This Trap is sent in case the Link Grouping Protection Fault clears."
      ::=  181

gnLossOfProtectionClearedTrap TRAP-TYPE
      ENTERPRISE  ceragon
      VARIABLES  {gnGenCfgTrapSeverity , gnGenCfgAlarmText , gnGenCfgCLLI}
      DESCRIPTION
          "This Trap is sent in case the Loss of Protection clears."
      ::=  182

gnTempLicenseClearedTrap TRAP-TYPE
      ENTERPRISE  ceragon
      VARIABLES  {gnGenCfgTrapSeverity , gnGenCfgAlarmText , gnGenCfgCLLI}
      DESCRIPTION
          "This Trap is sent in case the Temp License Enable clears."
      ::=  183

gnMUXCfgXTempLicenseClearedTrap TRAP-TYPE
      ENTERPRISE  ceragon
      VARIABLES  {gnGenCfgTrapSeverity , gnGenCfgAlarmText , gnGenCfgCLLI}
      DESCRIPTION
          "This Trap is sent in case the Temp License Enable clears."
      ::=  184


-- ********************

gnRODUPowerFailTrap TRAP-TYPE
      ENTERPRISE  ceragon
      VARIABLES  {gnGenCfgTrapSeverity , gnGenCfgAlarmText , gnOduStatusPowerSupply,gnGenCfgCLLI}
      DESCRIPTION
          "This Trap is sent every time a Remote ODU Power fault occurs."
      ::= 210

gnRODUSynthUnLockTrap TRAP-TYPE
      ENTERPRISE  ceragon
      VARIABLES  {gnGenCfgTrapSeverity , gnGenCfgAlarmText , gnOduStatusSynthesizerVCOLock,gnGenCfgCLLI}
      DESCRIPTION
          "This Trap is sent every time a Remote ODU Hardware fault occurs ."
      ::= 211

gnRODUTxLevelOutOfRangeTrap TRAP-TYPE
      ENTERPRISE  ceragon
      VARIABLES  {gnGenCfgTrapSeverity , gnGenCfgAlarmText , gnOduStatusTransmitLevel,gnGenCfgCLLI}
      DESCRIPTION
          "This Trap is sent every time a Remote ODU TX signal is out of range."
      ::= 212

gnRODURxLevelOutOfRangeTrap TRAP-TYPE
      ENTERPRISE  ceragon
      VARIABLES  {gnGenCfgTrapSeverity , gnGenCfgAlarmText , gnOduStatusReceiveLevel,gnGenCfgCLLI}
      DESCRIPTION
          "This Trap is sent every time a Remote ODU RX signal is out of range."
      ::= 213

gnRODUExtremeTempTrap TRAP-TYPE
      ENTERPRISE  ceragon
      VARIABLES  {gnGenCfgTrapSeverity , gnGenCfgAlarmText , gnOduStatusFahrenheitTemp,gnGenCfgCLLI}
      DESCRIPTION
          "This Trap is sent every time a Remote ODU extreme temperature event occurs."
      ::= 214

gnRIDUPowerFailTrap TRAP-TYPE
      ENTERPRISE  ceragon
      VARIABLES  {gnGenCfgTrapSeverity , gnGenCfgAlarmText , gnGenStatDevicePowerSupply,gnGenCfgCLLI}
      DESCRIPTION
          "This Trap is sent every time a Remote IDU Power fault occurs."
      ::= 215

gnRCableFaultTrap TRAP-TYPE
      ENTERPRISE  ceragon
      VARIABLES  {gnGenCfgTrapSeverity , gnGenCfgAlarmText , gnGenStatDeviceCable,gnGenCfgCLLI}
      DESCRIPTION
          "This Trap is sent every time a Remote IDU-ODU cable fault occurs."
      ::= 216

gnRModemFailTrap TRAP-TYPE
      ENTERPRISE  ceragon
      VARIABLES  {gnGenCfgTrapSeverity , gnGenCfgAlarmText , gnGenCfgCLLI}
      DESCRIPTION
          "This Trap is sent every time a Remote Modem faults occurs."
      ::= 217


gnRIDUExtremeTempTrap TRAP-TYPE
      ENTERPRISE  ceragon
      VARIABLES  {gnGenCfgTrapSeverity , gnGenCfgAlarmText , gnGenStatDeviceFahrenheitTemp,gnGenCfgCLLI}
      DESCRIPTION
          "This Trap is sent every time a Remote IDU extreme temperature event occurs."
      ::= 218

gnRLoopbackOnTrap TRAP-TYPE
      ENTERPRISE  ceragon
      VARIABLES  {gnGenCfgTrapSeverity , gnGenCfgAlarmText , gnGenCfgCLLI}
      DESCRIPTION
          "This Trap is sent every time a Remote Loopback is activated."
      ::= 219

gnRRemoteCommFaultTrap TRAP-TYPE
      ENTERPRISE  ceragon
      VARIABLES  {gnGenCfgTrapSeverity , gnGenCfgAlarmText , gnGenCfgCLLI}
      DESCRIPTION
          "This Trap is sent every time the remote communication is disconnected."
      ::= 220

gnRTestRunningTrap TRAP-TYPE
      ENTERPRISE  ceragon
      VARIABLES  {gnGenCfgTrapSeverity , gnGenCfgAlarmText , gnRstCfgTestActivate,gnGenCfgCLLI}
      DESCRIPTION
          "This Trap is sent every time a Remote SDH/SONET test is activated."
      ::=  221

gnRLOFTrap TRAP-TYPE
      ENTERPRISE  ceragon
      VARIABLES  {ifIndex, gnGenCfgTrapSeverity , gnGenCfgAlarmText , gnGenCfgCLLI}
      DESCRIPTION
          "This Trap is sent every time a Remote Loss of Frame alarm occurs."
      ::=  222

gnRLOSTrap TRAP-TYPE
      ENTERPRISE  ceragon
      VARIABLES  {ifIndex, gnGenCfgTrapSeverity , gnGenCfgAlarmText , gnGenCfgCLLI}
      DESCRIPTION
          "This Trap is sent every time a Remote Loss of signal alarm occurs."
      ::=  223

gnRTIMTrap TRAP-TYPE
      ENTERPRISE  ceragon
      VARIABLES  {ifIndex, gnGenCfgTrapSeverity , gnGenCfgAlarmText , gnGenCfgCLLI}
      DESCRIPTION
          "This Trap is sent every time a Remote Trace Identifier Mismatch alarm occurs."
      ::=  224

gnREXCTrap TRAP-TYPE
      ENTERPRISE  ceragon
      VARIABLES  {ifIndex, gnGenCfgTrapSeverity , gnGenCfgAlarmText , gnRstStatBERCur,gnGenCfgCLLI}
      DESCRIPTION
          "This Trap is sent every time a Remote Excessive BER alarm is raised."
      ::=  225

gnRSDTrap TRAP-TYPE
      ENTERPRISE  ceragon
      VARIABLES  {ifIndex, gnGenCfgTrapSeverity , gnGenCfgAlarmText , gnRstStatBERCur,gnGenCfgCLLI}
      DESCRIPTION
          "This Trap is sent every time a Remote Signal Degrade alarm is raised."
      ::=  226

gnRAisTrap TRAP-TYPE
      ENTERPRISE  ceragon
      VARIABLES  {ifIndex, gnGenCfgTrapSeverity , gnGenCfgAlarmText , gnGenCfgCLLI}
      DESCRIPTION
          "This Trap is sent every time the Remote terminal receives an Alarm Indication Signal (AIS)."
      ::=  227

gnRUnExpTrap TRAP-TYPE
      ENTERPRISE  ceragon
      VARIABLES  {ifIndex, gnGenCfgTrapSeverity , gnGenCfgAlarmText , gnGenCfgCLLI}
      DESCRIPTION
          "This Trap is sent every time a Remote terminal receives an unexpected signal."
      ::=  228

gnRLocTrap TRAP-TYPE
      ENTERPRISE  ceragon
      VARIABLES  {ifIndex, gnGenCfgTrapSeverity , gnGenCfgAlarmText , gnGenCfgCLLI}
      DESCRIPTION
          "This Trap is sent every time a Remote Loss of Carrier (On the FE interfaces) alarm occurs."
      ::=   229

---
gnRLopTrap TRAP-TYPE
      ENTERPRISE  ceragon
      VARIABLES  {ifIndex, gnGenCfgTrapSeverity , gnGenCfgAlarmText , gnGenCfgCLLI}
      DESCRIPTION
          "This Trap is sent every time a Remote Loss of pointer alarm occurs."
      ::=         230

gnRRdiTrap TRAP-TYPE
      ENTERPRISE  ceragon
      VARIABLES  {ifIndex, gnGenCfgTrapSeverity , gnGenCfgAlarmText , gnGenCfgCLLI}
      DESCRIPTION
          "This Trap is sent every time the Remote terminal receives a Remote Defect Identifier signal (RDI)."
      ::=         231

gnRSlmTrap TRAP-TYPE
      ENTERPRISE  ceragon
      VARIABLES  {ifIndex, gnGenCfgTrapSeverity , gnGenCfgAlarmText , gnGenCfgCLLI}
      DESCRIPTION
          "This Trap is sent every time a Remote Signal (Payload) Label Mismatch alarm occurs."
      ::=         232

gnRUnqTrap TRAP-TYPE
      ENTERPRISE  ceragon
      VARIABLES  {ifIndex, gnGenCfgTrapSeverity , gnGenCfgAlarmText , gnGenCfgCLLI}
      DESCRIPTION
          "This Trap is sent every time a Remote unequipped signal is received."
      ::=         233

---


gnRExternalAlarm1OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 1 is raised."
      ::=  234

gnRExternalAlarm2OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 2 is raised."
      ::=  235

gnRExternalAlarm3OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 3 is raised."
      ::=  236

gnRExternalAlarm4OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 4 is raised."
      ::=  237

gnRExternalAlarm5OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 5 is raised."
      ::=  238

gnRExternalAlarm6OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 6 is raised."
      ::=  239

gnRExternalAlarm7OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 7 is raised."
      ::=  240

gnRExternalAlarm8OnTrap TRAP-TYPE
      ENTERPRISE  ceragon
      VARIABLES  {gnGenCfgTrapSeverity , gnGenCfgAlarmText , gnGenStatDeviceDryContact,gnGenCfgCLLI}
      DESCRIPTION
          "This Trap is sent every time a Remote External alarm 8 is raised."
      ::=  241

gnRSystemFaultTrap TRAP-TYPE
      ENTERPRISE  ceragon
      VARIABLES  {gnGenCfgTrapSeverity , gnGenCfgAlarmText , gnGenStatInternalCommunication,gnGenCfgCLLI}
      DESCRIPTION
          "This Trap is sent every time a Remote System fault occurs."
      ::=  242

gnRTftpFaultTrap TRAP-TYPE
      ENTERPRISE  ceragon
      VARIABLES  {gnGenCfgTrapSeverity , gnGenCfgAlarmText , gnGenCfgCLLI}
      DESCRIPTION
          "This Trap is sent every time a Remote TFTP Download fails."
      ::= 243

gnRInternalDownloadFaultTrap TRAP-TYPE
      ENTERPRISE  ceragon
      VARIABLES  {gnGenCfgTrapSeverity , gnGenCfgAlarmText , gnGenCfgCLLI}
      DESCRIPTION
          "This Trap is sent every time a Remote internal Download fails."
      ::= 244

gnRIntralinkFaultTrap TRAP-TYPE
      ENTERPRISE  ceragon
      VARIABLES  {gnGenCfgTrapSeverity , gnGenCfgAlarmText , gnGenCfgCLLI}
      DESCRIPTION
          "This Trap is sent every time a Remote intra-link download fails."
      ::= 245

gnRConfMismatchTrap TRAP-TYPE
      ENTERPRISE  ceragon
      VARIABLES  {gnGenCfgTrapSeverity , gnGenCfgAlarmText , gnGenCfgCLLI}
      DESCRIPTION
          "This Trap is sent every time a Remote configuration mismatch fault occurs."
      ::= 246

gnRProtectSwitchFaultTrap TRAP-TYPE
      ENTERPRISE  ceragon
      VARIABLES  {gnGenCfgTrapSeverity , gnGenCfgAlarmText , gnGenCfgCLLI}
      DESCRIPTION
          "This Trap is sent every time a Remote Protection fault is raised."
      ::= 247

gnRProtectCableFaultTrap TRAP-TYPE
      ENTERPRISE  ceragon
      VARIABLES  {gnGenCfgTrapSeverity , gnGenCfgAlarmText , gnGenCfgCLLI}
      DESCRIPTION
          "This Trap is sent every time a Remote protection cable fault is raised."
      ::= 248

gnRHeartBeatTrap  TRAP-TYPE
      ENTERPRISE  ceragon
      VARIABLES  {gnGenCfgTrapSeverity , gnGenCfgAlarmText , gnGenCfgCLLI}
      DESCRIPTION
          "This Trap is a periodic heart beat trap."
      ::= 249

gnRLomTrap TRAP-TYPE
      ENTERPRISE  ceragon
      VARIABLES  {ifIndex, gnGenCfgTrapSeverity , gnGenCfgAlarmText , gnGenCfgCLLI}
      DESCRIPTION
          "This Trap is sent every time a Remote Loss of Multi-frame alarm occurs."
      ::= 250

--gnRHitlessProblemTrap TRAP-TYPE
--      ENTERPRISE  ceragon
--      VARIABLES  {gnGenCfgTrapSeverity , gnGenCfgAlarmText , gnGenCfgCLLI}
--      DESCRIPTION
--          "This Trap is sent every time a Remote Hitless fault occurs."
--     ::= 251

gnRHitlessRadioLofTrap TRAP-TYPE
      ENTERPRISE  ceragon
      VARIABLES  {gnGenCfgTrapSeverity , gnGenCfgAlarmText , gnGenCfgCLLI}
      DESCRIPTION
          "This Trap is sent every time a Remote Hitless RadioLOF fault occurs."
      ::= 252

gnRHitlessCableDisconnectTrap TRAP-TYPE
      ENTERPRISE  ceragon
      VARIABLES  {gnGenCfgTrapSeverity , gnGenCfgAlarmText , gnGenCfgCLLI}
      DESCRIPTION
          "This Trap is sent every time a Remote Hitless cable fault is raised."
      ::= 253


--                 skip 254-256 (MSP PAM, SCM, INV)
--                 skip 257                 (Inband)





gnRODUPowerOkTrap TRAP-TYPE
      ENTERPRISE  ceragon
      VARIABLES  {gnGenCfgTrapSeverity , gnGenCfgAlarmText , gnOduStatusPowerSupply,gnGenCfgCLLI}
      DESCRIPTION
          "This Trap is sent every time a Remote ODU Power fault cleared."
      ::= 310

gnRODUSynthLockTrap TRAP-TYPE
      ENTERPRISE  ceragon
      VARIABLES  {gnGenCfgTrapSeverity , gnGenCfgAlarmText , gnOduStatusSynthesizerVCOLock,gnGenCfgCLLI}
      DESCRIPTION
          "This Trap is sent every time a Remote ODU Hardware fault is cleared."
      ::= 311

gnRODUTxLevelInRangeTrap TRAP-TYPE
      ENTERPRISE  ceragon
      VARIABLES  {gnGenCfgTrapSeverity , gnGenCfgAlarmText , gnOduStatusTransmitLevel,gnGenCfgCLLI}
      DESCRIPTION
          "This Trap is sent every time a Remote ODU TX signal is in range."
      ::= 312

gnRODURxLevelInRangeTrap TRAP-TYPE
      ENTERPRISE  ceragon
      VARIABLES  {gnGenCfgTrapSeverity , gnGenCfgAlarmText , gnOduStatusReceiveLevel,gnGenCfgCLLI}
      DESCRIPTION
          "This Trap is sent every time a Remote ODU RX signal is in range."
      ::= 313

gnRODUNormalTempTrap TRAP-TYPE
      ENTERPRISE  ceragon
      VARIABLES  {gnGenCfgTrapSeverity , gnGenCfgAlarmText , gnOduStatusFahrenheitTemp,gnGenCfgCLLI}
      DESCRIPTION
          "This Trap is sent every time a Remote ODU returns to normal temperature."
      ::= 314

gnRIDUPowerOkTrap TRAP-TYPE
      ENTERPRISE  ceragon
      VARIABLES  {gnGenCfgTrapSeverity , gnGenCfgAlarmText , gnGenStatDevicePowerSupply,gnGenCfgCLLI}
      DESCRIPTION
          "This Trap is sent every time a Remote IDU Power fault is cleared."
      ::= 315


gnRCableOkTrap TRAP-TYPE
      ENTERPRISE  ceragon
      VARIABLES  {gnGenCfgTrapSeverity , gnGenCfgAlarmText , gnGenStatDeviceCable,gnGenCfgCLLI}
      DESCRIPTION
          "This Trap is sent every time a Remote IDU-ODU cable fault is cleared."
      ::= 316

gnRModemOkTrap TRAP-TYPE
      ENTERPRISE  ceragon
      VARIABLES  {gnGenCfgTrapSeverity , gnGenCfgAlarmText , gnGenCfgCLLI}
      DESCRIPTION
          "This Trap is sent every time a Remote Modem faults is cleared."
      ::= 317


gnRIDUNormalTempTrap TRAP-TYPE
      ENTERPRISE  ceragon
      VARIABLES  {gnGenCfgTrapSeverity , gnGenCfgAlarmText , gnGenStatDeviceFahrenheitTemp,gnGenCfgCLLI}
      DESCRIPTION
          "This Trap is sent every time a Remote IDU returns to normal temperature."
      ::= 318

gnRLoopbackOffTrap TRAP-TYPE
      ENTERPRISE  ceragon
      VARIABLES  {gnGenCfgTrapSeverity , gnGenCfgAlarmText , gnGenCfgCLLI}
      DESCRIPTION
          "This Trap is sent every time a Remote Loopback is cleared."
      ::=  319

gnRRemoteCommOkTrap TRAP-TYPE
      ENTERPRISE  ceragon
      VARIABLES  {gnGenCfgTrapSeverity , gnGenCfgAlarmText , gnGenCfgCLLI}
      DESCRIPTION
          "This Trap is sent every time the remote communication is re-connected."
      ::=  320

gnRNoTestRunningTrap TRAP-TYPE
      ENTERPRISE  ceragon
      VARIABLES  {gnGenCfgTrapSeverity , gnGenCfgAlarmText , gnRstCfgTestActivate,gnGenCfgCLLI}
      DESCRIPTION
          "This Trap is sent every time a Remote SDH/SONET test is cleared."
      ::=  321

gnRNoLOFTrap TRAP-TYPE
      ENTERPRISE  ceragon
      VARIABLES  {ifIndex, gnGenCfgTrapSeverity , gnGenCfgAlarmText , gnGenCfgCLLI}
      DESCRIPTION
          "This Trap is sent every time a Remote Loss of Frame alarm is cleared."
      ::= 322

gnRNoLOSTrap TRAP-TYPE
      ENTERPRISE  ceragon
      VARIABLES  {ifIndex, gnGenCfgTrapSeverity , gnGenCfgAlarmText , gnGenCfgCLLI}
      DESCRIPTION
          "This Trap is sent every time a Remote Loss of Signal alarm is cleared."
      ::= 323

gnRNoTIMTrap TRAP-TYPE
      ENTERPRISE  ceragon
      VARIABLES  {ifIndex, gnGenCfgTrapSeverity , gnGenCfgAlarmText , gnGenCfgCLLI}
      DESCRIPTION
          "This Trap is sent every time a Remote Trace Identifier Mismatch alarm is cleared."
      ::= 324

gnRNoEXCTrap TRAP-TYPE
      ENTERPRISE  ceragon
      VARIABLES  {ifIndex, gnGenCfgTrapSeverity , gnGenCfgAlarmText , gnRstStatBERCur,gnGenCfgCLLI}
      DESCRIPTION
          "This Trap is sent every time a Remote Excessive BER alarm is cleared."
      ::=  325

gnRNoSDTrap TRAP-TYPE
      ENTERPRISE  ceragon
      VARIABLES  {ifIndex, gnGenCfgTrapSeverity , gnGenCfgAlarmText , gnRstStatBERCur,gnGenCfgCLLI}
      DESCRIPTION
          "This Trap is sent every time a Remote Signal Degrade alarm is cleared."
      ::=  326


gnRNoAisTrap TRAP-TYPE
      ENTERPRISE  ceragon
      VARIABLES  {ifIndex, gnGenCfgTrapSeverity , gnGenCfgAlarmText , gnGenCfgCLLI}
      DESCRIPTION
          "This Trap is sent every time the Remote terminal stops receiving an Alarm Indication Signal (AIS)."
      ::=  327

gnRNoUnExpTrap TRAP-TYPE
      ENTERPRISE  ceragon
      VARIABLES  {ifIndex, gnGenCfgTrapSeverity , gnGenCfgAlarmText , gnGenCfgCLLI}
      DESCRIPTION
          "This Trap is sent every time a Remote terminal stops receiving an unexpected signal."
      ::=  328

gnRNoLocTrap TRAP-TYPE
      ENTERPRISE  ceragon
      VARIABLES  {ifIndex, gnGenCfgTrapSeverity , gnGenCfgAlarmText , gnGenCfgCLLI}
      DESCRIPTION
          "This Trap is sent every time a Remote Loss of Carrier (on the FE interfaces) alarm is cleared."
      ::=  329

---
gnRNoLopTrap TRAP-TYPE
      ENTERPRISE  ceragon
      VARIABLES  {ifIndex, gnGenCfgTrapSeverity , gnGenCfgAlarmText , gnGenCfgCLLI}
      DESCRIPTION
          "This Trap is sent every time a Remote Loss of pointer alarm is cleared."
      ::=         330

gnRNoRdiTrap TRAP-TYPE
      ENTERPRISE  ceragon
      VARIABLES  {ifIndex, gnGenCfgTrapSeverity , gnGenCfgAlarmText , gnGenCfgCLLI}
      DESCRIPTION
          "This Trap is sent every time the Remote terminal stops receiving a Remote Defect Identifier signal (RDI)."
      ::=         331

gnRNoSlmTrap TRAP-TYPE
      ENTERPRISE  ceragon
      VARIABLES  {ifIndex, gnGenCfgTrapSeverity , gnGenCfgAlarmText , gnGenCfgCLLI}
      DESCRIPTION
          "This Trap is sent every time a Remote Signal (Payload) Label Mismatch alarm is cleared."
      ::=         332

gnRNoUnqTrap TRAP-TYPE
      ENTERPRISE  ceragon
      VARIABLES  {ifIndex, gnGenCfgTrapSeverity , gnGenCfgAlarmText , gnGenCfgCLLI}
      DESCRIPTION
          "This Trap is sent every time a Remote terminal start receiving an equipped signal."
      ::=         333

---

gnRExternalAlarm1OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 1 is cleared."
      ::= 334

gnRExternalAlarm2OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 2 is cleared."
      ::= 335

gnRExternalAlarm3OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 3 is cleared."
      ::= 336

gnRExternalAlarm4OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 4 is cleared."
      ::= 337

gnRExternalAlarm5OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 5 is cleared."
      ::= 338

gnRExternalAlarm6OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 6 is cleared."
      ::= 339

gnRExternalAlarm7OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 7 is cleared."
      ::= 340

gnRExternalAlarm8OffTrap TRAP-TYPE
      ENTERPRISE  ceragon
      VARIABLES  {gnGenCfgTrapSeverity , gnGenCfgAlarmText , gnGenStatDeviceDryContact,gnGenCfgCLLI}
      DESCRIPTION
          "This Trap is sent every time a Remote External alarm 8 is cleared."
      ::= 341

gnRSystemOkTrap TRAP-TYPE
      ENTERPRISE  ceragon
      VARIABLES  {gnGenCfgTrapSeverity , gnGenCfgAlarmText , gnGenStatInternalCommunication,gnGenCfgCLLI}
      DESCRIPTION
          "This Trap is sent every time a Remote System fault is cleared."
      ::= 342

gnRTftpOkTrap TRAP-TYPE
      ENTERPRISE  ceragon
      VARIABLES  {gnGenCfgTrapSeverity , gnGenCfgAlarmText , gnGenCfgCLLI}
      DESCRIPTION
          "This Trap is sent every time a Remote TFTP Download succeeded."
      ::= 343

gnRInternalDownloadOkTrap TRAP-TYPE
      ENTERPRISE  ceragon
      VARIABLES  {gnGenCfgTrapSeverity , gnGenCfgAlarmText , gnGenCfgCLLI}
      DESCRIPTION
          "This Trap is sent every time a Remoteinternal Download succeeded."
      ::= 344

gnRIntralinkOkTrap TRAP-TYPE
      ENTERPRISE  ceragon
      VARIABLES  {gnGenCfgTrapSeverity , gnGenCfgAlarmText , gnGenCfgCLLI}
      DESCRIPTION
          "This Trap is sent every time a Remote intra-link download succeeded."
      ::= 345

gnRNoConfMismatchTrap TRAP-TYPE
      ENTERPRISE  ceragon
      VARIABLES  {gnGenCfgTrapSeverity , gnGenCfgAlarmText , gnGenCfgCLLI}
      DESCRIPTION
          "This Trap is sent every time a Remote configuration mismatch fault is cleared."
      ::= 346

-- "positive" traps are not being send when protection switch occurs.
-- gnRProtectSwitchOkTrap TRAP-TYPE
--     ENTERPRISE  ceragon
--     VARIABLES  {gnGenCfgTrapSeverity , gnGenCfgAlarmText , gnGenCfgCLLI}
--     DESCRIPTION
--        "Never sent."
--     ::= 347

gnRProtectCableOkTrap TRAP-TYPE
      ENTERPRISE  ceragon
      VARIABLES  {gnGenCfgTrapSeverity , gnGenCfgAlarmText , gnGenCfgCLLI}
      DESCRIPTION
          "This Trap is sent every time a Remote protection cable fault is cleared."
      ::= 348

gnRLomOkTrap TRAP-TYPE
      ENTERPRISE  ceragon
      VARIABLES  {ifIndex, gnGenCfgTrapSeverity , gnGenCfgAlarmText , gnGenCfgCLLI}
      DESCRIPTION
          "This Trap is sent every time a Remote Loss of Multi-frame alarm is cleared."
      ::= 350

--gnRHitlessProblemOKTrap TRAP-TYPE
--      ENTERPRISE  ceragon
--      VARIABLES  {gnGenCfgTrapSeverity , gnGenCfgAlarmText , gnGenCfgCLLI}
--      DESCRIPTION
--          "This Trap is sent every time a Remote Hitless fault is cleared."
--      ::= 351

gnRHitlessRadioLofOKTrap TRAP-TYPE
      ENTERPRISE  ceragon
      VARIABLES  {gnGenCfgTrapSeverity , gnGenCfgAlarmText , gnGenCfgCLLI}
      DESCRIPTION
          "This Trap is sent every time a Remote Hitless RadioLOF fault is cleared."
      ::= 352

gnRHitlessCableDisconnectOKTrap        TRAP-TYPE
      ENTERPRISE  ceragon
      VARIABLES  {gnGenCfgTrapSeverity , gnGenCfgAlarmText , gnGenCfgCLLI}
      DESCRIPTION
          "This Trap is sent every time a Remote Hitless cable fault is cleared."
      ::= 353

--                 skip 354-356 (MSP PAM, SCM, INV)
--                 skip 357                 (Inband)

-- Traps #400-600 are reserved for Managment.

END
