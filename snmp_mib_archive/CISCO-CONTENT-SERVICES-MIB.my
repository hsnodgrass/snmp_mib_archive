-- *****************************************************************
-- CISCO-CONTENT-SERVICES-MIB.my:  Cisco Content Billing MIB file
--   
-- January, 2007 Thamilarasu K
--   
-- Copyright (c) 2007-2010 by cisco Systems Inc.
-- All rights reserved.
--   
-- ****************************************************************

CISCO-CONTENT-SERVICES-MIB DEFINITIONS ::= BEGIN

IMPORTS
    MODULE-IDENTITY,
    OBJECT-TYPE,
    Counter32,
    Counter64,
    Gauge32,
    Integer32,
    Unsigned32,
    NOTIFICATION-TYPE
        FROM SNMPv2-SMI
    MODULE-COMPLIANCE,
    OBJECT-GROUP,
    NOTIFICATION-GROUP
        FROM SNMPv2-CONF
    TEXTUAL-CONVENTION,
    TruthValue,
    RowStatus,
    TimeInterval,
    TimeStamp
        FROM SNMPv2-TC
    InetAddressType,
    InetAddress,
    InetPortNumber
        FROM INET-ADDRESS-MIB
    MplsVpnId
        FROM MPLS-VPN-MIB
    entPhysicalIndex
        FROM ENTITY-MIB
    SnmpAdminString
        FROM SNMP-FRAMEWORK-MIB
    CounterBasedGauge64
        FROM HCNUM-TC
    ciscoMgmt
        FROM CISCO-SMI;


ciscoContentServicesMIB MODULE-IDENTITY
    LAST-UPDATED    "201001280000Z"
    ORGANIZATION    "Cisco Systems, Inc."
    CONTACT-INFO
            "Cisco Systems
            Customer Service

            Postal: 170 W. Tasman Drive
            San Jose, CA  95134
            USA

            tel: +1 800 553-NETS

            E-Mail: cs-csg@cisco.com"
    DESCRIPTION
        "Content Service is a capability to examine IP/TCP/UDP headers,
        payload and enable billing based on the content being provided.

        Abbreviations:

          BMA        Billing Mediation Agent. A BMA is the
                     server that receives accounting records.

          QuotaMgr   Quota Manager. This is a server that
                     receives requests and returns 
                     a billing quota for prepaid billing 
                     charges.

          VRF        Virtual Routing and Forwarding

          UDB        User Database. The user database is a 
                     service that translates a client IP 
                     address into a user identifier.

          GPRS       General Packet Radio Service.

          GTP        GPRS Tunneling Protocol. Transfer Protocol
                     for Charging Detail Records to BMAs and 
                     billing quota from quota managers.

          IPC        Inter Processor Communicaiton.
          Network Server  The service provider who provides the
                          online service.
          AdControl  The Cisco product to enable service providers to
                     share subscriber data with advertising providers 
                     in a controlled and secure manner.

          Gx         Gx is a reference point located between the Policy
                     and Charging Rules Function (PCRF) and the Policy
                     and Charging Enforcement Function (PCEF). Three
                     types of networks namely, 3G UMTS, 4G LTE and 4G
                     WiMax use the 3GPP Gx interface as the standard
                     policy control interface.

          NBAR       Network Based Application Recognition."
    REVISION        "201001280000Z"
    DESCRIPTION
        "Added ccsBillingPlanStatsTable
        Added OBJECT-GROUP ciscoContentServicesBillingPlanStatsGroup
        Added MODULE-COMPLIANCE ciscoContentServicesMIBComplianceRev5"
    REVISION        "200908120000Z"
    DESCRIPTION
        "Added ccsProtocolStatsTable with following objects:
        ccspsTransaction
        ccspsHCTransaction
        ccspsTransactionRate
        ccspsTransactionRateHighWater
        ccspsTransactionRateHighWaterResetTime
        ccspsTransactionRateHighWaterTime
        ccspsSubOutPackets
        ccspsHCSubOutPackets
        ccspsSubOutPacketRate
        ccspsSubOutPacketRateHighWater
        ccspsSubOutPacketRateHighWaterResetTime
        ccspsSubOutPacketRateHighWaterTime
        ccspsNetOutPackets
        ccspsHCNetOutPackets
        ccspsNetOutPacketRate
        ccspsNetOutPacketRateHighWater
        ccspsNetOutPacketRateHighWaterResetTime
        ccspsNetOutPacketRateHighWaterTime
        ccspsSubOutBytes
        ccspsHCSubOutBytes
        ccspsSubOutBitRate
        ccspsSubOutBitRateHighWater
        ccspsSubOutBitRateHighWaterResetTime
        ccspsSubOutBitRateHighWaterTime
        ccspsNetOutBytes
        ccspsHCNetOutBytes
        ccspsNetOutBitRate
        ccspsNetOutBitRateHighWater
        ccspsNetOutBitRateHighWaterResetTime
        ccspsNetOutBitRateHighWaterTime
        Added ccsLoadStatGxEventTable with following objects:
        ccsLoadStatGxEventsAllowed
        ccsLoadStatHCGxEventsAllowed
        ccsLoadStatGxEventsAllowedRate
        ccsLoadStatGxEventsAllowedRateHighWater
        ccsLoadStatHCGxEventsAllowedRateHighWater
        ccsLoadStatGxEventsIPCQueueDepthTolerance
        ccsLoadStatGxEventsDenied
        ccsLoadStatHCGxEventsDenied
        ccsLoadStatGxEventsDenialRate
        ccsLoadStatGxEventsDenialRateHighWater
        ccsLoadStatHCGxEventsDenialRateHighWater.
        Added following object groups to ciscoContentServicesMIBGroups:
        ciscoContentServiceProtocolStatsGroup
        ciscoContentServicesLoadStatGxEventGroup
        Added following new compliance statement to
        ciscoContentServicesMIBCompliances:
        ciscoContentServicesMIBComplianceRev4."
    REVISION        "200901280000Z"
    DESCRIPTION
        "Added following objects to ccsGlobalCfgTable:
        ccsNetServerAlarmUpdateTimer
        ccsNetServerResponseFailAlarmThreshold
        ccsNetServerResponseFailClearThreshold
        ccsNetServerFirstPayloadResponseTime
        ccsNetServerResponseTimeFailAlarmThreshold
        ccsNetServerResponseTimeFailClearThreshold
        ccsProtocolParseFailAlarmThreshold
        ccsProtocolParseFailClearThreshold.
        Added following object to ccsNotifCfgTable:
        ccsAdControlNotifEnabled.
        Added following object to ciscoContentServicesMIBObjects:
        ccsNotifInfo.
        Added following objects to ciscoContentServicesNotifGroup:
        ciscoContentServicesNetServerResponseFailExceeded,
        ciscoContentServicesNetServerResponseTimeExceeded
        ciscoContentServicesProtocolParseFailExceeded
        ciscoContentServicesNetServerResponseFailAlarmCleared
        ciscoContentServicesNetServerResponseTimeAlarmCleared
        ciscoContentServicesProtocolParseFailAlarmCleared
        Added ciscoContentServicesNotifInfoGroup with following objects:
        ccsTPIndexNotifInfo
        ccsServiceNameNotifInfo
        ccsContentNameNotifInfo
        ccsPolicyNameNotifInfo
        ccsNetServerIpAddrTypeNotifInfo
        ccsNetServerIpAddrNotifInfo
        ccsNetServerPortNotifInfo
        ccsSubscriberIpAddrTypeNotifInfo
        ccsSubscriberIpAddrNotifInfo
        ccsSubscriberPortNotifInfo
        ccsNetServerResponseFailCountNotifInfo
        ccsNetServerResponseTimeFailCountNotifInfo
        ccsProtocolParseFailCountNotifInfo
        Added following object groups to ciscoContentServicesMIBGroups:
        ciscoContentServicesGlobalCfgGroupSup2
        ciscoContentServicesNotifEnableGroupSup2
        ciscoContentServicesNotifGroupSup2
        ciscoContentServicesNotifInfoGroup
        Added following new compliance statement to
        ciscoContentServicesMIBCompliances:
        ciscoContentServicesMIBComplianceRev3"
    REVISION        "200809260000Z"
    DESCRIPTION
        "Added following object to ccsGlobalCfgTable.
        ccsgsUserThreshold.
        Added following object to ccsNotifCfgTable.
        ccsUserThresholdExceededNotifEnabled
        Added following object to ciscoContentServicesNotifGroup.
        ciscoContentServicesUserThresholdExceeded.
        Added following object groups to ciscoContentServicesMIBGroups.
        ciscoContentServicesGlobalCfgGroupSup1,
        ciscoContentServicesNotifEnableGroupSup1,
        ciscoContentServicesNotifGroupSup1
        Added following new compliance statement to
        ciscoContentServicesMIBCompliances.
        ciscoContentServicesMIBComplianceRev2"
    REVISION        "200804210000Z"
    DESCRIPTION
        "Added following object to ccsGlobalStatsTable.
        ccsgsGTPBMARejected,
        ccsgsHCGTPBMARejected,
        ccsgsGTPBMADropped,
        ccsgsHCGTPBMADropped,
        ccsgsGTPBMARetransmit,
        ccsgsHCGTPBMARetransmit,
        ccsgsGTPQuotaMgrRejected,
        ccsgsHCGTPQuotaMgrRejected,
        ccsgsGTPQuotaMgrDropped,
        ccsgsHCGTPQuotaMgrDropped,
        ccsgsGTPQuotaMgrRetransmit,
        ccsgsHCGTPQuotaMgrRetransmit,
        ccsgsGTPBMARateInterval,
        ccsgsGTPQuotaMgrRateInterval
        Added following object to ccsBMATable.
        ccsBMAPacketRate,
        ccsBMAAckRate
        Added following object to ccsQuotaMgrTable.
        ccsQuotaMgrPacketRate,
        ccsQuotaMgrAckRate
        Added following OID subtree in ccsStats to support load statistics.
        ccsLoadStatistics
        Added following object groups to ciscoContentServicesMIBGroups.
        ciscoContentServicesGlobalStatsGroupSup1,
        ciscoContentServicesBMAGroupSup1,
        ciscoContentServicesQuotaMgrGroupSup1
        Added following new compliance statement to ciscoContentServicesMIBCompliances.
        ciscoContentServicesMIBComplianceRev1"
    REVISION        "200703210000Z"
    DESCRIPTION
        "Initial version of this MIB module."
    ::= { ciscoMgmt 597 }


ciscoContentServicesMIBNotifs  OBJECT IDENTIFIER
    ::= { ciscoContentServicesMIB 0 }

ciscoContentServicesMIBObjects  OBJECT IDENTIFIER
    ::= { ciscoContentServicesMIB 1 }

ciscoContentServicesMIBConform  OBJECT IDENTIFIER
    ::= { ciscoContentServicesMIB 2 }

ccsConfig  OBJECT IDENTIFIER
    ::= { ciscoContentServicesMIBObjects 1 }

ccsStats  OBJECT IDENTIFIER
    ::= { ciscoContentServicesMIBObjects 2 }

ccsNotifConfig  OBJECT IDENTIFIER
    ::= { ciscoContentServicesMIBObjects 3 }

ccsNotifInfo  OBJECT IDENTIFIER
    ::= { ciscoContentServicesMIBObjects 4 }


-- ********************************************************************
-- *                                                                  *
-- * Textual Conventions                                              *
-- *                                                                  *
-- ********************************************************************

CcsServerPriority ::= TEXTUAL-CONVENTION
    STATUS          current
    DESCRIPTION
        "This convention applies to  billing mediation agents
        and quota managers. When multiple servers of the same
        type are defined, the priority defines the order of
        activation of the servers. The lowest priority value
        designates the highest priority."
    SYNTAX          Integer32 (1..1000)
-- *************************************************************
-- *                                                           *
-- * Content Billing Global Config Table                       *
-- *                                                           *
-- *************************************************************

ccsGlobalCfgTable OBJECT-TYPE
    SYNTAX          SEQUENCE OF CcsGlobalCfgTableEntry 
    MAX-ACCESS      not-accessible
    STATUS          current
    DESCRIPTION
        "This table contains configuration information
        for content billing feature."
    ::= { ccsConfig 1 }

ccsGlobalCfgTableEntry OBJECT-TYPE
    SYNTAX          CcsGlobalCfgTableEntry
    MAX-ACCESS      not-accessible
    STATUS          current
    DESCRIPTION
        "Each row in this table contains configuration
        information on content billing feature.

        entPhysicalIndex identifies the entity that
        that provides the content services."
    INDEX           { entPhysicalIndex } 
    ::= { ccsGlobalCfgTable 1 }

CcsGlobalCfgTableEntry ::= SEQUENCE {
        ccsgcBMALostRecordTimer                    TimeInterval,
        ccsgcQuotaMgrLostRecordTimer               TimeInterval,
        ccsgsUserThreshold                         Unsigned32,
        ccsAdControlAlarmUpdateTimer               TimeInterval,
        ccsNetServerResponseFailAlarmThreshold     Unsigned32,
        ccsNetServerResponseFailClearThreshold     Unsigned32,
        ccsNetServerFirstPayloadResponseTime       TimeInterval,
        ccsNetServerResponseTimeFailAlarmThreshold Unsigned32,
        ccsNetServerResponseTimeFailClearThreshold Unsigned32,
        ccsProtocolParseFailAlarmThreshold         Unsigned32,
        ccsProtocolParseFailClearThreshold         Unsigned32
}

ccsgcBMALostRecordTimer OBJECT-TYPE
    SYNTAX          TimeInterval
    UNITS           "seconds"
    MAX-ACCESS      read-write
    STATUS          current
    DESCRIPTION
        "The time interval for monitoring the lost-record
        event (ccsBMALostRecordEvent) of a billing
        mediation agent (BMA). A notification is issued when
        the BMA record is lost. An interval timer is 
        started with this value. When the timer expires the
        lost record count (ccsBMALostRecords) is checked. 
        If the lost record count has increased since the
        previous the detection, the timer is restarted to
        monitor another period. If the lost record count
        has not increased since the previous detection,
        a final notification is sent to indicate that the
        condition has cleared.

        The interval value ranges from 1 to 2147483647."
    DEFVAL          { 60 } 
    ::= { ccsGlobalCfgTableEntry 2 }

ccsgcQuotaMgrLostRecordTimer OBJECT-TYPE
    SYNTAX          TimeInterval
    UNITS           "seconds"
    MAX-ACCESS      read-write
    STATUS          current
    DESCRIPTION
        "The time interval for monitoring the lost-record
        event (ccsQuotaMgrLostRecordEvent) of a quota
        manager. A notification is issued when quota manager
        record is lost. An interval timer is 
        started with this value. When the timer expires the
        lost record count (ccsQuotaMgrLostRecords) is checked. 
        If the lost record count has increased since the
        previous the detection, the timer is restarted to
        monitor another period. If the lost record count
        has not increased since the previous detection,
        a final notification is sent to indicate that the
        condition has cleared.

        The interval value ranges from 1 to 2147483647."
    DEFVAL          { 60 } 
    ::= { ccsGlobalCfgTableEntry 3 }

ccsgsUserThreshold OBJECT-TYPE
    SYNTAX          Unsigned32
    UNITS           "users"
    MAX-ACCESS      read-write
    STATUS          current
    DESCRIPTION
        "The maximum number of users that is contractually
        allowed.  When the actual number of user exceeds
        the contractually established limit, a notification
        (ciscoContentServicesUserThresholdExceeded)
        is issued." 
    ::= { ccsGlobalCfgTableEntry 4 }

ccsAdControlAlarmUpdateTimer OBJECT-TYPE
    SYNTAX          TimeInterval (1..2147483647)
    UNITS           "seconds"
    MAX-ACCESS      read-write
    STATUS          current
    DESCRIPTION
        "The time interval to monitor the AdControl related errors.
        The alarm and clear notifications are enabled
        when ccsAdControlNotifEnabled is set to 'true'. The alarm 
        notifications are specified by
        ciscoContentServicesNetServerResponseFailExceeded,
        ciscoContentServicesNetServerResponseTimeExceeded,
        ciscoContentServicesProtocolParseFailExceeded.
        The clear notifications are specified
        ciscoContentServicesNetServerResponseFailAlarmCleared,
        ciscoContentServicesNetServerResponseTimeAlarmCleared,
        ciscoContentServicesProtocolParseFailAlarmCleared
        The AdControl will start a timer for each type of errors.
        Each error has a counter. The counters for the errors are
        ccsNetServerResponseFailCountNotifInfo,
        ccsNetServerResponseTimeFailCountNotifInfo,
        ccsProtocolParseFailCountNotifInfo.
        An alarm notification will be generated if the error exceeds
        the alarm threshold within the time interval and no such alarm
        has been raised yet. The timer will be restarted after an alarm 
        notification is generated. When the timer expires, a clear 
        notification will be generated if the error is equal to or less
        than the clear threshold and the alarm exists.
        The alarm thresholds are specified by
        ccsNetServerResponseFailAlarmThreshold,
        ccsNetServerResponseTimeFailAlarmThreshold,
        ccsProtocolParseFailAlarmThreshold.
        The clear thresholds are specified by
        ccsNetServerResponseFailClearThreshold,
        ccsNetServerResponseTimeFailClearThreshold,
        ccsProtocolParseFailClearThreshold.
        When the timer is changed, the alarm counters will be reset
        and the related alarms will be cleared if exist."
    DEFVAL          { 300 } 
    ::= { ccsGlobalCfgTableEntry 5 }

ccsNetServerResponseFailAlarmThreshold OBJECT-TYPE
    SYNTAX          Unsigned32 (1..4294967294)
    UNITS           "errors"
    MAX-ACCESS      read-write
    STATUS          current
    DESCRIPTION
        "This object specifies the alarm threshold of the
        number of the failed responses specified by
        ccsNetServerResponseFailCountNotifInfo from the network server
        in the time interval (ccsAdControlAlarmUpdateTimer).
        When ccsAdControlNotifEnabled is set to 'true', the count
        is greater than the threshold, and no alarm notification
        specified by
        ciscoContentServicesNetServerResponseFailExceeded
        has been issued within the timer interval, the alarm 
        notification will be generated and the timer will be
        re-started.
        The threshold should be greater than the clear 
        threshold ccsNetServerResponseFailClearThreshold.
        When the threshold is changed, the counter will be
        reset, the alarm will be cleared, and the timer will 
        be re-started."
    DEFVAL          { 5 } 
    ::= { ccsGlobalCfgTableEntry 6 }

ccsNetServerResponseFailClearThreshold OBJECT-TYPE
    SYNTAX          Unsigned32 (0..4294967293)
    UNITS           "errors"
    MAX-ACCESS      read-write
    STATUS          current
    DESCRIPTION
        "This object specifies the clear threshold associated
        with ccsNetServerResponseFailAlarmThreshold.
        If ccsAdControlNotifEnabled is set to 'true', the count
        (ccsNetServerResponseFailCountNotifInfo)
        is equal to or lower than the threshold when the timer
        (ccsAlarmUpdateTimer) expires and the 
        alarm specified by
        ciscoContentServicesNetServerResponseFailExceeded
        exists, the clear notification specified by
        ciscoContentServicesNetServerResponseFailAlarmCleared
        is generated.  The threshold should be less than the
        alarm threshold specified by
        ccsNetServerResponseFailAlarmThreshold.
        When the threshold is changed, the counter will be
        reset, the alarm will be cleared if exists, and the timer
        will be re-started."
    DEFVAL          { 0 } 
    ::= { ccsGlobalCfgTableEntry 7 }

ccsNetServerFirstPayloadResponseTime OBJECT-TYPE
    SYNTAX          TimeInterval (1..2147483647)
    UNITS           "seconds"
    MAX-ACCESS      read-write
    STATUS          current
    DESCRIPTION
        "The amount of time to wait for the first payload packet from
        the network server. The
        ciscoContentServicesNetServerResponseTimeExceeded notification
        is generated when the first payload response is exceeded by 
        the network server.
        When the time interval is changed, the
        counter specified by ccsNetServerResponseTimeFailCountNotifInfo
        will be reset and the alarm specified by
        ciscoContentServicesNetServerResponseTimeExceeded
        will be cleared if exists."
    DEFVAL          { 5 } 
    ::= { ccsGlobalCfgTableEntry 8 }

ccsNetServerResponseTimeFailAlarmThreshold OBJECT-TYPE
    SYNTAX          Unsigned32 (1..4294967294)
    UNITS           "errors"
    MAX-ACCESS      read-write
    STATUS          current
    DESCRIPTION
        "This object specifies the alarm threshold of the
        number of the responses specified by
        ccsNetServerResponseTimeFailCountNotifInfo
        for the first payload packet from the network server exceeds
        the response time ccsNetServerFirstPayloadResponseTime
        within the time interval (ccsAdControlAlarmUpdateTimer).
        When ccsAdControlNotifEnabled is set to 'true', the count 
        is greater than the threshold and no alarm notification
        specified by
        ciscoContentServicesNetServerResponseTimeExceeded
        has been issued, the alarm notification will be generated
        and the timer will be re-started. 
        The threshold should be greater than the clear threshold
        ccsNetServerResponseTimeFailClearThreshold.
        When the threshold is changed, the counter will be 
        reset, the alarm will be cleared if exists, and the timer
        will be re-started."
    DEFVAL          { 5 } 
    ::= { ccsGlobalCfgTableEntry 9 }

ccsNetServerResponseTimeFailClearThreshold OBJECT-TYPE
    SYNTAX          Unsigned32 (0..4294967293)
    UNITS           "errors"
    MAX-ACCESS      read-write
    STATUS          current
    DESCRIPTION
        "This object specifies the clear threshold associated with
        ccsNetServerResponseTimeFailAlarmThreshold.
        If ccsAdControlNotifEnabled is set to 'true', the count 
        (ccsNetServerResponseTimeFailCountNotifInfo)
        is equal to or lower than the threshold when the timer
        (ccsAdControlAlarmUpdateTimer) expires and the alarm 
        specified by
        ciscoContentServicesNetServerResponseTimeExceeded
        exists, the clear notification specified by
        ciscoContentServicesNetServerResponseTimeAlarmCleared
        is generated.  The threshold should be less than the
        alarm threshold specified by
        ccsNetServerResponseTimeFailAlarmThreshold.
        When the threshold is changed, the counter will be 
        reset, the alarm will be cleared, and the timer will be
        re-started."
    DEFVAL          { 0 } 
    ::= { ccsGlobalCfgTableEntry 10 }

ccsProtocolParseFailAlarmThreshold OBJECT-TYPE
    SYNTAX          Unsigned32 (1..4294967294)
    UNITS           "errors"
    MAX-ACCESS      read-write
    STATUS          current
    DESCRIPTION
        "This object specifies the alarm threshold of the
        number of errors specified by 
        ccsProtocolParseFailCountNotifInfo fail the
        protocol parsing in the time interval
        (ccsAdControlAlarmUpdateTimer). When 
        ccsAdControlNotifEnabled is set to 'true', the count 
        (ccsProtocolParseFailCountNotifInfo) is greater 
        than the thresholdand and no alarm notification specified
        by ciscoContentServicesProtocolParseFailExceeded
        has been issued within the time interval, the alarm 
        notification will be generated and the timer will be
        re-started. The threshold should be greater than
        the clear threshold
        ccsProtocolParseFailClearThreshold.
        When the threshold is changed, the counter will be reset,
        the alarm will be cleared, and the timer will be
        re-started."
    DEFVAL          { 5 } 
    ::= { ccsGlobalCfgTableEntry 11 }

ccsProtocolParseFailClearThreshold OBJECT-TYPE
    SYNTAX          Unsigned32 (0..4294967293)
    UNITS           "errors"
    MAX-ACCESS      read-write
    STATUS          current
    DESCRIPTION
        "This object specifies the clear threshold associated
        with ccsProtocolParseFailAlarmThreshold.
        If ccsAdControlNotifEnabled is set to 'true', the count
        (ccsProtocolParseFailCountNotifInfo)
        is equal to or lower than the threshold when the timer
        (ccsAdControlAlarmUpdateTimer) expires and the 
        alarm specified by
        ciscoContentServicesProtocolParseFailExceeded
        exists, the clear notification specified by
        ciscoContentServicesProtocolParseFailAlarmCleared
        is generated. The threshold should be less than
        the alarm threshold specified by
        ccsProtocolParseFailAlarmThreshold.
        When the threshold is changed, the counter will be 
        reset, the alarm will be cleared, and the timer will 
        be re-started."
    DEFVAL          { 0 } 
    ::= { ccsGlobalCfgTableEntry 12 }
 

-- *************************************************************
-- *                                                           *
-- *      Content Billing Global Stats Table                   *
-- *                                                           *
-- *************************************************************

ccsGlobalStatsTable OBJECT-TYPE
    SYNTAX          SEQUENCE OF CcsGlobalStatsTableEntry 
    MAX-ACCESS      not-accessible
    STATUS          current
    DESCRIPTION
        "This table contains the global statistical information
        in content billing feature."
    ::= { ccsStats 1 }

ccsGlobalStatsTableEntry OBJECT-TYPE
    SYNTAX          CcsGlobalStatsTableEntry
    MAX-ACCESS      not-accessible
    STATUS          current
    DESCRIPTION
        "Each row in this table contains statistical information
        for content billing feature.

        entPhysicalIndex identifies the entity that
        that provides the content services."
    INDEX           { entPhysicalIndex } 
    ::= { ccsGlobalStatsTable 1 }

CcsGlobalStatsTableEntry ::= SEQUENCE {
        ccsgsUserCurrent               Gauge32,
        ccsgsUserHighWater             Gauge32,
        ccsgsUserHighWaterResetTime    TimeStamp,
        ccsgsSessionCurrent            Gauge32,
        ccsgsSessionHighWater          Gauge32,
        ccsgsSessionHighWaterResetTime TimeStamp,
        ccsgsGTPBMARejected            Counter32,
        ccsgsHCGTPBMARejected          Counter64,
        ccsgsGTPBMADropped             Counter32,
        ccsgsHCGTPBMADropped           Counter64,
        ccsgsGTPBMARetransmit          Counter32,
        ccsgsHCGTPBMARetransmit        Counter64,
        ccsgsGTPQuotaMgrRejected       Counter32,
        ccsgsHCGTPQuotaMgrRejected     Counter64,
        ccsgsGTPQuotaMgrDropped        Counter32,
        ccsgsHCGTPQuotaMgrDropped      Counter64,
        ccsgsGTPQuotaMgrRetransmit     Counter32,
        ccsgsHCGTPQuotaMgrRetransmit   Counter64,
        ccsgsGTPBMARateInterval        TimeInterval,
        ccsgsGTPQuotaMgrRateInterval   TimeInterval
}

ccsgsUserCurrent OBJECT-TYPE
    SYNTAX          Gauge32
    UNITS           "users"
    MAX-ACCESS      read-only
    STATUS          current
    DESCRIPTION
        "The total number of users with one or more active
        sessions on the system." 
    ::= { ccsGlobalStatsTableEntry 1 }

ccsgsUserHighWater OBJECT-TYPE
    SYNTAX          Gauge32
    UNITS           "users"
    MAX-ACCESS      read-write
    STATUS          current
    DESCRIPTION
        "The highest number of active users as reported by
        ccsgsUserCurrent object since the object was reset as
        indicated by ccsgsUserHighWaterResetTime.  The only
        write operation allowed is to reset the value to 0." 
    ::= { ccsGlobalStatsTableEntry 2 }

ccsgsUserHighWaterResetTime OBJECT-TYPE
    SYNTAX          TimeStamp
    MAX-ACCESS      read-only
    STATUS          current
    DESCRIPTION
        "The time stamp at which the ccsgsUserHighWater object was
        last reset to 0." 
    ::= { ccsGlobalStatsTableEntry 3 }

ccsgsSessionCurrent OBJECT-TYPE
    SYNTAX          Gauge32
    UNITS           "sessions"
    MAX-ACCESS      read-only
    STATUS          current
    DESCRIPTION
        "The total number of sessions on the system.  A session
        corresponds to a TCP/UDP flow." 
    ::= { ccsGlobalStatsTableEntry 4 }

ccsgsSessionHighWater OBJECT-TYPE
    SYNTAX          Gauge32
    MAX-ACCESS      read-write
    STATUS          current
    DESCRIPTION
        "The highest number of active sessions as reported by the
        ccsgsSessionCurrent object since object was reset as indicated
        by ccsgsSessionHighWaterResetTime.  The only write operation
        allowed is to reset the value to zero." 
    ::= { ccsGlobalStatsTableEntry 5 }

ccsgsSessionHighWaterResetTime OBJECT-TYPE
    SYNTAX          TimeStamp
    MAX-ACCESS      read-only
    STATUS          current
    DESCRIPTION
        "The time stamp at which the ccsgsSessionHighWater object was
        last reset to 0." 
    ::= { ccsGlobalStatsTableEntry 6 }

ccsgsGTPBMARejected OBJECT-TYPE
    SYNTAX          Counter32
    UNITS           "messages"
    MAX-ACCESS      read-only
    STATUS          current
    DESCRIPTION
        "Number of  messages received from all
        the BMAs with reject cause code." 
    ::= { ccsGlobalStatsTableEntry 7 }

ccsgsHCGTPBMARejected OBJECT-TYPE
    SYNTAX          Counter64
    UNITS           "messages"
    MAX-ACCESS      read-only
    STATUS          current
    DESCRIPTION
        "This object is a 64-bit version of
        ccsgsGTPBMARejected." 
    ::= { ccsGlobalStatsTableEntry 8 }

ccsgsGTPBMADropped OBJECT-TYPE
    SYNTAX          Counter32
    UNITS           "messages"
    MAX-ACCESS      read-only
    STATUS          current
    DESCRIPTION
        "Total Number of messages dropped
        destined for any of the BMAs." 
    ::= { ccsGlobalStatsTableEntry 9 }

ccsgsHCGTPBMADropped OBJECT-TYPE
    SYNTAX          Counter64
    UNITS           "messages"
    MAX-ACCESS      read-only
    STATUS          current
    DESCRIPTION
        "This object is a 64-bit version of
        ccsgsGTPBMADropped." 
    ::= { ccsGlobalStatsTableEntry 10 }

ccsgsGTPBMARetransmit OBJECT-TYPE
    SYNTAX          Counter32
    UNITS           "messages"
    MAX-ACCESS      read-only
    STATUS          current
    DESCRIPTION
        "The number of messages retransmitted to
        all BMAs." 
    ::= { ccsGlobalStatsTableEntry 11 }

ccsgsHCGTPBMARetransmit OBJECT-TYPE
    SYNTAX          Counter64
    UNITS           "messages"
    MAX-ACCESS      read-only
    STATUS          current
    DESCRIPTION
        "This object is a 64-bit version of
        ccsgsGTPBMARetransmit." 
    ::= { ccsGlobalStatsTableEntry 12 }

ccsgsGTPQuotaMgrRejected OBJECT-TYPE
    SYNTAX          Counter32
    UNITS           "messages"
    MAX-ACCESS      read-only
    STATUS          current
    DESCRIPTION
        "Number of messages received from all the
        Quota Managers with reject cause code." 
    ::= { ccsGlobalStatsTableEntry 13 }

ccsgsHCGTPQuotaMgrRejected OBJECT-TYPE
    SYNTAX          Counter64
    UNITS           "messages"
    MAX-ACCESS      read-only
    STATUS          current
    DESCRIPTION
        "This object is a 64-bit version of
        ccsgsGTPQuotaMgrRejected." 
    ::= { ccsGlobalStatsTableEntry 14 }

ccsgsGTPQuotaMgrDropped OBJECT-TYPE
    SYNTAX          Counter32
    UNITS           "messages"
    MAX-ACCESS      read-only
    STATUS          current
    DESCRIPTION
        "Total Number of messages dropped
        destined for any of the Quota Managers." 
    ::= { ccsGlobalStatsTableEntry 15 }

ccsgsHCGTPQuotaMgrDropped OBJECT-TYPE
    SYNTAX          Counter64
    UNITS           "messages"
    MAX-ACCESS      read-only
    STATUS          current
    DESCRIPTION
        "This object is a 64-bit version of
        ccsgsGTPQuotaMgrDropped." 
    ::= { ccsGlobalStatsTableEntry 16 }

ccsgsGTPQuotaMgrRetransmit OBJECT-TYPE
    SYNTAX          Counter32
    UNITS           "messages"
    MAX-ACCESS      read-only
    STATUS          current
    DESCRIPTION
        "The number of messages retransmitted
        to all the Quota Managers." 
    ::= { ccsGlobalStatsTableEntry 17 }

ccsgsHCGTPQuotaMgrRetransmit OBJECT-TYPE
    SYNTAX          Counter64
    UNITS           "messages"
    MAX-ACCESS      read-only
    STATUS          current
    DESCRIPTION
        "This object is a 64-bit version of
        ccsgsGTPQuotaMgrRetransmit." 
    ::= { ccsGlobalStatsTableEntry 18 }

ccsgsGTPBMARateInterval OBJECT-TYPE
    SYNTAX          TimeInterval
    UNITS           "seconds"
    MAX-ACCESS      read-write
    STATUS          current
    DESCRIPTION
        "The duration of the time interval in
        ccsBMAPacketRate and ccsBMAAckRate."
    DEFVAL          { 2 } 
    ::= { ccsGlobalStatsTableEntry 19 }

ccsgsGTPQuotaMgrRateInterval OBJECT-TYPE
    SYNTAX          TimeInterval
    UNITS           "seconds"
    MAX-ACCESS      read-write
    STATUS          current
    DESCRIPTION
        "The duration of the time interval in
        ccsQuotaMgrPacketRate and ccsQuotaMgrAckRate."
    DEFVAL          { 2 } 
    ::= { ccsGlobalStatsTableEntry 20 }
 

-- *************************************************************
-- *                                                           *
-- *      Content Billing User Database Table                  *
-- *                                                           *
-- *************************************************************

ccsUserDbTable OBJECT-TYPE
    SYNTAX          SEQUENCE OF CcsUserDbTableEntry 
    MAX-ACCESS      not-accessible
    STATUS          current
    DESCRIPTION
        "Table of User Database Server. Entries are added to
        this table via ccsUserDbRowStatus in accordance with
        the RowStatus convention."
    ::= { ccsStats 2 }

ccsUserDbTableEntry OBJECT-TYPE
    SYNTAX          CcsUserDbTableEntry
    MAX-ACCESS      not-accessible
    STATUS          current
    DESCRIPTION
        "Entry that defines parameters for a User Database.
        The User Database is a server that returns a userid
        given an IP address received in request.

        entPhysicalIndex identifies the entity that
        that provides the content services."
    INDEX           {
                        entPhysicalIndex,
                        ccsUserDbVrfName,
                        ccsUserDbIpAddrType,
                        ccsUserDbIpAddr,
                        ccsUserDbPort
                    } 
    ::= { ccsUserDbTable 1 }

CcsUserDbTableEntry ::= SEQUENCE {
        ccsUserDbVrfName        MplsVpnId,
        ccsUserDbIpAddrType     InetAddressType,
        ccsUserDbIpAddr         InetAddress,
        ccsUserDbPort           InetPortNumber,
        ccsUserDbState          INTEGER,
        ccsUserDbRequests       Counter32,
        ccsUserDbHCRequests     Counter64,
        ccsUserDbUidsReturned   Counter32,
        ccsUserDbHCUidsReturned Counter64,
        ccsUserDbReqResent      Counter32,
        ccsUserDbHCReqResent    Counter64,
        ccsUserDbReqTimeouts    Counter32,
        ccsUserDbHCReqTimeouts  Counter64,
        ccsUserDbReqErrors      Counter32,
        ccsUserDbHCReqErrors    Counter64,
        ccsUserDbRowStatus      RowStatus
}

ccsUserDbVrfName OBJECT-TYPE
    SYNTAX          MplsVpnId
    MAX-ACCESS      not-accessible
    STATUS          current
    DESCRIPTION
        "Name of the VRF over which communication with
        User Data Server occurs.  If no VRF is specified,
        the global routing table is used." 
    ::= { ccsUserDbTableEntry 1 }

ccsUserDbIpAddrType OBJECT-TYPE
    SYNTAX          InetAddressType
    MAX-ACCESS      not-accessible
    STATUS          current
    DESCRIPTION
        "This object specifies the type of the address specified by
        ccsUserDbIpAddr." 
    ::= { ccsUserDbTableEntry 2 }

ccsUserDbIpAddr OBJECT-TYPE
    SYNTAX          InetAddress
    MAX-ACCESS      not-accessible
    STATUS          current
    DESCRIPTION
        "The IP address of the user database." 
    ::= { ccsUserDbTableEntry 3 }

ccsUserDbPort OBJECT-TYPE
    SYNTAX          InetPortNumber
    MAX-ACCESS      not-accessible
    STATUS          current
    DESCRIPTION
        "The listening UDP port of the user database." 
    ::= { ccsUserDbTableEntry 4 }

ccsUserDbState OBJECT-TYPE
    SYNTAX          INTEGER  {
                        reset(1),
                        active(2),
                        failed(3)
                    }
    MAX-ACCESS      read-only
    STATUS          current
    DESCRIPTION
        "State of the user database.
        'reset'    - State before the database is determined
                     to be active.
        'active'   - The database is available and processing
                     requests.
        'failed'   - The database has failed and is not  
                     processing requests." 
    ::= { ccsUserDbTableEntry 5 }

-- User Database statistics

ccsUserDbRequests OBJECT-TYPE
    SYNTAX          Counter32
    UNITS           "requests"
    MAX-ACCESS      read-only
    STATUS          current
    DESCRIPTION
        "Number of user database requests." 
    ::= { ccsUserDbTableEntry 6 }

ccsUserDbHCRequests OBJECT-TYPE
    SYNTAX          Counter64
    UNITS           "requests"
    MAX-ACCESS      read-only
    STATUS          current
    DESCRIPTION
        "Number of user database requests.

        This object is a 64-bit version of 
        ccsUserDbRequests." 
    ::= { ccsUserDbTableEntry 7 }

ccsUserDbUidsReturned OBJECT-TYPE
    SYNTAX          Counter32
    UNITS           "returned identifiers"
    MAX-ACCESS      read-only
    STATUS          current
    DESCRIPTION
        "Number of user identifiers returned." 
    ::= { ccsUserDbTableEntry 8 }

ccsUserDbHCUidsReturned OBJECT-TYPE
    SYNTAX          Counter64
    UNITS           "returned identifiers"
    MAX-ACCESS      read-only
    STATUS          current
    DESCRIPTION
        "Number of user identifiers returned.

        This object is a 64-bit version of 
        ccsUserDbHCUidsReturned." 
    ::= { ccsUserDbTableEntry 9 }

ccsUserDbReqResent OBJECT-TYPE
    SYNTAX          Counter32
    UNITS           "requests"
    MAX-ACCESS      read-only
    STATUS          current
    DESCRIPTION
        "Number of database requests resent." 
    ::= { ccsUserDbTableEntry 10 }

ccsUserDbHCReqResent OBJECT-TYPE
    SYNTAX          Counter64
    UNITS           "requests"
    MAX-ACCESS      read-only
    STATUS          current
    DESCRIPTION
        "Number of database requests resent.

        This object is a 64-bit version of 
        ccsUserDbReqResent." 
    ::= { ccsUserDbTableEntry 11 }

ccsUserDbReqTimeouts OBJECT-TYPE
    SYNTAX          Counter32
    UNITS           "timeouts"
    MAX-ACCESS      read-only
    STATUS          current
    DESCRIPTION
        "Number of user database requests that have timed out." 
    ::= { ccsUserDbTableEntry 12 }

ccsUserDbHCReqTimeouts OBJECT-TYPE
    SYNTAX          Counter64
    UNITS           "timeouts"
    MAX-ACCESS      read-only
    STATUS          current
    DESCRIPTION
        "Number of user database requests that have timed out.

        This object is a 64-bit version of 
        ccsUserDbReqTimeouts." 
    ::= { ccsUserDbTableEntry 13 }

ccsUserDbReqErrors OBJECT-TYPE
    SYNTAX          Counter32
    UNITS           "errors"
    MAX-ACCESS      read-only
    STATUS          current
    DESCRIPTION
        "Number of errors returned on user database requests." 
    ::= { ccsUserDbTableEntry 14 }

ccsUserDbHCReqErrors OBJECT-TYPE
    SYNTAX          Counter64
    UNITS           "errors"
    MAX-ACCESS      read-only
    STATUS          current
    DESCRIPTION
        "Number of errors returned on user database requests.

        This object is a 64-bit version of 
        ccsUserDbReqErrors." 
    ::= { ccsUserDbTableEntry 15 }

ccsUserDbRowStatus OBJECT-TYPE
    SYNTAX          RowStatus
    MAX-ACCESS      read-create
    STATUS          current
    DESCRIPTION
        "This object is used by the manager to create
        or delete the row entry in the ccsUserDbTable
        following the RowStatus textual convention.

        This row can be deleted regardless of the
        value of ccsUserDbState.  If all ccsUserDbTable
        rows have been deleted, then other mechanisms,
        such as intercepting RADIUS flows, may be used to
        associate a user name with an IP address. If
        this is not possible, then the user name will
        be absent from generated accounting records." 
    ::= { ccsUserDbTableEntry 16 }
 

-- *************************************************************
-- *                                                           *
-- *      Table of Content billing mediation agents            *
-- *                                                           *
-- *************************************************************

ccsBMATable OBJECT-TYPE
    SYNTAX          SEQUENCE OF CcsBMATableEntry 
    MAX-ACCESS      not-accessible
    STATUS          current
    DESCRIPTION
        "A table of billing mediation agents (BMAs).
        Columnar objects can be modified when the row is 'active'.
        Rows can be created and destroyed. Entries are added to 
        this table via ccsBMARowStatus in accordance with the 
        RowStatus convention.

        Multiple BMAs can be configured for the purposes of 
        load sharing and redundancy in the event of failure."
    ::= { ccsStats 3 }

ccsBMATableEntry OBJECT-TYPE
    SYNTAX          CcsBMATableEntry
    MAX-ACCESS      not-accessible
    STATUS          current
    DESCRIPTION
        "Entry that defines parameters for a mediation agent.

        entPhysicalIndex identifies the entity that
        that provides the content services."
    INDEX           {
                        entPhysicalIndex,
                        ccsBMAVrfName,
                        ccsBMAIpAddrType,
                        ccsBMAIpAddr,
                        ccsBMAPort
                    } 
    ::= { ccsBMATable 1 }

CcsBMATableEntry ::= SEQUENCE {
        ccsBMAVrfName            MplsVpnId,
        ccsBMAIpAddrType         InetAddressType,
        ccsBMAIpAddr             InetAddress,
        ccsBMAPort               InetPortNumber,
        ccsBMAPriority           CcsServerPriority,
        ccsBMAState              INTEGER,
        ccsBMALostRecords        Counter32,
        ccsBMAHCLostRecords      Counter64,
        ccsBMATotalSent          Counter32,
        ccsBMAHCTotalSent        Counter64,
        ccsBMAFailAck            Counter32,
        ccsBMAHCFailAck          Counter64,
        ccsBMAOutstanding        Gauge32,
        ccsBMAHighWater          Gauge32,
        ccsBMAHighWaterResetTime TimeStamp,
        ccsBMABadRecord          Counter32,
        ccsBMAHCBadRecord        Counter64,
        ccsBMARetransmit         Counter32,
        ccsBMAHCRetransmit       Counter64,
        ccsBMARowStatus          RowStatus,
        ccsBMAPacketRate         Gauge32,
        ccsBMAAckRate            Gauge32
}

ccsBMAVrfName OBJECT-TYPE
    SYNTAX          MplsVpnId
    MAX-ACCESS      not-accessible
    STATUS          current
    DESCRIPTION
        "Name of the VRF over which communication with
        Agent occurs.  If no VRF is specified, the
        global routing table is used." 
    ::= { ccsBMATableEntry 1 }

ccsBMAIpAddrType OBJECT-TYPE
    SYNTAX          InetAddressType
    MAX-ACCESS      not-accessible
    STATUS          current
    DESCRIPTION
        "This object specifies the type of the address specified by
        ccsBMAIpAddr." 
    ::= { ccsBMATableEntry 2 }

ccsBMAIpAddr OBJECT-TYPE
    SYNTAX          InetAddress
    MAX-ACCESS      not-accessible
    STATUS          current
    DESCRIPTION
        "The IP address of a BMA." 
    ::= { ccsBMATableEntry 3 }

ccsBMAPort OBJECT-TYPE
    SYNTAX          InetPortNumber
    MAX-ACCESS      not-accessible
    STATUS          current
    DESCRIPTION
        "The UDP port of a BMA." 
    ::= { ccsBMATableEntry 4 }

ccsBMAPriority OBJECT-TYPE
    SYNTAX          CcsServerPriority
    MAX-ACCESS      read-create
    STATUS          current
    DESCRIPTION
        "The activation priority of a BMA. BMAs are activated
        in highest priority order. If multiple BMAs are active for
        load sharing, the highest priority BMAs available are 
        activated. If an active BMA fails, the next highest 
        priority BMA (in 'standby' state) is activated." 
    ::= { ccsBMATableEntry 5 }

ccsBMAState OBJECT-TYPE
    SYNTAX          INTEGER  {
                        standby(1),
                        failed(2),
                        active(3),
                        echowait(4),
                        nawait(5),
                        suspended(6)
                    }
    MAX-ACCESS      read-only
    STATUS          current
    DESCRIPTION
        "States of a billing mediation agent.
        'standby'   - The server is prepared to become active.
        'failed'    - The server has failed to respond to requests.
        'active'    - The server has been activated to receive
                      requests.
        'echowait'  - An echo request to this 
                      billing mediation agent and is waiting 
                      for a response.
        'nawait'    - A node-alive request to this 
                      billing mediation agent and is waiting
                      for a response.
        'suspended' - The server has receive a stop request
                      from the operator." 
    ::= { ccsBMATableEntry 6 }

ccsBMALostRecords OBJECT-TYPE
    SYNTAX          Counter32
    UNITS           "records"
    MAX-ACCESS      read-only
    STATUS          current
    DESCRIPTION
        "Total number of lost records since system initialization
        or the last time the counter wrapped." 
    ::= { ccsBMATableEntry 7 }

ccsBMAHCLostRecords OBJECT-TYPE
    SYNTAX          Counter64
    UNITS           "records"
    MAX-ACCESS      read-only
    STATUS          current
    DESCRIPTION
        "Total number of lost records since system initialization
        or the last time the counter wrapped.

        This object is a 64-bit version of 
        ccsBMALostRecords." 
    ::= { ccsBMATableEntry 8 }

ccsBMATotalSent OBJECT-TYPE
    SYNTAX          Counter32
    UNITS           "records"
    MAX-ACCESS      read-only
    STATUS          current
    DESCRIPTION
        "Total number of records sent to the billing mediation
        agent." 
    ::= { ccsBMATableEntry 9 }

ccsBMAHCTotalSent OBJECT-TYPE
    SYNTAX          Counter64
    UNITS           "records"
    MAX-ACCESS      read-only
    STATUS          current
    DESCRIPTION
        "Total number of records sent to the billing mediation
        agent.

        This object is a 64-bit version of 
        ccsBMATotalSent." 
    ::= { ccsBMATableEntry 10 }

ccsBMAFailAck OBJECT-TYPE
    SYNTAX          Counter32
    UNITS           "acknowledgements"
    MAX-ACCESS      read-only
    STATUS          current
    DESCRIPTION
        "Number of acknowledgments received from the
        billing mediation agent for which there are no
        outstanding requests." 
    ::= { ccsBMATableEntry 11 }

ccsBMAHCFailAck OBJECT-TYPE
    SYNTAX          Counter64
    UNITS           "acknowledgements"
    MAX-ACCESS      read-only
    STATUS          current
    DESCRIPTION
        "Number of acknowledgments received from the
        billing mediation agent for which there are no
        outstanding requests.

        This object is a 64-bit version of 
        ccsBMAFailAck." 
    ::= { ccsBMATableEntry 12 }

ccsBMAOutstanding OBJECT-TYPE
    SYNTAX          Gauge32
    UNITS           "messages"
    MAX-ACCESS      read-only
    STATUS          current
    DESCRIPTION
        "Current number of messages waiting to be ACKed." 
    ::= { ccsBMATableEntry 13 }

ccsBMAHighWater OBJECT-TYPE
    SYNTAX          Gauge32
    UNITS           "messages"
    MAX-ACCESS      read-create
    STATUS          current
    DESCRIPTION
        "The highest number of messages waiting for ACKs as reported
        by ccsBMAOutstanding object since object was reset as indicated
        by ccsBMAHighWaterResetTime.  The only write operation allowed 
        is to reset the value to 0." 
    ::= { ccsBMATableEntry 14 }

ccsBMAHighWaterResetTime OBJECT-TYPE
    SYNTAX          TimeStamp
    MAX-ACCESS      read-only
    STATUS          current
    DESCRIPTION
        "The time stamp at which the ccsBMAHighWater object was
        last reset to 0." 
    ::= { ccsBMATableEntry 15 }

ccsBMABadRecord OBJECT-TYPE
    SYNTAX          Counter32
    UNITS           "records"
    MAX-ACCESS      read-only
    STATUS          current
    DESCRIPTION
        "The number of bad records received. These are records
        in which an error was detected while attempting to
        decode the contents." 
    ::= { ccsBMATableEntry 16 }

ccsBMAHCBadRecord OBJECT-TYPE
    SYNTAX          Counter64
    UNITS           "records"
    MAX-ACCESS      read-only
    STATUS          current
    DESCRIPTION
        "The number of bad records received. These are records
        in which an error was detected while attempting to
        decode the contents.

        This object is a 64-bit version of 
        ccsBMABadRecord." 
    ::= { ccsBMATableEntry 17 }

ccsBMARetransmit OBJECT-TYPE
    SYNTAX          Counter32
    UNITS           "messages"
    MAX-ACCESS      read-only
    STATUS          current
    DESCRIPTION
        "The number of messages retransmitted to the billing
        mediation agent." 
    ::= { ccsBMATableEntry 18 }

ccsBMAHCRetransmit OBJECT-TYPE
    SYNTAX          Counter64
    UNITS           "messages"
    MAX-ACCESS      read-only
    STATUS          current
    DESCRIPTION
        "The number of messages retransmitted to the billing
        mediation agent.

        This object is a 64-bit version of 
        ccsBMARetransmit." 
    ::= { ccsBMATableEntry 19 }

ccsBMARowStatus OBJECT-TYPE
    SYNTAX          RowStatus
    MAX-ACCESS      read-create
    STATUS          current
    DESCRIPTION
        "This object is used by the manager to create
        or delete the row entry in the ccsBMATable
        following the RowStatus textual convention.

        This row can be deleted regardless of the value
        of ccsBMAState. Requests queued for the deleted
        BMA are requeued to another BMA." 
    ::= { ccsBMATableEntry 20 }

ccsBMAPacketRate OBJECT-TYPE
    SYNTAX          Gauge32
    UNITS           "packets"
    MAX-ACCESS      read-only
    STATUS          current
    DESCRIPTION
        "Number of packets sent to the BMA per
        second calculated over the interval 
        indicated by ccsgsGTPBMARateInterval object." 
    ::= { ccsBMATableEntry 21 }

ccsBMAAckRate OBJECT-TYPE
    SYNTAX          Gauge32
    UNITS           "acknowledgments"
    MAX-ACCESS      read-only
    STATUS          current
    DESCRIPTION
        "Number of acknowledgments received from
        the BMA per second calculated over the interval 
        indicated by ccsgsGTPBMARateInterval object." 
    ::= { ccsBMATableEntry 22 }
 

-- *************************************************************
-- *                                                           *
-- *      Table of Content Billing Quota Managers              *
-- *                                                           *
-- *************************************************************

ccsQuotaMgrTable OBJECT-TYPE
    SYNTAX          SEQUENCE OF CcsQuotaMgrTableEntry 
    MAX-ACCESS      not-accessible
    STATUS          current
    DESCRIPTION
        "Table of quota managers. Columnar objects can
        be modified when the row is 'active'. Rows can be created
        and destroyed. Entries are added to this table via 
        ccsQuotaMgrRowStatus in accordance with the RowStatus
        convention."
    ::= { ccsStats 4 }

ccsQuotaMgrTableEntry OBJECT-TYPE
    SYNTAX          CcsQuotaMgrTableEntry
    MAX-ACCESS      not-accessible
    STATUS          current
    DESCRIPTION
        "Entry that defines parameters for a quota manager.

        entPhysicalIndex identifies the entity that
        that provides the content services."
    INDEX           {
                        entPhysicalIndex,
                        ccsQuotaMgrVrfName,
                        ccsQuotaMgrIpAddrType,
                        ccsQuotaMgrIpAddr,
                        ccsQuotaMgrPort
                    } 
    ::= { ccsQuotaMgrTable 1 }

CcsQuotaMgrTableEntry ::= SEQUENCE {
        ccsQuotaMgrVrfName            MplsVpnId,
        ccsQuotaMgrIpAddrType         InetAddressType,
        ccsQuotaMgrIpAddr             InetAddress,
        ccsQuotaMgrPort               InetPortNumber,
        ccsQuotaMgrPriority           CcsServerPriority,
        ccsQuotaMgrState              INTEGER,
        ccsQuotaMgrLostRecords        Counter32,
        ccsQuotaMgrHCLostRecords      Counter64,
        ccsQuotaMgrTotalSent          Counter32,
        ccsQuotaMgrHCTotalSent        Counter64,
        ccsQuotaMgrFailAck            Counter32,
        ccsQuotaMgrHCFailAck          Counter64,
        ccsQuotaMgrOutstanding        Gauge32,
        ccsQuotaMgrHighWater          Gauge32,
        ccsQuotaMgrHighWaterResetTime TimeStamp,
        ccsQuotaMgrBadRecord          Counter32,
        ccsQuotaMgrHCBadRecord        Counter64,
        ccsQuotaMgrRetransmit         Counter32,
        ccsQuotaMgrHCRetransmit       Counter64,
        ccsQuotaMgrRowStatus          RowStatus,
        ccsQuotaMgrPacketRate         Gauge32,
        ccsQuotaMgrAckRate            Gauge32
}

ccsQuotaMgrVrfName OBJECT-TYPE
    SYNTAX          MplsVpnId
    MAX-ACCESS      not-accessible
    STATUS          current
    DESCRIPTION
        "Name of the VRF over which communication with
        Quota Server occurs.  If no VRF is specified, the
        global routing table is used." 
    ::= { ccsQuotaMgrTableEntry 1 }

ccsQuotaMgrIpAddrType OBJECT-TYPE
    SYNTAX          InetAddressType
    MAX-ACCESS      not-accessible
    STATUS          current
    DESCRIPTION
        "This object specifies the type of the address specified by
        ccsQuotaMgrIpAddr." 
    ::= { ccsQuotaMgrTableEntry 2 }

ccsQuotaMgrIpAddr OBJECT-TYPE
    SYNTAX          InetAddress
    MAX-ACCESS      not-accessible
    STATUS          current
    DESCRIPTION
        "The IP address of a quota manager." 
    ::= { ccsQuotaMgrTableEntry 3 }

ccsQuotaMgrPort OBJECT-TYPE
    SYNTAX          InetPortNumber
    MAX-ACCESS      not-accessible
    STATUS          current
    DESCRIPTION
        "The UDP port of a quota manager." 
    ::= { ccsQuotaMgrTableEntry 4 }

ccsQuotaMgrPriority OBJECT-TYPE
    SYNTAX          CcsServerPriority
    MAX-ACCESS      read-create
    STATUS          current
    DESCRIPTION
        "The priority of a quota manager." 
    ::= { ccsQuotaMgrTableEntry 5 }

ccsQuotaMgrState OBJECT-TYPE
    SYNTAX          INTEGER  {
                        standby(1),
                        failed(2),
                        active(3),
                        echowait(4),
                        nawait(5),
                        suspended(6)
                    }
    MAX-ACCESS      read-only
    STATUS          current
    DESCRIPTION
        "States of a quota manager:
        'standby'   - The QuotaMgr is prepared to become active.
        'failed'    - The QuotaMgr has failed to respond to
                      requests.
        'active'    - The QuotaMgr has been activated to receive
                      requests.
        'echowait'  - An echo request to this QuotaMgr
                      and is waiting for a response.
        'nawait'    - A node-alive request to this 
                      QuotaMgr and is waiting for a response. 
        'suspended' - The QuotaMgr has receive a stop request
                      from the operator." 
    ::= { ccsQuotaMgrTableEntry 6 }

ccsQuotaMgrLostRecords OBJECT-TYPE
    SYNTAX          Counter32
    UNITS           "records"
    MAX-ACCESS      read-only
    STATUS          current
    DESCRIPTION
        "Total number of lost records since system initialization
        or the last time the counter wrapped." 
    ::= { ccsQuotaMgrTableEntry 7 }

ccsQuotaMgrHCLostRecords OBJECT-TYPE
    SYNTAX          Counter64
    UNITS           "records"
    MAX-ACCESS      read-only
    STATUS          current
    DESCRIPTION
        "Total number of lost records since system initialization
        or the last time the counter wrapped.

         This object is a 64-bit version of 
        ccsQuotaMgrLostRecords." 
    ::= { ccsQuotaMgrTableEntry 8 }

ccsQuotaMgrTotalSent OBJECT-TYPE
    SYNTAX          Counter32
    UNITS           "records"
    MAX-ACCESS      read-only
    STATUS          current
    DESCRIPTION
        "Total number of records sent to the quota manager." 
    ::= { ccsQuotaMgrTableEntry 9 }

ccsQuotaMgrHCTotalSent OBJECT-TYPE
    SYNTAX          Counter64
    UNITS           "records"
    MAX-ACCESS      read-only
    STATUS          current
    DESCRIPTION
        "Total number of records sent to the quota manager.

        This object is a 64-bit version of 
        ccsQuotaMgrTotalSent." 
    ::= { ccsQuotaMgrTableEntry 10 }

ccsQuotaMgrFailAck OBJECT-TYPE
    SYNTAX          Counter32
    UNITS           "acknowledgements"
    MAX-ACCESS      read-only
    STATUS          current
    DESCRIPTION
        "Number of acknowledgments received from the
        quota manager for which there are no requests." 
    ::= { ccsQuotaMgrTableEntry 11 }

ccsQuotaMgrHCFailAck OBJECT-TYPE
    SYNTAX          Counter64
    UNITS           "acknowledgements"
    MAX-ACCESS      read-only
    STATUS          current
    DESCRIPTION
        "Number of acknowledgments received from the
        quota manager for which there are no requests.

        This object is a 64-bit version of 
        ccsQuotaMgrFailAck." 
    ::= { ccsQuotaMgrTableEntry 12 }

ccsQuotaMgrOutstanding OBJECT-TYPE
    SYNTAX          Gauge32
    UNITS           "messages"
    MAX-ACCESS      read-only
    STATUS          current
    DESCRIPTION
        "Current number of messages waiting to be ACKed." 
    ::= { ccsQuotaMgrTableEntry 13 }

ccsQuotaMgrHighWater OBJECT-TYPE
    SYNTAX          Gauge32
    UNITS           "messages"
    MAX-ACCESS      read-create
    STATUS          current
    DESCRIPTION
        "The highest number of messages waiting for ACKs as reported
        by ccsQuotaMgrOutstanding object since object was reset as indicated
        by ccsQuotaMgrHighWaterResetTime.  The only write operation allowed 
        is to reset the value to 0." 
    ::= { ccsQuotaMgrTableEntry 14 }

ccsQuotaMgrHighWaterResetTime OBJECT-TYPE
    SYNTAX          TimeStamp
    MAX-ACCESS      read-only
    STATUS          current
    DESCRIPTION
        "The time stamp at which the ccsgsUserHighWater object was
        last reset to 0." 
    ::= { ccsQuotaMgrTableEntry 15 }

ccsQuotaMgrBadRecord OBJECT-TYPE
    SYNTAX          Counter32
    UNITS           "records"
    MAX-ACCESS      read-only
    STATUS          current
    DESCRIPTION
        "The number of bad records received. These are records
        in which the an error detected while attempting to
        decode the contents." 
    ::= { ccsQuotaMgrTableEntry 16 }

ccsQuotaMgrHCBadRecord OBJECT-TYPE
    SYNTAX          Counter64
    UNITS           "records"
    MAX-ACCESS      read-only
    STATUS          current
    DESCRIPTION
        "The number of bad records received. These are records
        in which the an error detected while attempting to
        decode the contents.

        This object is a 64-bit version of 
        ccsQuotaMgrBadRecord." 
    ::= { ccsQuotaMgrTableEntry 17 }

ccsQuotaMgrRetransmit OBJECT-TYPE
    SYNTAX          Counter32
    UNITS           "messages"
    MAX-ACCESS      read-only
    STATUS          current
    DESCRIPTION
        "The number of messages retransmitted to the billing
        mediation agent." 
    ::= { ccsQuotaMgrTableEntry 18 }

ccsQuotaMgrHCRetransmit OBJECT-TYPE
    SYNTAX          Counter64
    UNITS           "messages"
    MAX-ACCESS      read-only
    STATUS          current
    DESCRIPTION
        "The number of messages retransmitted to the billing
        mediation agent.

        This object is a 64-bit version of 
        ccsQuotaMgrRetransmit." 
    ::= { ccsQuotaMgrTableEntry 19 }

ccsQuotaMgrRowStatus OBJECT-TYPE
    SYNTAX          RowStatus
    MAX-ACCESS      read-create
    STATUS          current
    DESCRIPTION
        "This object is used by the manager to create
        or delete the row entry in the ccsQuotaMgrTable
        following the RowStatus textual convention. 

        For the prepaid billing
        function, at least one QuotaMgr must be available.
        Therefore, deletion of the last
        QuotaMgr causes all accounting processing to switch
        to post-paid billing.

        This row can be deleted regardless of the value
        of ccsQuotaMgrState. Requests queued for the deleted
        QuotaMgr are requeued to another QuotaMgr if one is
        available. If no QuotaMgr is available, processing
        reverts to post-paid billing." 
    ::= { ccsQuotaMgrTableEntry 20 }

ccsQuotaMgrPacketRate OBJECT-TYPE
    SYNTAX          Gauge32
    UNITS           "packets"
    MAX-ACCESS      read-only
    STATUS          current
    DESCRIPTION
        "Number of packets sent to the Quota Manager
        per second calculated over the interval 
        indicated by ccsgsGTPQuotaMgrRateInterval object." 
    ::= { ccsQuotaMgrTableEntry 21 }

ccsQuotaMgrAckRate OBJECT-TYPE
    SYNTAX          Gauge32
    UNITS           "acknowledgments"
    MAX-ACCESS      read-only
    STATUS          current
    DESCRIPTION
        "Number of acknowledgments received from the
        Quota Manager per second calculated over the interval 
        indicated by ccsgsGTPQuotaMgrRateInterval object." 
    ::= { ccsQuotaMgrTableEntry 22 }
 

ccsLoadStatistics  OBJECT IDENTIFIER
    ::= { ccsStats 5 }

-- *************************************************************
-- *                                                           *
-- *      Table of Protocol Stats                              *
-- *                                                           *
-- *************************************************************

ccsProtocolStatsTable OBJECT-TYPE
    SYNTAX          SEQUENCE OF CcsProtocolStatsEntry 
    MAX-ACCESS      not-accessible
    STATUS          current
    DESCRIPTION
        "This table contains the traffic related statistics for two
        categories of protocols. The first category of protocols are
        identified using the protocol handlers of the entity which
        provides the content services. These typically includes
        protocols like http, ftp, rtsp, sip, pop3, imap, smtp, wap and dns
        which use well-known ports and for which deep packet inspection
        upto the application layer has been performed. The second
        category contains those protocols which have been identified
        using the NBAR classification engine and are known as NBAR
        protocols. These typically consist of the various peer-to-peer
        (P2P) protocols which do not use a standard port range.
        This table is indexed on entPhysicalIndex which identifies the
        entity that provides the content services, ccspsInspectionMethod
        which denotes the type of inspection method used to identify the
        protocol, and ccspsProtocolName which is the name of the
        protocol."
    ::= { ccsStats 6 }

ccsProtocolStatsEntry OBJECT-TYPE
    SYNTAX          CcsProtocolStatsEntry
    MAX-ACCESS      not-accessible
    STATUS          current
    DESCRIPTION
        "Each row in this table contains the traffic related statistics
        for a supported application layer protocol.
        An entry is added in this table when the traffic for a given
        protocol passes for the first time through the entity which
        provides the content services. An entry is deleted from this
        table when the corresponding entity denoted by the
        entPhysicalIndex is removed from the entityMIB."
    INDEX           {
                        entPhysicalIndex,
                        ccspsInspectionMethod,
                        ccspsProtocolName
                    } 
    ::= { ccsProtocolStatsTable 1 }

CcsProtocolStatsEntry ::= SEQUENCE {
        ccspsInspectionMethod                   INTEGER,
        ccspsProtocolName                       SnmpAdminString,
        ccspsTransaction                        Counter32,
        ccspsHCTransaction                      Counter64,
        ccspsTransactionRate                    Gauge32,
        ccspsTransactionRateHighWater           Gauge32,
        ccspsTransactionRateHighWaterResetTime  TimeStamp,
        ccspsTransactionRateHighWaterTime       TimeStamp,
        ccspsSubOutPackets                      Counter32,
        ccspsHCSubOutPackets                    Counter64,
        ccspsSubOutPacketRate                   Gauge32,
        ccspsSubOutPacketRateHighWater          Gauge32,
        ccspsSubOutPacketRateHighWaterResetTime TimeStamp,
        ccspsSubOutPacketRateHighWaterTime      TimeStamp,
        ccspsNetOutPackets                      Counter32,
        ccspsHCNetOutPackets                    Counter64,
        ccspsNetOutPacketRate                   Gauge32,
        ccspsNetOutPacketRateHighWater          Gauge32,
        ccspsNetOutPacketRateHighWaterResetTime TimeStamp,
        ccspsNetOutPacketRateHighWaterTime      TimeStamp,
        ccspsSubOutBytes                        Counter32,
        ccspsHCSubOutBytes                      Counter64,
        ccspsSubOutBitRate                      Gauge32,
        ccspsSubOutBitRateHighWater             Gauge32,
        ccspsSubOutBitRateHighWaterResetTime    TimeStamp,
        ccspsSubOutBitRateHighWaterTime         TimeStamp,
        ccspsNetOutBytes                        Counter32,
        ccspsHCNetOutBytes                      Counter64,
        ccspsNetOutBitRate                      Gauge32,
        ccspsNetOutBitRateHighWater             Gauge32,
        ccspsNetOutBitRateHighWaterResetTime    TimeStamp,
        ccspsNetOutBitRateHighWaterTime         TimeStamp
}

ccspsInspectionMethod OBJECT-TYPE
    SYNTAX          INTEGER  {
                        system(1),
                        nbar(2)
                    }
    MAX-ACCESS      not-accessible
    STATUS          current
    DESCRIPTION
        "This object denotes the type of inspection method used to
        identify the protocol:
        'system' - Inspection method used for protocols which have been
        identified using the protocol handler of the entity which
        provides the content services.
        'nbar' - Inspection method used for NBAR protocols which have
        been identified using the NBAR classification engine." 
    ::= { ccsProtocolStatsEntry 1 }

ccspsProtocolName OBJECT-TYPE
    SYNTAX          SnmpAdminString (SIZE  (1..64))
    MAX-ACCESS      not-accessible
    STATUS          current
    DESCRIPTION
        "The value of the protocol name is the case sensitive protocol
        name used in the configuration of the entity which provides the
        content services. This protocol name should be consistent
        between other management interfaces that use a string identifier
        for the protocol. For example, this protocol name should match
        the protocol name options available through the CLI." 
    ::= { ccsProtocolStatsEntry 2 }

ccspsTransaction OBJECT-TYPE
    SYNTAX          Counter32
    UNITS           "transactions"
    MAX-ACCESS      read-only
    STATUS          current
    DESCRIPTION
        "Total number of transactions for a given protocol. The
        definition of a transaction varies according to the type of
        protocol." 
    ::= { ccsProtocolStatsEntry 3 }

ccspsHCTransaction OBJECT-TYPE
    SYNTAX          Counter64
    UNITS           "transactions"
    MAX-ACCESS      read-only
    STATUS          current
    DESCRIPTION
        "Total number of transactions for a given protocol. This object is
        a 64-bit version of ccspsTransaction." 
    ::= { ccsProtocolStatsEntry 4 }

ccspsTransactionRate OBJECT-TYPE
    SYNTAX          Gauge32
    UNITS           "transactions per second"
    MAX-ACCESS      read-only
    STATUS          current
    DESCRIPTION
        "Number of transactions per second for the given protocol." 
    ::= { ccsProtocolStatsEntry 5 }

ccspsTransactionRateHighWater OBJECT-TYPE
    SYNTAX          Gauge32
    UNITS           "transactions per second"
    MAX-ACCESS      read-write
    STATUS          current
    DESCRIPTION
        "The highest number of transactions per second as reported by
        ccspsTransactionRate. The only write operation allowed is to
        reset the value to 0." 
    ::= { ccsProtocolStatsEntry 6 }

ccspsTransactionRateHighWaterResetTime OBJECT-TYPE
    SYNTAX          TimeStamp
    MAX-ACCESS      read-only
    STATUS          current
    DESCRIPTION
        "The time stamp at which the transactions per second as indicated
        by ccspsTransactionRate was last reset to 0." 
    ::= { ccsProtocolStatsEntry 7 }

ccspsTransactionRateHighWaterTime OBJECT-TYPE
    SYNTAX          TimeStamp
    MAX-ACCESS      read-only
    STATUS          current
    DESCRIPTION
        "The time stamp at which the transactions per second as indicated
        by ccspsTransactionRate was maximum." 
    ::= { ccsProtocolStatsEntry 8 }

ccspsSubOutPackets OBJECT-TYPE
    SYNTAX          Counter32
    UNITS           "packets"
    MAX-ACCESS      read-only
    STATUS          current
    DESCRIPTION
        "Total number of outgoing subscriber packets. Outgoing
        subscriber packets are the packets going from the subscriber to
        the network through the entity which provides the content
        services." 
    ::= { ccsProtocolStatsEntry 9 }

ccspsHCSubOutPackets OBJECT-TYPE
    SYNTAX          Counter64
    UNITS           "packets"
    MAX-ACCESS      read-only
    STATUS          current
    DESCRIPTION
        "Total number of outgoing subscriber packets. This object is a
        64-bit version of ccspsSubOutPackets." 
    ::= { ccsProtocolStatsEntry 10 }

ccspsSubOutPacketRate OBJECT-TYPE
    SYNTAX          Gauge32
    UNITS           "packets per second"
    MAX-ACCESS      read-only
    STATUS          current
    DESCRIPTION
        "Number of outgoing subscriber packets per second." 
    ::= { ccsProtocolStatsEntry 11 }

ccspsSubOutPacketRateHighWater OBJECT-TYPE
    SYNTAX          Gauge32
    UNITS           "packets per second"
    MAX-ACCESS      read-write
    STATUS          current
    DESCRIPTION
        "The highest number of outgoing subscriber packets per second as
        reported by ccspsSubOutPacketRate. The only write operation
        allowed is to reset the value to 0." 
    ::= { ccsProtocolStatsEntry 12 }

ccspsSubOutPacketRateHighWaterResetTime OBJECT-TYPE
    SYNTAX          TimeStamp
    MAX-ACCESS      read-only
    STATUS          current
    DESCRIPTION
        "The time stamp at which the outgoing subscriber packets per
        second as indicated by ccspsSubOutPacketRate was last reset to
        0." 
    ::= { ccsProtocolStatsEntry 13 }

ccspsSubOutPacketRateHighWaterTime OBJECT-TYPE
    SYNTAX          TimeStamp
    MAX-ACCESS      read-only
    STATUS          current
    DESCRIPTION
        "The time stamp at which the packets per second as indicated by
        ccspsSubOutPacketRate was maximum." 
    ::= { ccsProtocolStatsEntry 14 }

ccspsNetOutPackets OBJECT-TYPE
    SYNTAX          Counter32
    UNITS           "packets"
    MAX-ACCESS      read-only
    STATUS          current
    DESCRIPTION
        "Total number of outgoing network packets. Outgoing network
        packet are the packets going from the network to the subscriber
        through the entity which provides the content services." 
    ::= { ccsProtocolStatsEntry 15 }

ccspsHCNetOutPackets OBJECT-TYPE
    SYNTAX          Counter64
    UNITS           "packets"
    MAX-ACCESS      read-only
    STATUS          current
    DESCRIPTION
        "Total number of outgoing network packets. This object is a
        64-bit version of ccspsNetOutPackets." 
    ::= { ccsProtocolStatsEntry 16 }

ccspsNetOutPacketRate OBJECT-TYPE
    SYNTAX          Gauge32
    UNITS           "packets per second"
    MAX-ACCESS      read-only
    STATUS          current
    DESCRIPTION
        "Number of outgoing network packets per second." 
    ::= { ccsProtocolStatsEntry 17 }

ccspsNetOutPacketRateHighWater OBJECT-TYPE
    SYNTAX          Gauge32
    UNITS           "packets per second"
    MAX-ACCESS      read-write
    STATUS          current
    DESCRIPTION
        "The highest number of outgoing network packets per second as
        reported by ccspsNetOutPacketRate. The only write operation
        allowed is to reset the value to 0." 
    ::= { ccsProtocolStatsEntry 18 }

ccspsNetOutPacketRateHighWaterResetTime OBJECT-TYPE
    SYNTAX          TimeStamp
    MAX-ACCESS      read-only
    STATUS          current
    DESCRIPTION
        "The time stamp at which the outgoing network packets per second
        as indicated by ccspsNetOutPacketRate was last reset to 0." 
    ::= { ccsProtocolStatsEntry 19 }

ccspsNetOutPacketRateHighWaterTime OBJECT-TYPE
    SYNTAX          TimeStamp
    MAX-ACCESS      read-only
    STATUS          current
    DESCRIPTION
        "The time stamp at which the outgoing network packets per second
        as indicated by ccspsNetOutPacketRate was maximum." 
    ::= { ccsProtocolStatsEntry 20 }

ccspsSubOutBytes OBJECT-TYPE
    SYNTAX          Counter32
    UNITS           "bytes"
    MAX-ACCESS      read-only
    STATUS          current
    DESCRIPTION
        "Total number of outgoing subscriber bytes. Outgoing subscriber
        bytes are the bytes going from the subscriber to the network
        through the entity which provides the content services." 
    ::= { ccsProtocolStatsEntry 21 }

ccspsHCSubOutBytes OBJECT-TYPE
    SYNTAX          Counter64
    UNITS           "bytes"
    MAX-ACCESS      read-only
    STATUS          current
    DESCRIPTION
        "Total number of outgoing subscriber bytes. This object is a
        64-bit version of ccspsSubOutBytes." 
    ::= { ccsProtocolStatsEntry 22 }

ccspsSubOutBitRate OBJECT-TYPE
    SYNTAX          Gauge32
    UNITS           "bits per second"
    MAX-ACCESS      read-only
    STATUS          current
    DESCRIPTION
        "Number of outgoing subscriber bits per second." 
    ::= { ccsProtocolStatsEntry 23 }

ccspsSubOutBitRateHighWater OBJECT-TYPE
    SYNTAX          Gauge32
    UNITS           "bits per second"
    MAX-ACCESS      read-write
    STATUS          current
    DESCRIPTION
        "The highest number of outgoing subscriber bits per second as
        reported by ccspsSubOutBitRate. The only write operation allowed
        is to reset the value to 0." 
    ::= { ccsProtocolStatsEntry 24 }

ccspsSubOutBitRateHighWaterResetTime OBJECT-TYPE
    SYNTAX          TimeStamp
    MAX-ACCESS      read-only
    STATUS          current
    DESCRIPTION
        "The time stamp at which the outgoing subscriber bits per second
        as indicated by ccspsSubOutBitRate was last reset to 0." 
    ::= { ccsProtocolStatsEntry 25 }

ccspsSubOutBitRateHighWaterTime OBJECT-TYPE
    SYNTAX          TimeStamp
    MAX-ACCESS      read-only
    STATUS          current
    DESCRIPTION
        "The time stamp at which the outgoing subscriber bits per second
        as indicated by ccspsSubOutBitRate was maximum." 
    ::= { ccsProtocolStatsEntry 26 }

ccspsNetOutBytes OBJECT-TYPE
    SYNTAX          Counter32
    UNITS           "bytes"
    MAX-ACCESS      read-only
    STATUS          current
    DESCRIPTION
        "Total number of outgoing network bytes. Outgoing network bytes
        are the bytes going from the network to the subscriber through
        the entity which provides the content services." 
    ::= { ccsProtocolStatsEntry 27 }

ccspsHCNetOutBytes OBJECT-TYPE
    SYNTAX          Counter64
    UNITS           "bytes"
    MAX-ACCESS      read-only
    STATUS          current
    DESCRIPTION
        "Total number of outgoing network bytes. This object is a 64-bit
        version of ccspsNetOutBytes." 
    ::= { ccsProtocolStatsEntry 28 }

ccspsNetOutBitRate OBJECT-TYPE
    SYNTAX          Gauge32
    UNITS           "bits per second"
    MAX-ACCESS      read-only
    STATUS          current
    DESCRIPTION
        "Number of outgoing network bits per second." 
    ::= { ccsProtocolStatsEntry 29 }

ccspsNetOutBitRateHighWater OBJECT-TYPE
    SYNTAX          Gauge32
    UNITS           "bits per second"
    MAX-ACCESS      read-write
    STATUS          current
    DESCRIPTION
        "The highest number of outgoing network bits per second as
        reported by ccspsNetOutBitRate. The only write operation allowed
        is to reset the value to 0." 
    ::= { ccsProtocolStatsEntry 30 }

ccspsNetOutBitRateHighWaterResetTime OBJECT-TYPE
    SYNTAX          TimeStamp
    MAX-ACCESS      read-only
    STATUS          current
    DESCRIPTION
        "The time stamp at which the outgoing network bits per second as
        indicated by ccspsNetOutBitRate was last reset to 0." 
    ::= { ccsProtocolStatsEntry 31 }

ccspsNetOutBitRateHighWaterTime OBJECT-TYPE
    SYNTAX          TimeStamp
    MAX-ACCESS      read-only
    STATUS          current
    DESCRIPTION
        "The time stamp at which the outgoing network bits per second as
        indicated by ccspsNetOutBitRate was maximum." 
    ::= { ccsProtocolStatsEntry 32 }
 

-- *************************************************************
-- *                                                           *
-- *      Table of Billing Plan Stats                          *
-- *                                                           *
-- *************************************************************

ccsBillingPlanStatsTable OBJECT-TYPE
    SYNTAX          SEQUENCE OF CcsBillingPlanStatsEntry 
    MAX-ACCESS      not-accessible
    STATUS          current
    DESCRIPTION
        "This table contains the statistics of subscribers for
        all configured Billing Plans."
    ::= { ccsStats 7 }

ccsBillingPlanStatsEntry OBJECT-TYPE
    SYNTAX          CcsBillingPlanStatsEntry
    MAX-ACCESS      not-accessible
    STATUS          current
    DESCRIPTION
        "Each entry in this table contains subscriber statistics related
        to Billing Plan. A billing plan is a set of services. An entry
        is created in the table, whenever a billing  plan is configured.
        An entry will be deleted from the table, whenever a billing plan
        is unconfigured.

        The entPhysicalIndex identifies the entity that provides the 
        content services."
    INDEX           {
                        entPhysicalIndex,
                        ccsbpsBillingPlanName
                    } 
    ::= { ccsBillingPlanStatsTable 1 }

CcsBillingPlanStatsEntry ::= SEQUENCE {
        ccsbpsBillingPlanName        SnmpAdminString,
        ccsbpsSubscribers            Gauge32,
        ccsbpsHCSubscribers          CounterBasedGauge64,
        ccsbpsSubscribersHighWater   Gauge32,
        ccsbpsHCSubscribersHighWater CounterBasedGauge64
}

ccsbpsBillingPlanName OBJECT-TYPE
    SYNTAX          SnmpAdminString (SIZE  (1..64))
    MAX-ACCESS      not-accessible
    STATUS          current
    DESCRIPTION
        "The name of Billing Plan. Billing plan is set of services.
        Each service represents a group of content that is billed
        the same way, such as billing per-click (or per-request)
        or billing per-IP byte, and that shares part of a
        subscriber quota.
        A content configuration contains the following information:
        Layer 3 information that specifies the IP-level details
        of the content.
        Layer 4 information that specifies transport layer parameters,
        such as TCP and User Datagram Protocol (UDP) port numbers."
    ::= { ccsBillingPlanStatsEntry 1 }

ccsbpsSubscribers OBJECT-TYPE
    SYNTAX          Gauge32
    UNITS           "subscribers"
    MAX-ACCESS      read-only
    STATUS          current
    DESCRIPTION
        "Number of subscribers associated with a given
        Billing Plan." 
    ::= { ccsBillingPlanStatsEntry 2 }

ccsbpsHCSubscribers OBJECT-TYPE
    SYNTAX          CounterBasedGauge64
    UNITS           "subscribers"
    MAX-ACCESS      read-only
    STATUS          current
    DESCRIPTION
        "Number of subscribers associated with a given Billing Plan.
        This object is 64-bit version of ccsbpsSubscribers." 
    ::= { ccsBillingPlanStatsEntry 3 }

ccsbpsSubscribersHighWater OBJECT-TYPE
    SYNTAX          Gauge32
    UNITS           "subscribers"
    MAX-ACCESS      read-only
    STATUS          current
    DESCRIPTION
        "The highest number of subscribers associated with a given
        Billing Plan so far, as reported by ccsbpsSubscribers." 
    ::= { ccsBillingPlanStatsEntry 4 }

ccsbpsHCSubscribersHighWater OBJECT-TYPE
    SYNTAX          CounterBasedGauge64
    UNITS           "subscribers"
    MAX-ACCESS      read-only
    STATUS          current
    DESCRIPTION
        "The highest number of subscribers associated with a given
        Billing Plan so far, as reported by ccsbpsHCSubscribers. 
        This object is 64-bit version of ccsbpsSubscribersHighWater." 
    ::= { ccsBillingPlanStatsEntry 5 }
 

-- *************************************************************
-- *                                                           *
-- *      Table of Radius Load Statistics                      *
-- *                                                           *
-- *************************************************************

ccsLoadStatRadiusTable OBJECT-TYPE
    SYNTAX          SEQUENCE OF CcsLoadStatRadiusEntry 
    MAX-ACCESS      not-accessible
    STATUS          current
    DESCRIPTION
        "This table contains the load statistical
        information related to Radius Protocol. All
        the counters in this table are related to 
        outgoing traffic."
    ::= { ccsLoadStatistics 1 }

ccsLoadStatRadiusEntry OBJECT-TYPE
    SYNTAX          CcsLoadStatRadiusEntry
    MAX-ACCESS      not-accessible
    STATUS          current
    DESCRIPTION
        "Each row in this table contains load
        statistics related to Radius.

        entPhysicalIndex identifies the entity 
        that provides the content services."
    INDEX           { entPhysicalIndex } 
    ::= { ccsLoadStatRadiusTable 1 }

CcsLoadStatRadiusEntry ::= SEQUENCE {
        ccsLoadStatRadiusStartAllowed                Counter32,
        ccsLoadStatHCRadiusStartAllowed              Counter64,
        ccsLoadStatRadiusStartAllowedRate            Gauge32,
        ccsLoadStatRadiusStartAllowedRateHighWater   Gauge32,
        ccsLoadStatHCRadiusStartAllowedRateHighWater Counter64,
        ccsLoadStatRadiusStartIPCQueueDepthTolerance Integer32,
        ccsLoadStatRadiusStartDenied                 Counter32,
        ccsLoadStatHCRadiusStartDenied               Counter64,
        ccsLoadStatRadiusStartDenialRate             Gauge32,
        ccsLoadStatRadiusStartDenialRateHighWater    Gauge32,
        ccsLoadStatHCRadiusStartDenialRateHighWater  Counter64
}

ccsLoadStatRadiusStartAllowed OBJECT-TYPE
    SYNTAX          Counter32
    UNITS           "requests"
    MAX-ACCESS      read-only
    STATUS          current
    DESCRIPTION
        "Number of outgoing Radius start requests
        allowed." 
    ::= { ccsLoadStatRadiusEntry 1 }

ccsLoadStatHCRadiusStartAllowed OBJECT-TYPE
    SYNTAX          Counter64
    UNITS           "requests"
    MAX-ACCESS      read-only
    STATUS          current
    DESCRIPTION
        "This object is a 64-bit version of
        ccsLoadStatRadiusStartAllowed." 
    ::= { ccsLoadStatRadiusEntry 2 }

ccsLoadStatRadiusStartAllowedRate OBJECT-TYPE
    SYNTAX          Gauge32
    UNITS           "requests"
    MAX-ACCESS      read-only
    STATUS          current
    DESCRIPTION
        "Number of outgoing Radius start requests
        allowed per second." 
    ::= { ccsLoadStatRadiusEntry 3 }

ccsLoadStatRadiusStartAllowedRateHighWater OBJECT-TYPE
    SYNTAX          Gauge32
    UNITS           "requests"
    MAX-ACCESS      read-only
    STATUS          current
    DESCRIPTION
        "The highest number of outgoing Radius start
        requests allowed per second as reported 
        by ccsLoadStatRadiusStartAllowedRate." 
    ::= { ccsLoadStatRadiusEntry 4 }

ccsLoadStatHCRadiusStartAllowedRateHighWater OBJECT-TYPE
    SYNTAX          Counter64
    UNITS           "requests"
    MAX-ACCESS      read-only
    STATUS          current
    DESCRIPTION
        "This object is a 64-bit version of
        ccsLoadStatRadiusStartAllowedRateHighWater." 
    ::= { ccsLoadStatRadiusEntry 5 }

ccsLoadStatRadiusStartIPCQueueDepthTolerance OBJECT-TYPE
    SYNTAX          Integer32
    MAX-ACCESS      read-only
    STATUS          current
    DESCRIPTION
        "Maximum queue depth for Radius start in
        the IPC queue." 
    ::= { ccsLoadStatRadiusEntry 6 }

ccsLoadStatRadiusStartDenied OBJECT-TYPE
    SYNTAX          Counter32
    UNITS           "requests"
    MAX-ACCESS      read-only
    STATUS          current
    DESCRIPTION
        "Number of outgoing Radius start requests
        denied." 
    ::= { ccsLoadStatRadiusEntry 7 }

ccsLoadStatHCRadiusStartDenied OBJECT-TYPE
    SYNTAX          Counter64
    UNITS           "requests"
    MAX-ACCESS      read-only
    STATUS          current
    DESCRIPTION
        "This object is a 64-bit version of
        ccsLoadStatRadiusStartDenied." 
    ::= { ccsLoadStatRadiusEntry 8 }

ccsLoadStatRadiusStartDenialRate OBJECT-TYPE
    SYNTAX          Gauge32
    UNITS           "requests"
    MAX-ACCESS      read-only
    STATUS          current
    DESCRIPTION
        "Number of outgoing Radius start requests
        denied per second." 
    ::= { ccsLoadStatRadiusEntry 9 }

ccsLoadStatRadiusStartDenialRateHighWater OBJECT-TYPE
    SYNTAX          Gauge32
    UNITS           "requests"
    MAX-ACCESS      read-only
    STATUS          current
    DESCRIPTION
        "The highest number of outgoing Radius start
        requests denied per second as reported 
        by ccsLoadStatRadiusStartDenialRate." 
    ::= { ccsLoadStatRadiusEntry 10 }

ccsLoadStatHCRadiusStartDenialRateHighWater OBJECT-TYPE
    SYNTAX          Counter64
    UNITS           "requests"
    MAX-ACCESS      read-only
    STATUS          current
    DESCRIPTION
        "This object is a 64-bit version of
        ccsLoadStatRadiusStartDenialRateHighWater." 
    ::= { ccsLoadStatRadiusEntry 11 }
 

-- *************************************************************
-- *                                                           *
-- *      Table of User Database Load Statistics               *
-- *                                                           *
-- *************************************************************

ccsLoadStatUserDBTable OBJECT-TYPE
    SYNTAX          SEQUENCE OF CcsLoadStatUserDBEntry 
    MAX-ACCESS      not-accessible
    STATUS          current
    DESCRIPTION
        "This table contains the load statistical
        information related to user database. All
        the counters in this table are related to 
        outgoing traffic."
    ::= { ccsLoadStatistics 2 }

ccsLoadStatUserDBEntry OBJECT-TYPE
    SYNTAX          CcsLoadStatUserDBEntry
    MAX-ACCESS      not-accessible
    STATUS          current
    DESCRIPTION
        "Each row in this table contains load
        statistics related to user database.

        entPhysicalIndex identifies the entity 
        that provides the content services."
    INDEX           { entPhysicalIndex } 
    ::= { ccsLoadStatUserDBTable 1 }

CcsLoadStatUserDBEntry ::= SEQUENCE {
        ccsLoadStatUserDBReqAllowed                Counter32,
        ccsLoadStatHCUserDBReqAllowed              Counter64,
        ccsLoadStatUserDBReqAllowedRate            Gauge32,
        ccsLoadStatUserDBReqAllowedRateHighWater   Gauge32,
        ccsLoadStatHCUserDBReqAllowedRateHighWater Counter64,
        ccsLoadStatUserDBReqIPCQueueDepthTolerance Integer32,
        ccsLoadStatUserDBReqDenied                 Counter32,
        ccsLoadStatHCUserDBReqDenied               Counter64,
        ccsLoadStatUserDBReqDenialRate             Gauge32,
        ccsLoadStatUserDBReqDenialRateHighWater    Gauge32,
        ccsLoadStatHCUserDBReqDenialRateHighWater  Counter64
}

ccsLoadStatUserDBReqAllowed OBJECT-TYPE
    SYNTAX          Counter32
    UNITS           "requests"
    MAX-ACCESS      read-only
    STATUS          current
    DESCRIPTION
        "Number of outgoing UDB requests allowed." 
    ::= { ccsLoadStatUserDBEntry 1 }

ccsLoadStatHCUserDBReqAllowed OBJECT-TYPE
    SYNTAX          Counter64
    UNITS           "requests"
    MAX-ACCESS      read-only
    STATUS          current
    DESCRIPTION
        "This object is a 64-bit version of
        ccsLoadStatUserDBReqAllowed." 
    ::= { ccsLoadStatUserDBEntry 2 }

ccsLoadStatUserDBReqAllowedRate OBJECT-TYPE
    SYNTAX          Gauge32
    UNITS           "requests"
    MAX-ACCESS      read-only
    STATUS          current
    DESCRIPTION
        "Number of outgoing UDB requests allowed
        per second." 
    ::= { ccsLoadStatUserDBEntry 3 }

ccsLoadStatUserDBReqAllowedRateHighWater OBJECT-TYPE
    SYNTAX          Gauge32
    UNITS           "requests"
    MAX-ACCESS      read-only
    STATUS          current
    DESCRIPTION
        "The highest number of outgoing UDB
        requests allowed per second as reported
        by ccsLoadStatUserDBReqAllowedRate." 
    ::= { ccsLoadStatUserDBEntry 4 }

ccsLoadStatHCUserDBReqAllowedRateHighWater OBJECT-TYPE
    SYNTAX          Counter64
    UNITS           "requests"
    MAX-ACCESS      read-only
    STATUS          current
    DESCRIPTION
        "This object is a 64-bit version of
        ccsLoadStatUserDBReqAllowedRateHighWater." 
    ::= { ccsLoadStatUserDBEntry 5 }

ccsLoadStatUserDBReqIPCQueueDepthTolerance OBJECT-TYPE
    SYNTAX          Integer32
    MAX-ACCESS      read-only
    STATUS          current
    DESCRIPTION
        "Maximum queue depth for UDB requests
        in the IPC queue." 
    ::= { ccsLoadStatUserDBEntry 6 }

ccsLoadStatUserDBReqDenied OBJECT-TYPE
    SYNTAX          Counter32
    UNITS           "requests"
    MAX-ACCESS      read-only
    STATUS          current
    DESCRIPTION
        "Number of outgoing UDB requests denied." 
    ::= { ccsLoadStatUserDBEntry 7 }

ccsLoadStatHCUserDBReqDenied OBJECT-TYPE
    SYNTAX          Counter64
    UNITS           "requests"
    MAX-ACCESS      read-only
    STATUS          current
    DESCRIPTION
        "This object is a 64-bit version of
        ccsLoadStatUserDBReqDenied." 
    ::= { ccsLoadStatUserDBEntry 8 }

ccsLoadStatUserDBReqDenialRate OBJECT-TYPE
    SYNTAX          Gauge32
    UNITS           "requests"
    MAX-ACCESS      read-only
    STATUS          current
    DESCRIPTION
        "Number of outgoing UDB requests denied
        per second." 
    ::= { ccsLoadStatUserDBEntry 9 }

ccsLoadStatUserDBReqDenialRateHighWater OBJECT-TYPE
    SYNTAX          Gauge32
    UNITS           "requests"
    MAX-ACCESS      read-only
    STATUS          current
    DESCRIPTION
        "The highest number of outgoing UDB
        requests denied per second as reported
        by ccsLoadStatUserDBReqDenialRate." 
    ::= { ccsLoadStatUserDBEntry 10 }

ccsLoadStatHCUserDBReqDenialRateHighWater OBJECT-TYPE
    SYNTAX          Counter64
    UNITS           "requests"
    MAX-ACCESS      read-only
    STATUS          current
    DESCRIPTION
        "This object is a 64-bit version of
        ccsLoadStatUserDBReqDenialRateHighWater." 
    ::= { ccsLoadStatUserDBEntry 11 }
 

-- *************************************************************
-- *                                                           *
-- *      Table of Session Load Statistics                     *
-- *                                                           *
-- *************************************************************

ccsLoadStatSessionTable OBJECT-TYPE
    SYNTAX          SEQUENCE OF CcsLoadStatSessionEntry 
    MAX-ACCESS      not-accessible
    STATUS          current
    DESCRIPTION
        "This table contains the load statistical
        information related to sessions on the system.
        A session corresponds to a TCP/UDP flow on the
        system."
    ::= { ccsLoadStatistics 3 }

ccsLoadStatSessionEntry OBJECT-TYPE
    SYNTAX          CcsLoadStatSessionEntry
    MAX-ACCESS      not-accessible
    STATUS          current
    DESCRIPTION
        "Each row in this table contains load
        statistics related to sessions on the system.

        entPhysicalIndex identifies the entity 
        that provides the content services."
    INDEX           { entPhysicalIndex } 
    ::= { ccsLoadStatSessionTable 1 }

CcsLoadStatSessionEntry ::= SEQUENCE {
        ccsLoadStatSessionCreateAllowed                Counter32,
        ccsLoadStatHCSessionCreateAllowed              Counter64,
        ccsLoadStatSessionCreateAllowedRate            Gauge32,
        ccsLoadStatSessionCreateAllowedRateHighWater   Gauge32,
        ccsLoadStatHCSessionCreateAllowedRateHighWater Counter64,
        ccsLoadStatSessionCreateIPCQueueDepthTolerance Integer32,
        ccsLoadStatSessionCreateDenied                 Counter32,
        ccsLoadStatHCSessionCreateDenied               Counter64,
        ccsLoadStatSessionCreateDenialRate             Gauge32,
        ccsLoadStatSessionCreateDenialRateHighWater    Gauge32,
        ccsLoadStatHCSessionCreateDenialRateHighWater  Counter64
}

ccsLoadStatSessionCreateAllowed OBJECT-TYPE
    SYNTAX          Counter32
    UNITS           "requests"
    MAX-ACCESS      read-only
    STATUS          current
    DESCRIPTION
        "Number of session creation requests
        allowed on the system." 
    ::= { ccsLoadStatSessionEntry 1 }

ccsLoadStatHCSessionCreateAllowed OBJECT-TYPE
    SYNTAX          Counter64
    UNITS           "requests"
    MAX-ACCESS      read-only
    STATUS          current
    DESCRIPTION
        "This object is a 64-bit version of
        ccsLoadStatSessionCreateAllowed." 
    ::= { ccsLoadStatSessionEntry 2 }

ccsLoadStatSessionCreateAllowedRate OBJECT-TYPE
    SYNTAX          Gauge32
    UNITS           "requests"
    MAX-ACCESS      read-only
    STATUS          current
    DESCRIPTION
        "Number of session creation requests
        allowed per second on the system." 
    ::= { ccsLoadStatSessionEntry 3 }

ccsLoadStatSessionCreateAllowedRateHighWater OBJECT-TYPE
    SYNTAX          Gauge32
    UNITS           "requests"
    MAX-ACCESS      read-only
    STATUS          current
    DESCRIPTION
        "The highest number of session creation
        requests allowed per second as reported 
        by ccsLoadStatSessionCreateAllowedRate." 
    ::= { ccsLoadStatSessionEntry 4 }

ccsLoadStatHCSessionCreateAllowedRateHighWater OBJECT-TYPE
    SYNTAX          Counter64
    UNITS           "requests"
    MAX-ACCESS      read-only
    STATUS          current
    DESCRIPTION
        "This object is a 64-bit version of
        ccsLoadStatSessionCreateAllowedRateHighWater." 
    ::= { ccsLoadStatSessionEntry 5 }

ccsLoadStatSessionCreateIPCQueueDepthTolerance OBJECT-TYPE
    SYNTAX          Integer32
    MAX-ACCESS      read-only
    STATUS          current
    DESCRIPTION
        "Maximum queue depth for session creation
        in the IPC queue." 
    ::= { ccsLoadStatSessionEntry 6 }

ccsLoadStatSessionCreateDenied OBJECT-TYPE
    SYNTAX          Counter32
    UNITS           "requests"
    MAX-ACCESS      read-only
    STATUS          current
    DESCRIPTION
        "Number of session creation requests
        denied on the system." 
    ::= { ccsLoadStatSessionEntry 7 }

ccsLoadStatHCSessionCreateDenied OBJECT-TYPE
    SYNTAX          Counter64
    UNITS           "requests"
    MAX-ACCESS      read-only
    STATUS          current
    DESCRIPTION
        "This object is a 64-bit version of
        ccsLoadStatSessionCreateDenied." 
    ::= { ccsLoadStatSessionEntry 8 }

ccsLoadStatSessionCreateDenialRate OBJECT-TYPE
    SYNTAX          Gauge32
    UNITS           "requests"
    MAX-ACCESS      read-only
    STATUS          current
    DESCRIPTION
        "Number of session creation requests
        denied per second on the system." 
    ::= { ccsLoadStatSessionEntry 9 }

ccsLoadStatSessionCreateDenialRateHighWater OBJECT-TYPE
    SYNTAX          Gauge32
    UNITS           "requests"
    MAX-ACCESS      read-only
    STATUS          current
    DESCRIPTION
        "The highest number of session creation
        requests denied per second as reported by 
        ccsLoadStatSessionCreateDenialRate." 
    ::= { ccsLoadStatSessionEntry 10 }

ccsLoadStatHCSessionCreateDenialRateHighWater OBJECT-TYPE
    SYNTAX          Counter64
    UNITS           "requests"
    MAX-ACCESS      read-only
    STATUS          current
    DESCRIPTION
        "This object is a 64-bit version of
        ccsLoadStatSessionCreateDenialRateHighWater." 
    ::= { ccsLoadStatSessionEntry 11 }
 

-- *************************************************************
-- *                                                           *
-- *      Table of BMA Load Statistics                         *
-- *                                                           *
-- *************************************************************

ccsLoadStatBMATable OBJECT-TYPE
    SYNTAX          SEQUENCE OF CcsLoadStatBMAEntry 
    MAX-ACCESS      not-accessible
    STATUS          current
    DESCRIPTION
        "This table contains the load statistical
        information related to BMA. All the counters
        in this table are related to outgoing traffic."
    ::= { ccsLoadStatistics 4 }

ccsLoadStatBMAEntry OBJECT-TYPE
    SYNTAX          CcsLoadStatBMAEntry
    MAX-ACCESS      not-accessible
    STATUS          current
    DESCRIPTION
        "Each row in this table contains load
        statistics related to BMAs.

        entPhysicalIndex identifies the entity 
        that provides the content services."
    INDEX           { entPhysicalIndex } 
    ::= { ccsLoadStatBMATable 1 }

CcsLoadStatBMAEntry ::= SEQUENCE {
        ccsLoadStatBMAMsgsAllowed                Counter32,
        ccsLoadStatHCBMAMsgsAllowed              Counter64,
        ccsLoadStatBMAMsgsAllowedRate            Gauge32,
        ccsLoadStatBMAMsgsAllowedRateHighWater   Gauge32,
        ccsLoadStatHCBMAMsgsAllowedRateHighWater Counter64,
        ccsLoadStatBMAMsgsIPCQueueDepthTolerance Integer32,
        ccsLoadStatBMAMsgsDenied                 Counter32,
        ccsLoadStatHCBMAMsgsDenied               Counter64,
        ccsLoadStatBMAMsgsDenialRate             Gauge32,
        ccsLoadStatBMAMsgsDenialRateHighWater    Gauge32,
        ccsLoadStatHCBMAMsgsDenialRateHighWater  Counter64
}

ccsLoadStatBMAMsgsAllowed OBJECT-TYPE
    SYNTAX          Counter32
    UNITS           "messages"
    MAX-ACCESS      read-only
    STATUS          current
    DESCRIPTION
        "Number of outgoing BMA messages allowed." 
    ::= { ccsLoadStatBMAEntry 1 }

ccsLoadStatHCBMAMsgsAllowed OBJECT-TYPE
    SYNTAX          Counter64
    UNITS           "messages"
    MAX-ACCESS      read-only
    STATUS          current
    DESCRIPTION
        "This object is a 64-bit version of
        ccsLoadStatBMAMsgsAllowed." 
    ::= { ccsLoadStatBMAEntry 2 }

ccsLoadStatBMAMsgsAllowedRate OBJECT-TYPE
    SYNTAX          Gauge32
    UNITS           "messages"
    MAX-ACCESS      read-only
    STATUS          current
    DESCRIPTION
        "Number of outgoing BMA messages allowed per
        per second." 
    ::= { ccsLoadStatBMAEntry 3 }

ccsLoadStatBMAMsgsAllowedRateHighWater OBJECT-TYPE
    SYNTAX          Gauge32
    UNITS           "messages"
    MAX-ACCESS      read-only
    STATUS          current
    DESCRIPTION
        "The highest number of outgoing BMA messages
        allowed per second as reported by 
        ccsLoadStatBMAMsgsAllowedRate." 
    ::= { ccsLoadStatBMAEntry 4 }

ccsLoadStatHCBMAMsgsAllowedRateHighWater OBJECT-TYPE
    SYNTAX          Counter64
    UNITS           "messages"
    MAX-ACCESS      read-only
    STATUS          current
    DESCRIPTION
        "This object is a 64-bit version of
        ccsLoadStatBMAMsgsAllowedRateHighWater." 
    ::= { ccsLoadStatBMAEntry 5 }

ccsLoadStatBMAMsgsIPCQueueDepthTolerance OBJECT-TYPE
    SYNTAX          Integer32
    MAX-ACCESS      read-only
    STATUS          current
    DESCRIPTION
        "Maximum queue depth for BMA messages
        in the IPC queue." 
    ::= { ccsLoadStatBMAEntry 6 }

ccsLoadStatBMAMsgsDenied OBJECT-TYPE
    SYNTAX          Counter32
    UNITS           "messages"
    MAX-ACCESS      read-only
    STATUS          current
    DESCRIPTION
        "Number of outgoing BMA messages denied." 
    ::= { ccsLoadStatBMAEntry 7 }

ccsLoadStatHCBMAMsgsDenied OBJECT-TYPE
    SYNTAX          Counter64
    UNITS           "messages"
    MAX-ACCESS      read-only
    STATUS          current
    DESCRIPTION
        "This object is a 64-bit version of
        ccsLoadStatBMAMsgsDenied." 
    ::= { ccsLoadStatBMAEntry 8 }

ccsLoadStatBMAMsgsDenialRate OBJECT-TYPE
    SYNTAX          Gauge32
    UNITS           "messages"
    MAX-ACCESS      read-only
    STATUS          current
    DESCRIPTION
        "Number of outgoing BMA messages denied
        per second." 
    ::= { ccsLoadStatBMAEntry 9 }

ccsLoadStatBMAMsgsDenialRateHighWater OBJECT-TYPE
    SYNTAX          Gauge32
    UNITS           "messages"
    MAX-ACCESS      read-only
    STATUS          current
    DESCRIPTION
        "The highest number of outgoing BMA messages
        denied per second as reported by 
        ccsLoadStatBMAMsgsDenialRate." 
    ::= { ccsLoadStatBMAEntry 10 }

ccsLoadStatHCBMAMsgsDenialRateHighWater OBJECT-TYPE
    SYNTAX          Counter64
    UNITS           "messages"
    MAX-ACCESS      read-only
    STATUS          current
    DESCRIPTION
        "This object is a 64-bit version of
        ccsLoadStatBMAMsgsDenialRateHighWater." 
    ::= { ccsLoadStatBMAEntry 11 }
 

-- *************************************************************
-- *                                                           *
-- *      Table of Quota Manager Load Statistics               *
-- *                                                           *
-- *************************************************************

ccsLoadStatQuotaMgrTable OBJECT-TYPE
    SYNTAX          SEQUENCE OF CcsLoadStatQuotaMgrEntry 
    MAX-ACCESS      not-accessible
    STATUS          current
    DESCRIPTION
        "This table contains the load statistical
        information related to QuotaMgr. All 
        the counters in this table are related to 
        outgoing traffic."
    ::= { ccsLoadStatistics 5 }

ccsLoadStatQuotaMgrEntry OBJECT-TYPE
    SYNTAX          CcsLoadStatQuotaMgrEntry
    MAX-ACCESS      not-accessible
    STATUS          current
    DESCRIPTION
        "Each row in this table contains load
        statistics related to QuotaMgr.

        entPhysicalIndex identifies the entity 
        that provides the content services."
    INDEX           { entPhysicalIndex } 
    ::= { ccsLoadStatQuotaMgrTable 1 }

CcsLoadStatQuotaMgrEntry ::= SEQUENCE {
        ccsLoadStatQuotaMgrMsgsAllowed                Counter32,
        ccsLoadStatHCQuotaMgrMsgsAllowed              Counter64,
        ccsLoadStatQuotaMgrMsgsAllowedRate            Gauge32,
        ccsLoadStatQuotaMgrMsgsAllowedRateHighWater   Gauge32,
        ccsLoadStatHCQuotaMgrMsgsAllowedRateHighWater Counter64,
        ccsLoadStatQuotaMgrMsgsIPCQueueDepthTolerance Integer32,
        ccsLoadStatQuotaMgrMsgsDenied                 Counter32,
        ccsLoadStatHCQuotaMgrMsgsDenied               Counter64,
        ccsLoadStatQuotaMgrMsgsDenialRate             Gauge32,
        ccsLoadStatQuotaMgrMsgsDenialRateHighWater    Gauge32,
        ccsLoadStatHCQuotaMgrMsgsDenialRateHighWater  Counter64
}

ccsLoadStatQuotaMgrMsgsAllowed OBJECT-TYPE
    SYNTAX          Counter32
    UNITS           "messages"
    MAX-ACCESS      read-only
    STATUS          current
    DESCRIPTION
        "Number of outgoing messages to QuotaMgr
        allowed." 
    ::= { ccsLoadStatQuotaMgrEntry 1 }

ccsLoadStatHCQuotaMgrMsgsAllowed OBJECT-TYPE
    SYNTAX          Counter64
    UNITS           "messages"
    MAX-ACCESS      read-only
    STATUS          current
    DESCRIPTION
        "This object is a 64-bit version of
        ccsLoadStatQuotaMgrMsgsAllowed." 
    ::= { ccsLoadStatQuotaMgrEntry 2 }

ccsLoadStatQuotaMgrMsgsAllowedRate OBJECT-TYPE
    SYNTAX          Gauge32
    UNITS           "messages"
    MAX-ACCESS      read-only
    STATUS          current
    DESCRIPTION
        "Number of outgoing messages to QuotaMgr
        allowed per second." 
    ::= { ccsLoadStatQuotaMgrEntry 3 }

ccsLoadStatQuotaMgrMsgsAllowedRateHighWater OBJECT-TYPE
    SYNTAX          Gauge32
    UNITS           "messages"
    MAX-ACCESS      read-only
    STATUS          current
    DESCRIPTION
        "The highest number of outgoing messages to
        QuotaMgr allowed per second as reported 
        by ccsLoadStatQuotaMgrMsgsAllowedRate." 
    ::= { ccsLoadStatQuotaMgrEntry 4 }

ccsLoadStatHCQuotaMgrMsgsAllowedRateHighWater OBJECT-TYPE
    SYNTAX          Counter64
    UNITS           "messages"
    MAX-ACCESS      read-only
    STATUS          current
    DESCRIPTION
        "This object is a 64-bit version of
        ccsLoadStatQuotaMgrMsgsAllowedRateHighWater." 
    ::= { ccsLoadStatQuotaMgrEntry 5 }

ccsLoadStatQuotaMgrMsgsIPCQueueDepthTolerance OBJECT-TYPE
    SYNTAX          Integer32
    MAX-ACCESS      read-only
    STATUS          current
    DESCRIPTION
        "Maximum queue depth for messages to
        QuotaMgr in the IPC queue." 
    ::= { ccsLoadStatQuotaMgrEntry 6 }

ccsLoadStatQuotaMgrMsgsDenied OBJECT-TYPE
    SYNTAX          Counter32
    UNITS           "messages"
    MAX-ACCESS      read-only
    STATUS          current
    DESCRIPTION
        "Number of outgoing messages to QuotaMgr
        denied." 
    ::= { ccsLoadStatQuotaMgrEntry 7 }

ccsLoadStatHCQuotaMgrMsgsDenied OBJECT-TYPE
    SYNTAX          Counter64
    UNITS           "messages"
    MAX-ACCESS      read-only
    STATUS          current
    DESCRIPTION
        "This object is a 64-bit version of
        ccsLoadStatQuotaMgrMsgsDenied." 
    ::= { ccsLoadStatQuotaMgrEntry 8 }

ccsLoadStatQuotaMgrMsgsDenialRate OBJECT-TYPE
    SYNTAX          Gauge32
    UNITS           "messages"
    MAX-ACCESS      read-only
    STATUS          current
    DESCRIPTION
        "Number of outgoing messages to QuotaMgr
        denied per second." 
    ::= { ccsLoadStatQuotaMgrEntry 9 }

ccsLoadStatQuotaMgrMsgsDenialRateHighWater OBJECT-TYPE
    SYNTAX          Gauge32
    UNITS           "messages"
    MAX-ACCESS      read-only
    STATUS          current
    DESCRIPTION
        "The highest number of outgoing messages to
        QuotaMgr denied per second as reported 
        by ccsLoadStatQuotaMgrMsgsDenialRate." 
    ::= { ccsLoadStatQuotaMgrEntry 10 }

ccsLoadStatHCQuotaMgrMsgsDenialRateHighWater OBJECT-TYPE
    SYNTAX          Counter64
    UNITS           "messages"
    MAX-ACCESS      read-only
    STATUS          current
    DESCRIPTION
        "This object is a 64-bit version of
        ccsLoadStatQuotaMgrMsgsDenialRateHighWater." 
    ::= { ccsLoadStatQuotaMgrEntry 11 }
 

-- *************************************************************
-- *                                                           *
-- *      Table of GX Event Load Statistics               *
-- *                                                           *
-- *************************************************************

ccsLoadStatGxEventTable OBJECT-TYPE
    SYNTAX          SEQUENCE OF CcsLoadStatGxEventEntry 
    MAX-ACCESS      not-accessible
    STATUS          current
    DESCRIPTION
        "This table contains the load statistical information related to
        Gx Events. A Gx Event is a notification which is generated from
        the PCEF to the PCRF. Examples of these events include exceeding
        of time threshold, volume threshold etc.
        This table is indexed at entPhysicalIndex which identifies the
        entity that provides the content services."
    ::= { ccsLoadStatistics 6 }

ccsLoadStatGxEventEntry OBJECT-TYPE
    SYNTAX          CcsLoadStatGxEventEntry
    MAX-ACCESS      not-accessible
    STATUS          current
    DESCRIPTION
        "Each row in this table contains load statistics related to Gx
        Events. An entry will be added to this table, when the entity
        that provides the content services is identified and modelled in
        entityMIB, and removed when the corresponding entity will be
        deleted from entityMIB."
    INDEX           { entPhysicalIndex } 
    ::= { ccsLoadStatGxEventTable 1 }

CcsLoadStatGxEventEntry ::= SEQUENCE {
        ccsLoadStatGxEventsAllowed                Counter32,
        ccsLoadStatHCGxEventsAllowed              Counter64,
        ccsLoadStatGxEventsAllowedRate            Gauge32,
        ccsLoadStatGxEventsAllowedRateHighWater   Gauge32,
        ccsLoadStatHCGxEventsAllowedRateHighWater Counter64,
        ccsLoadStatGxEventsIPCQueueDepthTolerance Integer32,
        ccsLoadStatGxEventsDenied                 Counter32,
        ccsLoadStatHCGxEventsDenied               Counter64,
        ccsLoadStatGxEventsDenialRate             Gauge32,
        ccsLoadStatGxEventsDenialRateHighWater    Gauge32,
        ccsLoadStatHCGxEventsDenialRateHighWater  Counter64
}

ccsLoadStatGxEventsAllowed OBJECT-TYPE
    SYNTAX          Counter32
    UNITS           "notifications"
    MAX-ACCESS      read-only
    STATUS          current
    DESCRIPTION
        "Number of Gx Events allowed." 
    ::= { ccsLoadStatGxEventEntry 1 }

ccsLoadStatHCGxEventsAllowed OBJECT-TYPE
    SYNTAX          Counter64
    UNITS           "notifications"
    MAX-ACCESS      read-only
    STATUS          current
    DESCRIPTION
        "This object is a 64-bit version of
        ccsLoadStatGxEventsAllowed." 
    ::= { ccsLoadStatGxEventEntry 2 }

ccsLoadStatGxEventsAllowedRate OBJECT-TYPE
    SYNTAX          Gauge32
    UNITS           "notifications per second"
    MAX-ACCESS      read-only
    STATUS          current
    DESCRIPTION
        "Number of Gx Events allowed per second." 
    ::= { ccsLoadStatGxEventEntry 3 }

ccsLoadStatGxEventsAllowedRateHighWater OBJECT-TYPE
    SYNTAX          Gauge32
    UNITS           "notifications per second"
    MAX-ACCESS      read-only
    STATUS          current
    DESCRIPTION
        "The highest number of Gx Events allowed per second
        as reported by ccsLoadStatGxEventsAllowedRate." 
    ::= { ccsLoadStatGxEventEntry 4 }

ccsLoadStatHCGxEventsAllowedRateHighWater OBJECT-TYPE
    SYNTAX          Counter64
    UNITS           "notifications per second"
    MAX-ACCESS      read-only
    STATUS          current
    DESCRIPTION
        "This object is a 64-bit version of
        ccsLoadStatGxEventsAllowedRateHighWater." 
    ::= { ccsLoadStatGxEventEntry 5 }

ccsLoadStatGxEventsIPCQueueDepthTolerance OBJECT-TYPE
    SYNTAX          Integer32
    MAX-ACCESS      read-only
    STATUS          current
    DESCRIPTION
        "Maximum queue depth for Gx Events in the IPC
        queue." 
    ::= { ccsLoadStatGxEventEntry 6 }

ccsLoadStatGxEventsDenied OBJECT-TYPE
    SYNTAX          Counter32
    UNITS           "notifications"
    MAX-ACCESS      read-only
    STATUS          current
    DESCRIPTION
        "Number of Gx Events denied." 
    ::= { ccsLoadStatGxEventEntry 7 }

ccsLoadStatHCGxEventsDenied OBJECT-TYPE
    SYNTAX          Counter64
    UNITS           "notifications"
    MAX-ACCESS      read-only
    STATUS          current
    DESCRIPTION
        "This object is a 64-bit version of
        ccsLoadStatGxEventsDenied." 
    ::= { ccsLoadStatGxEventEntry 8 }

ccsLoadStatGxEventsDenialRate OBJECT-TYPE
    SYNTAX          Gauge32
    UNITS           "notifications per second"
    MAX-ACCESS      read-only
    STATUS          current
    DESCRIPTION
        "Number of Gx Events denied per second." 
    ::= { ccsLoadStatGxEventEntry 9 }

ccsLoadStatGxEventsDenialRateHighWater OBJECT-TYPE
    SYNTAX          Gauge32
    UNITS           "notifications per second"
    MAX-ACCESS      read-only
    STATUS          current
    DESCRIPTION
        "The highest number of Gx Events denied per second
        as reported by ccsLoadStatQuotaMgrMsgsDenialRate." 
    ::= { ccsLoadStatGxEventEntry 10 }

ccsLoadStatHCGxEventsDenialRateHighWater OBJECT-TYPE
    SYNTAX          Counter64
    UNITS           "notifications per second"
    MAX-ACCESS      read-only
    STATUS          current
    DESCRIPTION
        "This object is a 64-bit version of
        ccsLoadStatGxEventsDenialRateHighWater." 
    ::= { ccsLoadStatGxEventEntry 11 }
 

-- *************************************************************
-- *                                                           *
-- *      Notifications Config Table                           *
-- *                                                           *
-- *************************************************************

ccsNotifCfgTable OBJECT-TYPE
    SYNTAX          SEQUENCE OF CcsNotifCfgTableEntry 
    MAX-ACCESS      not-accessible
    STATUS          current
    DESCRIPTION
        "Notification config table."
    ::= { ccsNotifConfig 1 }

ccsNotifCfgTableEntry OBJECT-TYPE
    SYNTAX          CcsNotifCfgTableEntry
    MAX-ACCESS      not-accessible
    STATUS          current
    DESCRIPTION
        "Entry that defines the notification objects.

        entPhysicalIndex identifies the entity that
        that provides the content services."
    INDEX           { entPhysicalIndex } 
    ::= { ccsNotifCfgTable 1 }

CcsNotifCfgTableEntry ::= SEQUENCE {
        ccsBMAStateChangeNotifEnabled          TruthValue,
        ccsQuotaMgrStateChangeNotifEnabled     TruthValue,
        ccsUserDbStateChangeNotifEnabled       TruthValue,
        ccsBMALostRecordEventNotifEnabled      TruthValue,
        ccsQuotaMgrLostRecordEventNotifEnabled TruthValue,
        ccsUserThresholdExceededNotifEnabled   TruthValue,
        ccsAdControlNotifEnabled               TruthValue
}

ccsBMAStateChangeNotifEnabled OBJECT-TYPE
    SYNTAX          TruthValue
    MAX-ACCESS      read-write
    STATUS          current
    DESCRIPTION
        "This object controls the generation of the
        Billing Mediation Agent state change 
        notification (ciscoContentServicesBMAStateChange)

        'true'  Indicates that all BMA state change
                notification is enabled.
        'false' Indicates that notification is disabled."
    DEFVAL          { false } 
    ::= { ccsNotifCfgTableEntry 1 }

ccsQuotaMgrStateChangeNotifEnabled OBJECT-TYPE
    SYNTAX          TruthValue
    MAX-ACCESS      read-write
    STATUS          current
    DESCRIPTION
        "This object controls the generation of the Quota Manager
        state change notification (ciscoContentServicesQuotaMgrStateChange)

        'true'  Indicates that all Quota Manager state change
                notification is enabled.
        'false' Indicates that notification is disabled."
    DEFVAL          { false } 
    ::= { ccsNotifCfgTableEntry 2 }

ccsUserDbStateChangeNotifEnabled OBJECT-TYPE
    SYNTAX          TruthValue
    MAX-ACCESS      read-write
    STATUS          current
    DESCRIPTION
        "This object controls the generation of the User Database Server
        state change notification (ciscoContentServicesUserDbStateChange)

        'true'  Indicates that all User DB state change
                notification is enabled.
        'false' Indicates that notification is disabled."
    DEFVAL          { false } 
    ::= { ccsNotifCfgTableEntry 3 }

ccsBMALostRecordEventNotifEnabled OBJECT-TYPE
    SYNTAX          TruthValue
    MAX-ACCESS      read-write
    STATUS          current
    DESCRIPTION
        "This object controls the generation of the
        Billing Mediation Agent Lost Reocrd 
        notification (ciscoContentServicesBMALostRecordEvent)

        'true'  Indicates that all BMA record lost event
                notification is enabled.
        'false' Indicates that notification is disabled."
    DEFVAL          { false } 
    ::= { ccsNotifCfgTableEntry 4 }

ccsQuotaMgrLostRecordEventNotifEnabled OBJECT-TYPE
    SYNTAX          TruthValue
    MAX-ACCESS      read-write
    STATUS          current
    DESCRIPTION
        "This object controls the generation of the
        Quota Manager Lost Record notification 
        (ciscoContentServicesQuotaMgrLostRecordEvent)

        'true'  Indicates that all Quota Manager record lost event
                notification is enabled.
        'false' Indicates that notification is disabled."
    DEFVAL          { false } 
    ::= { ccsNotifCfgTableEntry 5 }

ccsUserThresholdExceededNotifEnabled OBJECT-TYPE
    SYNTAX          TruthValue
    MAX-ACCESS      read-write
    STATUS          current
    DESCRIPTION
        "This object controls the generation of the
        Users threshold exceeded notification
        (ciscoContentServicesUserThresholdExceeded)

        'true'  Indicates that Users threshold
                exceeded notification is enabled.
        'false' Indicates that notification is disabled."
    DEFVAL          { true } 
    ::= { ccsNotifCfgTableEntry 6 }

ccsAdControlNotifEnabled OBJECT-TYPE
    SYNTAX          TruthValue
    MAX-ACCESS      read-write
    STATUS          current
    DESCRIPTION
        "This object controls the generation of the notifications
        for the AdControl. The alarm and clear notifications are 
        enabled when ccsAdControlNotifEnabled is set to 'true'. 
        The AdControl will start a timer with the interval controlled 
        by ccsAdControlAlarmUpdateTimer for each event. An alarm
        notification will be generated if the error exceeds the 
        alarm threshold within the interval and no such alarm has
        been raised yet. The timer will be restarted after an 
        alarm notification is generated. When the timer expires, 
        a clear notification will be generated if the error is 
        equal to or less than the clear threshold and the 
        alarm exists.

        'true'  Indicates that the notifications are enabled.
        'false' Indicates that notifications are disabled."
    DEFVAL          { false } 
    ::= { ccsNotifCfgTableEntry 7 }
 


-- *************************************************************
-- *                                                           *
-- *      Info for notification                                *
-- *                                                           *
-- *************************************************************

ccsTPIndexNotifInfo OBJECT-TYPE
    SYNTAX          Unsigned32
    MAX-ACCESS      accessible-for-notify
    STATUS          current
    DESCRIPTION
        "This object specifies the Traffic Processor (TP) index." 
    ::= { ccsNotifInfo 1 }

ccsServiceNameNotifInfo OBJECT-TYPE
    SYNTAX          OCTET STRING (SIZE  (1..16))
    MAX-ACCESS      accessible-for-notify
    STATUS          current
    DESCRIPTION
        "This object specifies the Service Name that the notification is
        generated for." 
    ::= { ccsNotifInfo 2 }

ccsContentNameNotifInfo OBJECT-TYPE
    SYNTAX          OCTET STRING (SIZE  (1..15))
    MAX-ACCESS      accessible-for-notify
    STATUS          current
    DESCRIPTION
        "This object specifies the content name." 
    ::= { ccsNotifInfo 3 }

ccsPolicyNameNotifInfo OBJECT-TYPE
    SYNTAX          OCTET STRING (SIZE  (1..16))
    MAX-ACCESS      accessible-for-notify
    STATUS          current
    DESCRIPTION
        "This object specifies the policy name." 
    ::= { ccsNotifInfo 4 }

ccsNetServerIpAddrTypeNotifInfo OBJECT-TYPE
    SYNTAX          InetAddressType
    MAX-ACCESS      accessible-for-notify
    STATUS          current
    DESCRIPTION
        "This object specifies the type of the address specified by
        ccsNetServerIpAddrNotifInfo." 
    ::= { ccsNotifInfo 5 }

ccsNetServerIpAddrNotifInfo OBJECT-TYPE
    SYNTAX          InetAddress
    MAX-ACCESS      accessible-for-notify
    STATUS          current
    DESCRIPTION
        "This object specifies the IP address of the network server." 
    ::= { ccsNotifInfo 6 }

ccsNetServerPortNotifInfo OBJECT-TYPE
    SYNTAX          InetPortNumber
    MAX-ACCESS      accessible-for-notify
    STATUS          current
    DESCRIPTION
        "This object specifies the port number of the network server." 
    ::= { ccsNotifInfo 7 }

ccsSubscriberIpAddrTypeNotifInfo OBJECT-TYPE
    SYNTAX          InetAddressType
    MAX-ACCESS      accessible-for-notify
    STATUS          current
    DESCRIPTION
        "This object specifies the type of the address specified by
        ccsSubscriberIpAddrNotifInfo." 
    ::= { ccsNotifInfo 8 }

ccsSubscriberIpAddrNotifInfo OBJECT-TYPE
    SYNTAX          InetAddress
    MAX-ACCESS      accessible-for-notify
    STATUS          current
    DESCRIPTION
        "This object specifies the IP address of the subscriber." 
    ::= { ccsNotifInfo 9 }

ccsSubscriberPortNotifInfo OBJECT-TYPE
    SYNTAX          InetPortNumber
    MAX-ACCESS      accessible-for-notify
    STATUS          current
    DESCRIPTION
        "This object specifies the port number of the subscriber." 
    ::= { ccsNotifInfo 10 }

ccsNetServerResponseFailCountNotifInfo OBJECT-TYPE
    SYNTAX          Unsigned32
    MAX-ACCESS      accessible-for-notify
    STATUS          current
    DESCRIPTION
        "This object specifies the number of the failed response
        from the network server." 
    ::= { ccsNotifInfo 11 }

ccsNetServerResponseTimeFailCountNotifInfo OBJECT-TYPE
    SYNTAX          Unsigned32
    MAX-ACCESS      accessible-for-notify
    STATUS          current
    DESCRIPTION
        "This object specifies the number of the response for
        the first payload packet from the network server exceeds
        the response time specified by
        ccsNetServerFirstPayloadResponseTime." 
    ::= { ccsNotifInfo 12 }

ccsProtocolParseFailCountNotifInfo OBJECT-TYPE
    SYNTAX          Unsigned32
    MAX-ACCESS      accessible-for-notify
    STATUS          current
    DESCRIPTION
        "This object specifies the number of the errors fail the
        protocol parsing." 
    ::= { ccsNotifInfo 13 }

-- *************************************************************
-- *                                                           *
-- *      Notifications                                        *
-- *                                                           *
-- *************************************************************

ciscoContentServicesBMAStateChange NOTIFICATION-TYPE
    OBJECTS         {
                        ccsBMAState,
                        ccsBMALostRecords,
                        ccsBMATotalSent,
                        ccsBMAFailAck,
                        ccsBMAOutstanding,
                        ccsBMAHighWater,
                        ccsBMABadRecord,
                        ccsBMARetransmit
                    }
    STATUS          current
    DESCRIPTION
        "This notification is issued when ccsBMAStateChangeNotifEnabled
        is set to 'true', and the billing mediation agent changes
        state. There is one exception: No notification is issued
        for state changes involving 'echowait' because this would
        cause an excessive number of notifications."
   ::= { ciscoContentServicesMIBNotifs 1 }

ciscoContentServicesQuotaMgrStateChange NOTIFICATION-TYPE
    OBJECTS         {
                        ccsQuotaMgrState,
                        ccsQuotaMgrLostRecords,
                        ccsQuotaMgrTotalSent,
                        ccsQuotaMgrFailAck,
                        ccsQuotaMgrOutstanding,
                        ccsQuotaMgrHighWater,
                        ccsQuotaMgrBadRecord,
                        ccsQuotaMgrRetransmit
                    }
    STATUS          current
    DESCRIPTION
        "This notification is issued when ccsQuotaMgrStateChangeNotifEnabled
        is set to 'true', and the quota manager changes state. 
        There is one exception: No notification is issued for 
        state changes involving 'echowait' because this would 
        cause an excessive number of notifications."
   ::= { ciscoContentServicesMIBNotifs 2 }

ciscoContentServicesUserDbStateChange NOTIFICATION-TYPE
    OBJECTS         {
                        ccsUserDbState,
                        ccsUserDbRequests,
                        ccsUserDbUidsReturned,
                        ccsUserDbReqResent,
                        ccsUserDbReqTimeouts,
                        ccsUserDbReqErrors
                    }
    STATUS          current
    DESCRIPTION
        "This notification is issued when ccsUserDbStateChangeNotifEnabled
        is set to 'true', and the user database changes state."
   ::= { ciscoContentServicesMIBNotifs 3 }

ciscoContentServicesBMALostRecordEvent NOTIFICATION-TYPE
    OBJECTS         {
                        ccsBMAState,
                        ccsBMALostRecords,
                        ccsBMATotalSent,
                        ccsBMAFailAck,
                        ccsBMAOutstanding,
                        ccsBMAHighWater,
                        ccsBMABadRecord,
                        ccsBMARetransmit
                    }
    STATUS          current
    DESCRIPTION
        "This notification is issued when ccsBMAStateChangeNotifEnabled
        is set to 'true', and accounting records,
        should be sent to the billing mediation agent, must be
        discarded.

        Initially, ccsBMALostRecords is set to 0.
        When a record is discarded, ccsBMALostRecords 
        is incremented, a period timer is started, and this 
        notification is issued. The NMS and the agent save 
        this value. The agent continues to increment 
        ccsBMALostRecords each time a record is lost.  
        When the period timer expires, the agent compares
        the current value of ccsBMALostRecords with
        the previous (saved) value. If the values are equal
        this notification is issued again, signalling to the
        NMS that the condition has been cleared. Otherwise,
        the timer is restarted to monitor the next period.

        When a record is lost and no period timer is active, 
        this notification is issued and the above procedure 
        is repeated."
   ::= { ciscoContentServicesMIBNotifs 4 }

ciscoContentServicesQuotaMgrLostRecordEvent NOTIFICATION-TYPE
    OBJECTS         {
                        ccsQuotaMgrState,
                        ccsQuotaMgrLostRecords,
                        ccsQuotaMgrTotalSent,
                        ccsQuotaMgrFailAck,
                        ccsQuotaMgrOutstanding,
                        ccsQuotaMgrHighWater,
                        ccsQuotaMgrBadRecord,
                        ccsQuotaMgrRetransmit
                    }
    STATUS          current
    DESCRIPTION
        "This notification is issued when ccsQuotaMgrStateChangeNotifEnabled
        is set to 'true', and request records to be sent to the 
        quota manager must be discarded. The processing 
        is the same as described in the description for 
        ccsBMALostRecordEvent."
   ::= { ciscoContentServicesMIBNotifs 5 }

ciscoContentServicesUserThresholdExceeded NOTIFICATION-TYPE
    OBJECTS         {
                        ccsgsUserCurrent,
                        ccsgsUserHighWater,
                        ccsgsUserThreshold
                    }
    STATUS          current
    DESCRIPTION
        "This notification is issued when
        ccsUserThresholdExceededNotifEnabled
        is set to 'true', and when actual users limit
        exceeds threshold which is set by ccsgsUserThreshold."
   ::= { ciscoContentServicesMIBNotifs 6 }

ciscoContentServicesNetServerResponseFailExceeded NOTIFICATION-TYPE
    OBJECTS         {
                        ccsTPIndexNotifInfo,
                        ccsServiceNameNotifInfo,
                        ccsContentNameNotifInfo,
                        ccsPolicyNameNotifInfo,
                        ccsNetServerIpAddrTypeNotifInfo,
                        ccsNetServerIpAddrNotifInfo,
                        ccsNetServerPortNotifInfo,
                        ccsSubscriberIpAddrTypeNotifInfo,
                        ccsSubscriberIpAddrNotifInfo,
                        ccsSubscriberPortNotifInfo,
                        ccsNetServerResponseFailCountNotifInfo,
                        ccsNetServerResponseFailAlarmThreshold,
                        ccsNetServerResponseFailClearThreshold
                    }
    STATUS          current
    DESCRIPTION
        "A notification of this type is generated for the service
        specified by ccsServiceNameNotifInfo when the number of
        failed responses received on the Traffic Processor specified
        by ccsTPIndexNotifInfo from the network server exceeds the 
        alarm threshold ccsNetServerResponseFailAlarmThreshold
        within the interval ccsAdControlAlarmUpdateTimer. The alarm
        is not generated repeatly on the same alarm state.
        The ccsAdControlNotifEnabled has to set to 'true' to generate
        the notification.
        The timer will be restarted after the notification is 
        generated."
   ::= { ciscoContentServicesMIBNotifs 7 }

ciscoContentServicesNetServerResponseTimeExceeded NOTIFICATION-TYPE
    OBJECTS         {
                        ccsTPIndexNotifInfo,
                        ccsServiceNameNotifInfo,
                        ccsContentNameNotifInfo,
                        ccsPolicyNameNotifInfo,
                        ccsNetServerIpAddrTypeNotifInfo,
                        ccsNetServerIpAddrNotifInfo,
                        ccsNetServerPortNotifInfo,
                        ccsSubscriberIpAddrTypeNotifInfo,
                        ccsSubscriberIpAddrNotifInfo,
                        ccsSubscriberPortNotifInfo,
                        ccsNetServerResponseTimeFailCountNotifInfo,
                        ccsNetServerResponseTimeFailAlarmThreshold,
                        ccsNetServerResponseTimeFailClearThreshold
                    }
    STATUS          current
    DESCRIPTION
        "A notification of this type is generated for the service
        specified by ccsServiceNameNotifInfo when the
        number of the responses that are received on the Traffic 
        Processor from the network server and exceed the response
        time (ccsNetServerFirstPayloadResponseTime) for the 
        first payload packet exceeds the alarm theshold
        ccsNetServerResponseTimeFailAlarmThreshold,
        within the interval ccsAdControlAlarmUpdateTimer. The alarm
        is not generated repeatly on the same alarm state.
        The ccsAdControlNotifEnabled has to set to 'true' to generate
        the notification.
        The timer will be restarted after the notification is generated."
   ::= { ciscoContentServicesMIBNotifs 8 }

ciscoContentServicesProtocolParseFailExceeded NOTIFICATION-TYPE
    OBJECTS         {
                        ccsTPIndexNotifInfo,
                        ccsServiceNameNotifInfo,
                        ccsContentNameNotifInfo,
                        ccsPolicyNameNotifInfo,
                        ccsNetServerIpAddrTypeNotifInfo,
                        ccsNetServerIpAddrNotifInfo,
                        ccsNetServerPortNotifInfo,
                        ccsSubscriberIpAddrTypeNotifInfo,
                        ccsSubscriberIpAddrNotifInfo,
                        ccsSubscriberPortNotifInfo,
                        ccsProtocolParseFailCountNotifInfo,
                        ccsProtocolParseFailAlarmThreshold,
                        ccsProtocolParseFailClearThreshold
                    }
    STATUS          current
    DESCRIPTION
        "A notification of this type is generated for the service
        specified by ccsServiceNameNotifInfo when the
        number of errors that are received on the Traffic Processor 
        and fail the protocol parsing exceeds the alarm threshold
        ccsProcolParseFailedAlarmThreshold
        within the interval ccsAdControlAlarmUpdateTimer. The alarm
        is not generated repeatly on the same alarm state.
        The ccsAdControlNotifEnabled has to set to 'true' to generate
        the notification.
        The timer will be restarted after the notification is generated."
   ::= { ciscoContentServicesMIBNotifs 9 }

ciscoContentServicesNetServerResponseFailAlarmCleared NOTIFICATION-TYPE
    OBJECTS         {
                        ccsTPIndexNotifInfo,
                        ccsServiceNameNotifInfo,
                        ccsContentNameNotifInfo,
                        ccsPolicyNameNotifInfo,
                        ccsNetServerIpAddrTypeNotifInfo,
                        ccsNetServerIpAddrNotifInfo,
                        ccsNetServerPortNotifInfo,
                        ccsSubscriberIpAddrTypeNotifInfo,
                        ccsSubscriberIpAddrNotifInfo,
                        ccsSubscriberPortNotifInfo,
                        ccsNetServerResponseFailCountNotifInfo,
                        ccsNetServerResponseFailAlarmThreshold,
                        ccsNetServerResponseFailClearThreshold
                    }
    STATUS          current
    DESCRIPTION
        "A notification of this type is generated for the service
        specified by ccsServiceNameNotifInfo if the number of 
        failed responses received on the Traffic Processor 
        from the network server is equal to or lower than 
        ccsNetServerResponseFailClearThreshold when 
        the timer ccsAdControlAlarmUpdateTimer expires.
        The notification is also generated when the update timer,
        the alarm threshold, or the clear threshold is changed.
        The notification is generated only when the alarm
        (ciscoContentServicesNetServerResponseFailExceeded)
        exists. The ccsAdControlNotifEnabled has to set to 'true'
        to generate the notification.
        The timer will be restarted after the notification is generated."
   ::= { ciscoContentServicesMIBNotifs 10 }

ciscoContentServicesNetServerResponseTimeAlarmCleared NOTIFICATION-TYPE
    OBJECTS         {
                        ccsTPIndexNotifInfo,
                        ccsServiceNameNotifInfo,
                        ccsContentNameNotifInfo,
                        ccsPolicyNameNotifInfo,
                        ccsNetServerIpAddrTypeNotifInfo,
                        ccsNetServerIpAddrNotifInfo,
                        ccsNetServerPortNotifInfo,
                        ccsSubscriberIpAddrTypeNotifInfo,
                        ccsSubscriberIpAddrNotifInfo,
                        ccsSubscriberPortNotifInfo,
                        ccsNetServerResponseTimeFailCountNotifInfo,
                        ccsNetServerResponseTimeFailAlarmThreshold,
                        ccsNetServerResponseTimeFailClearThreshold
                    }
    STATUS          current
    DESCRIPTION
        "A notification of this type is generated for the service
        specified by ccsServiceNameNotifInfo if the number of the 
        responses that are received on the Traffic Processor from 
        the network server and exceed the response time
        (ccsNetServerFirstPayloadResponseTime) for the
        first payload packet is equal to or lower than
        ccsNetServerResponseTimeFailClearThreshold
        when the timer ccsAdControlAlarmUpdateTimer expires.
        The notification is also generated when the update timer,
        the response time, the alarm threshold, or the clear threshold
        is changed. The notification is generated only when the alarm
        (ciscoContentServicesNetServerResponseTimeExceeded) exists,
        The ccsAdControlNotifEnabled has to set to 'true'
        to generate the notification.
        The update timer will be restarted after the notification
        is generated."
   ::= { ciscoContentServicesMIBNotifs 11 }

ciscoContentServicesProtocolParseFailAlarmCleared NOTIFICATION-TYPE
    OBJECTS         {
                        ccsTPIndexNotifInfo,
                        ccsServiceNameNotifInfo,
                        ccsContentNameNotifInfo,
                        ccsPolicyNameNotifInfo,
                        ccsNetServerIpAddrTypeNotifInfo,
                        ccsNetServerIpAddrNotifInfo,
                        ccsNetServerPortNotifInfo,
                        ccsSubscriberIpAddrTypeNotifInfo,
                        ccsSubscriberIpAddrNotifInfo,
                        ccsSubscriberPortNotifInfo,
                        ccsProtocolParseFailCountNotifInfo,
                        ccsProtocolParseFailAlarmThreshold,
                        ccsProtocolParseFailClearThreshold
                    }
    STATUS          current
    DESCRIPTION
        "A notification of this type is generated for the service
        specified by ccsServiceNameNotifInfo if the number of errors
        that are received on the Traffic Processor and fail the 
        protocol parsing is equal to or lower than 
        ccsProcolParseFailedAlarmThreshold
        when the timer ccsAdControlAlarmUpdateTimer expires.
        The notification is also generated when the update timer,
        the alarm threshold, or the clear threshold is changed.
        The notification is generated only when the alarm
        (ciscoContentServicesProtocolParseFailExceeded) exists.
        The ccsAdControlNotifEnabled has to set to 'true'
        to generate the notification.
        The update timer will be restarted after the notification
        is generated."
   ::= { ciscoContentServicesMIBNotifs 12 }
-- *************************************************************
-- *                                                           *
-- *      Conformance Information                              *
-- *                                                           *
-- *************************************************************

ciscoContentServicesMIBCompliances  OBJECT IDENTIFIER
    ::= { ciscoContentServicesMIBConform 1 }

ciscoContentServicesMIBGroups  OBJECT IDENTIFIER
    ::= { ciscoContentServicesMIBConform 2 }


-- compliance statements

ciscoContentServicesMIBCompliance MODULE-COMPLIANCE
    STATUS          deprecated
    DESCRIPTION
        "The compliance statement for entities which implement
        the Cisco Content Services MIB."
    MODULE          -- this module
    MANDATORY-GROUPS {
                        ciscoContentServicesGlobalCfgGroup,
                        ciscoContentServicesGlobalStatsGroup,
                        ciscoContentServicesBMAGroup,
                        ciscoContentServicesQuotaMgrGroup,
                        ciscoContentServicesUserDbGroup,
                        ciscoContentServicesNotifEnableGroup,
                        ciscoContentServicesNotifGroup
                    }

    OBJECT          ccsBMAHighWater
    MIN-ACCESS      read-only
    DESCRIPTION
        "Create/Write access is not required."

    OBJECT          ccsQuotaMgrHighWater
    MIN-ACCESS      read-only
    DESCRIPTION
        "Create/Write access is not required."

    OBJECT          ccsBMAPriority
    MIN-ACCESS      read-only
    DESCRIPTION
        "Create/Write access is not required."

    OBJECT          ccsQuotaMgrPriority
    MIN-ACCESS      read-only
    DESCRIPTION
        "Create/Write access is not required."

    OBJECT          ccsBMARowStatus
    MIN-ACCESS      read-only
    DESCRIPTION
        "Write access is not required."

    OBJECT          ccsQuotaMgrRowStatus
    MIN-ACCESS      read-only
    DESCRIPTION
        "Write access is not required."
    ::= { ciscoContentServicesMIBCompliances 1 }

ciscoContentServicesMIBComplianceRev1 MODULE-COMPLIANCE
    STATUS          deprecated
    DESCRIPTION
        "The compliance statement for entities which implement
        the Cisco Content Services MIB."
    MODULE          -- this module
    MANDATORY-GROUPS {
                        ciscoContentServicesGlobalCfgGroup,
                        ciscoContentServicesGlobalStatsGroup,
                        ciscoContentServicesBMAGroup,
                        ciscoContentServicesQuotaMgrGroup,
                        ciscoContentServicesUserDbGroup,
                        ciscoContentServicesNotifEnableGroup,
                        ciscoContentServicesNotifGroup,
                        ciscoContentServicesLoadStatRadiusGroup,
                        ciscoContentServicesLoadStatUserDBGroup,
                        ciscoContentServicesLoadStatSessionGroup,
                        ciscoContentServicesLoadStatBMAGroup,
                        ciscoContentServicesLoadStatQuotaMgrGroup,
                        ciscoContentServicesGlobalStatsGroupSup1,
                        ciscoContentServicesBMAGroupSup1,
                        ciscoContentServicesQuotaMgrGroupSup1
                    }

    OBJECT          ccsBMAHighWater
    MIN-ACCESS      read-only
    DESCRIPTION
        "Create/Write access is not required."

    OBJECT          ccsQuotaMgrHighWater
    MIN-ACCESS      read-only
    DESCRIPTION
        "Create/Write access is not required."

    OBJECT          ccsBMAPriority
    MIN-ACCESS      read-only
    DESCRIPTION
        "Create/Write access is not required."

    OBJECT          ccsQuotaMgrPriority
    MIN-ACCESS      read-only
    DESCRIPTION
        "Create/Write access is not required."

    OBJECT          ccsBMARowStatus
    MIN-ACCESS      read-only
    DESCRIPTION
        "Write access is not required."

    OBJECT          ccsQuotaMgrRowStatus
    MIN-ACCESS      read-only
    DESCRIPTION
        "Write access is not required."

    OBJECT          ccsgsGTPBMARateInterval
    MIN-ACCESS      read-only
    DESCRIPTION
        "Write access is not required."

    OBJECT          ccsgsGTPQuotaMgrRateInterval
    MIN-ACCESS      read-only
    DESCRIPTION
        "Write access is not required."
    ::= { ciscoContentServicesMIBCompliances 2 }

ciscoContentServicesMIBComplianceRev2 MODULE-COMPLIANCE
    STATUS          deprecated
    DESCRIPTION
        "The compliance statement for entities which implement
        the Cisco Content Services MIB."
    MODULE          -- this module
    MANDATORY-GROUPS {
                        ciscoContentServicesGlobalCfgGroup,
                        ciscoContentServicesGlobalStatsGroup,
                        ciscoContentServicesBMAGroup,
                        ciscoContentServicesQuotaMgrGroup,
                        ciscoContentServicesUserDbGroup,
                        ciscoContentServicesNotifEnableGroup,
                        ciscoContentServicesNotifGroup,
                        ciscoContentServicesLoadStatRadiusGroup,
                        ciscoContentServicesLoadStatUserDBGroup,
                        ciscoContentServicesLoadStatSessionGroup,
                        ciscoContentServicesLoadStatBMAGroup,
                        ciscoContentServicesLoadStatQuotaMgrGroup,
                        ciscoContentServicesGlobalStatsGroupSup1,
                        ciscoContentServicesBMAGroupSup1,
                        ciscoContentServicesQuotaMgrGroupSup1,
                        ciscoContentServicesGlobalCfgGroupSup1,
                        ciscoContentServicesNotifEnableGroupSup1,
                        ciscoContentServicesNotifGroupSup1
                    }

    OBJECT          ccsBMAHighWater
    MIN-ACCESS      read-only
    DESCRIPTION
        "Create/Write access is not required."

    OBJECT          ccsQuotaMgrHighWater
    MIN-ACCESS      read-only
    DESCRIPTION
        "Create/Write access is not required."

    OBJECT          ccsBMAPriority
    MIN-ACCESS      read-only
    DESCRIPTION
        "Create/Write access is not required."

    OBJECT          ccsQuotaMgrPriority
    MIN-ACCESS      read-only
    DESCRIPTION
        "Create/Write access is not required."

    OBJECT          ccsBMARowStatus
    MIN-ACCESS      read-only
    DESCRIPTION
        "Write access is not required."

    OBJECT          ccsQuotaMgrRowStatus
    MIN-ACCESS      read-only
    DESCRIPTION
        "Write access is not required."

    OBJECT          ccsgsGTPBMARateInterval
    MIN-ACCESS      read-only
    DESCRIPTION
        "Write access is not required."

    OBJECT          ccsgsGTPQuotaMgrRateInterval
    MIN-ACCESS      read-only
    DESCRIPTION
        "Write access is not required."
    ::= { ciscoContentServicesMIBCompliances 3 }

ciscoContentServicesMIBComplianceRev3 MODULE-COMPLIANCE
    STATUS          deprecated
    DESCRIPTION
        "The compliance statement for entities which implement
        the Cisco Content Services MIB."
    MODULE          -- this module
    MANDATORY-GROUPS {
                        ciscoContentServicesGlobalCfgGroup,
                        ciscoContentServicesGlobalStatsGroup,
                        ciscoContentServicesBMAGroup,
                        ciscoContentServicesQuotaMgrGroup,
                        ciscoContentServicesUserDbGroup,
                        ciscoContentServicesNotifEnableGroup,
                        ciscoContentServicesNotifGroup,
                        ciscoContentServicesLoadStatRadiusGroup,
                        ciscoContentServicesLoadStatUserDBGroup,
                        ciscoContentServicesLoadStatSessionGroup,
                        ciscoContentServicesLoadStatBMAGroup,
                        ciscoContentServicesLoadStatQuotaMgrGroup,
                        ciscoContentServicesGlobalStatsGroupSup1,
                        ciscoContentServicesBMAGroupSup1,
                        ciscoContentServicesQuotaMgrGroupSup1,
                        ciscoContentServicesGlobalCfgGroupSup1,
                        ciscoContentServicesNotifEnableGroupSup1,
                        ciscoContentServicesNotifGroupSup1,
                        ciscoContentServicesGlobalCfgGroupSup2,
                        ciscoContentServicesNotifEnableGroupSup2,
                        ciscoContentServicesNotifGroupSup2,
                        ciscoContentServicesNotifInfoGroup
                    }

    OBJECT          ccsBMAHighWater
    MIN-ACCESS      read-only
    DESCRIPTION
        "Create/Write access is not required."

    OBJECT          ccsQuotaMgrHighWater
    MIN-ACCESS      read-only
    DESCRIPTION
        "Create/Write access is not required."

    OBJECT          ccsBMAPriority
    MIN-ACCESS      read-only
    DESCRIPTION
        "Create/Write access is not required."

    OBJECT          ccsQuotaMgrPriority
    MIN-ACCESS      read-only
    DESCRIPTION
        "Create/Write access is not required."

    OBJECT          ccsBMARowStatus
    MIN-ACCESS      read-only
    DESCRIPTION
        "Write access is not required."

    OBJECT          ccsQuotaMgrRowStatus
    MIN-ACCESS      read-only
    DESCRIPTION
        "Write access is not required."

    OBJECT          ccsgsGTPBMARateInterval
    MIN-ACCESS      read-only
    DESCRIPTION
        "Write access is not required."

    OBJECT          ccsgsGTPQuotaMgrRateInterval
    MIN-ACCESS      read-only
    DESCRIPTION
        "Write access is not required."
    ::= { ciscoContentServicesMIBCompliances 4 }

ciscoContentServicesMIBComplianceRev4 MODULE-COMPLIANCE
    STATUS          deprecated
    DESCRIPTION
        "The compliance statement for entities which implement
        the Cisco Content Services MIB. This compliance statement
        deprecates the ciscoContentServicesMIBComplianceRev3."
    MODULE          -- this module
    MANDATORY-GROUPS {
                        ciscoContentServicesGlobalCfgGroup,
                        ciscoContentServicesGlobalStatsGroup,
                        ciscoContentServicesBMAGroup,
                        ciscoContentServicesQuotaMgrGroup,
                        ciscoContentServicesUserDbGroup,
                        ciscoContentServicesNotifEnableGroup,
                        ciscoContentServicesNotifGroup,
                        ciscoContentServicesLoadStatRadiusGroup,
                        ciscoContentServicesLoadStatUserDBGroup,
                        ciscoContentServicesLoadStatSessionGroup,
                        ciscoContentServicesLoadStatBMAGroup,
                        ciscoContentServicesLoadStatQuotaMgrGroup,
                        ciscoContentServicesGlobalStatsGroupSup1,
                        ciscoContentServicesBMAGroupSup1,
                        ciscoContentServicesQuotaMgrGroupSup1,
                        ciscoContentServicesGlobalCfgGroupSup1,
                        ciscoContentServicesNotifEnableGroupSup1,
                        ciscoContentServicesNotifGroupSup1,
                        ciscoContentServicesGlobalCfgGroupSup2,
                        ciscoContentServicesNotifEnableGroupSup2,
                        ciscoContentServicesNotifGroupSup2,
                        ciscoContentServicesNotifInfoGroup,
                        ciscoContentServiceProtocolStatsGroup,
                        ciscoContentServicesLoadStatGxEventGroup
                    }

    OBJECT          ccsBMAHighWater
    MIN-ACCESS      read-only
    DESCRIPTION
        "Create/Write access is not required."

    OBJECT          ccsQuotaMgrHighWater
    MIN-ACCESS      read-only
    DESCRIPTION
        "Create/Write access is not required."

    OBJECT          ccsBMAPriority
    MIN-ACCESS      read-only
    DESCRIPTION
        "Create/Write access is not required."

    OBJECT          ccsQuotaMgrPriority
    MIN-ACCESS      read-only
    DESCRIPTION
        "Create/Write access is not required."

    OBJECT          ccsBMARowStatus
    MIN-ACCESS      read-only
    DESCRIPTION
        "Write access is not required."

    OBJECT          ccsQuotaMgrRowStatus
    MIN-ACCESS      read-only
    DESCRIPTION
        "Write access is not required."

    OBJECT          ccsgsGTPBMARateInterval
    MIN-ACCESS      read-only
    DESCRIPTION
        "Write access is not required."

    OBJECT          ccsgsGTPQuotaMgrRateInterval
    MIN-ACCESS      read-only
    DESCRIPTION
        "Write access is not required."

    OBJECT          ccspsTransactionRateHighWater
    MIN-ACCESS      read-only
    DESCRIPTION
        "Write access is not required."

    OBJECT          ccspsSubOutPacketRateHighWater
    MIN-ACCESS      read-only
    DESCRIPTION
        "Write access is not required."

    OBJECT          ccspsNetOutPacketRateHighWater
    MIN-ACCESS      read-only
    DESCRIPTION
        "Write access is not required."

    OBJECT          ccspsSubOutBitRateHighWater
    MIN-ACCESS      read-only
    DESCRIPTION
        "Write access is not required."

    OBJECT          ccspsNetOutBitRateHighWater
    MIN-ACCESS      read-only
    DESCRIPTION
        "Write access is not required."
    ::= { ciscoContentServicesMIBCompliances 5 }

ciscoContentServicesMIBComplianceRev5 MODULE-COMPLIANCE
    STATUS          current
    DESCRIPTION
        "The compliance statement for entities which implement
        the Cisco Content Services MIB."
    MODULE          -- this module
    MANDATORY-GROUPS {
                        ciscoContentServicesGlobalCfgGroup,
                        ciscoContentServicesGlobalStatsGroup,
                        ciscoContentServicesBMAGroup,
                        ciscoContentServicesQuotaMgrGroup,
                        ciscoContentServicesUserDbGroup,
                        ciscoContentServicesNotifEnableGroup,
                        ciscoContentServicesNotifGroup,
                        ciscoContentServicesLoadStatRadiusGroup,
                        ciscoContentServicesLoadStatUserDBGroup,
                        ciscoContentServicesLoadStatSessionGroup,
                        ciscoContentServicesLoadStatBMAGroup,
                        ciscoContentServicesLoadStatQuotaMgrGroup,
                        ciscoContentServicesGlobalStatsGroupSup1,
                        ciscoContentServicesBMAGroupSup1,
                        ciscoContentServicesQuotaMgrGroupSup1,
                        ciscoContentServicesGlobalCfgGroupSup1,
                        ciscoContentServicesNotifEnableGroupSup1,
                        ciscoContentServicesNotifGroupSup1,
                        ciscoContentServicesGlobalCfgGroupSup2,
                        ciscoContentServicesNotifEnableGroupSup2,
                        ciscoContentServicesNotifGroupSup2,
                        ciscoContentServicesNotifInfoGroup,
                        ciscoContentServiceProtocolStatsGroup,
                        ciscoContentServicesLoadStatGxEventGroup,
                        ciscoContentServicesBillingPlanStatsGroup
                    }

    OBJECT          ccsBMAHighWater
    MIN-ACCESS      read-only
    DESCRIPTION
        "Create/Write access is not required."

    OBJECT          ccsQuotaMgrHighWater
    MIN-ACCESS      read-only
    DESCRIPTION
        "Create/Write access is not required."

    OBJECT          ccsBMAPriority
    MIN-ACCESS      read-only
    DESCRIPTION
        "Create/Write access is not required."

    OBJECT          ccsQuotaMgrPriority
    MIN-ACCESS      read-only
    DESCRIPTION
        "Create/Write access is not required."

    OBJECT          ccsBMARowStatus
    MIN-ACCESS      read-only
    DESCRIPTION
        "Write access is not required."

    OBJECT          ccsQuotaMgrRowStatus
    MIN-ACCESS      read-only
    DESCRIPTION
        "Write access is not required."

    OBJECT          ccsgsGTPBMARateInterval
    MIN-ACCESS      read-only
    DESCRIPTION
        "Write access is not required."

    OBJECT          ccsgsGTPQuotaMgrRateInterval
    MIN-ACCESS      read-only
    DESCRIPTION
        "Write access is not required."

    OBJECT          ccspsTransactionRateHighWater
    MIN-ACCESS      read-only
    DESCRIPTION
        "Write access is not required."

    OBJECT          ccspsSubOutPacketRateHighWater
    MIN-ACCESS      read-only
    DESCRIPTION
        "Write access is not required."

    OBJECT          ccspsNetOutPacketRateHighWater
    MIN-ACCESS      read-only
    DESCRIPTION
        "Write access is not required."

    OBJECT          ccspsSubOutBitRateHighWater
    MIN-ACCESS      read-only
    DESCRIPTION
        "Write access is not required."

    OBJECT          ccspsNetOutBitRateHighWater
    MIN-ACCESS      read-only
    DESCRIPTION
        "Write access is not required."
    ::= { ciscoContentServicesMIBCompliances 6 }

-- units of conformance

ciscoContentServicesGlobalCfgGroup OBJECT-GROUP
    OBJECTS         {
                        ccsgcBMALostRecordTimer,
                        ccsgcQuotaMgrLostRecordTimer
                    }
    STATUS          current
    DESCRIPTION
        "Global Config objects."
    ::= { ciscoContentServicesMIBGroups 1 }

ciscoContentServicesGlobalStatsGroup OBJECT-GROUP
    OBJECTS         {
                        ccsgsUserCurrent,
                        ccsgsUserHighWater,
                        ccsgsUserHighWaterResetTime,
                        ccsgsSessionCurrent,
                        ccsgsSessionHighWater,
                        ccsgsSessionHighWaterResetTime
                    }
    STATUS          current
    DESCRIPTION
        "Global Statistic objects."
    ::= { ciscoContentServicesMIBGroups 2 }

ciscoContentServicesUserDbGroup OBJECT-GROUP
    OBJECTS         {
                        ccsUserDbState,
                        ccsUserDbRequests,
                        ccsUserDbHCRequests,
                        ccsUserDbUidsReturned,
                        ccsUserDbHCUidsReturned,
                        ccsUserDbReqResent,
                        ccsUserDbHCReqResent,
                        ccsUserDbReqTimeouts,
                        ccsUserDbHCReqTimeouts,
                        ccsUserDbReqErrors,
                        ccsUserDbHCReqErrors,
                        ccsUserDbRowStatus
                    }
    STATUS          current
    DESCRIPTION
        "User Database Statistics."
    ::= { ciscoContentServicesMIBGroups 3 }

ciscoContentServicesBMAGroup OBJECT-GROUP
    OBJECTS         {
                        ccsBMAPriority,
                        ccsBMAState,
                        ccsBMALostRecords,
                        ccsBMAHCLostRecords,
                        ccsBMATotalSent,
                        ccsBMAHCTotalSent,
                        ccsBMAFailAck,
                        ccsBMAHCFailAck,
                        ccsBMAOutstanding,
                        ccsBMAHighWater,
                        ccsBMAHighWaterResetTime,
                        ccsBMABadRecord,
                        ccsBMAHCBadRecord,
                        ccsBMARetransmit,
                        ccsBMAHCRetransmit,
                        ccsBMARowStatus
                    }
    STATUS          current
    DESCRIPTION
        "BMA Statistics."
    ::= { ciscoContentServicesMIBGroups 4 }

ciscoContentServicesQuotaMgrGroup OBJECT-GROUP
    OBJECTS         {
                        ccsQuotaMgrPriority,
                        ccsQuotaMgrState,
                        ccsQuotaMgrLostRecords,
                        ccsQuotaMgrHCLostRecords,
                        ccsQuotaMgrTotalSent,
                        ccsQuotaMgrHCTotalSent,
                        ccsQuotaMgrFailAck,
                        ccsQuotaMgrHCFailAck,
                        ccsQuotaMgrOutstanding,
                        ccsQuotaMgrHighWater,
                        ccsQuotaMgrHighWaterResetTime,
                        ccsQuotaMgrBadRecord,
                        ccsQuotaMgrHCBadRecord,
                        ccsQuotaMgrRetransmit,
                        ccsQuotaMgrHCRetransmit,
                        ccsQuotaMgrRowStatus
                    }
    STATUS          current
    DESCRIPTION
        "Quota Manager Statistics."
    ::= { ciscoContentServicesMIBGroups 5 }

ciscoContentServicesNotifEnableGroup OBJECT-GROUP
    OBJECTS         {
                        ccsBMAStateChangeNotifEnabled,
                        ccsQuotaMgrStateChangeNotifEnabled,
                        ccsUserDbStateChangeNotifEnabled,
                        ccsBMALostRecordEventNotifEnabled,
                        ccsQuotaMgrLostRecordEventNotifEnabled
                    }
    STATUS          current
    DESCRIPTION
        "Notifications enable/disable flags."
    ::= { ciscoContentServicesMIBGroups 7 }

ciscoContentServicesNotifGroup NOTIFICATION-GROUP
   NOTIFICATIONS    {
                        ciscoContentServicesBMAStateChange,
                        ciscoContentServicesQuotaMgrStateChange,
                        ciscoContentServicesUserDbStateChange,
                        ciscoContentServicesBMALostRecordEvent,
                        ciscoContentServicesQuotaMgrLostRecordEvent
                    }
    STATUS          current
    DESCRIPTION
        "A collection of objects providing notifications."
    ::= { ciscoContentServicesMIBGroups 8 }

ciscoContentServicesLoadStatRadiusGroup OBJECT-GROUP
    OBJECTS         {
                        ccsLoadStatRadiusStartAllowed,
                        ccsLoadStatHCRadiusStartAllowed,
                        ccsLoadStatRadiusStartAllowedRate,
                        ccsLoadStatRadiusStartAllowedRateHighWater,
                        ccsLoadStatHCRadiusStartAllowedRateHighWater,
                        ccsLoadStatRadiusStartIPCQueueDepthTolerance,
                        ccsLoadStatRadiusStartDenied,
                        ccsLoadStatHCRadiusStartDenied,
                        ccsLoadStatRadiusStartDenialRate,
                        ccsLoadStatRadiusStartDenialRateHighWater,
                        ccsLoadStatHCRadiusStartDenialRateHighWater
                    }
    STATUS          current
    DESCRIPTION
        "Load Statistics for Radius."
    ::= { ciscoContentServicesMIBGroups 9 }

ciscoContentServicesLoadStatUserDBGroup OBJECT-GROUP
    OBJECTS         {
                        ccsLoadStatUserDBReqAllowed,
                        ccsLoadStatHCUserDBReqAllowed,
                        ccsLoadStatUserDBReqAllowedRate,
                        ccsLoadStatUserDBReqAllowedRateHighWater,
                        ccsLoadStatHCUserDBReqAllowedRateHighWater,
                        ccsLoadStatUserDBReqIPCQueueDepthTolerance,
                        ccsLoadStatUserDBReqDenied,
                        ccsLoadStatHCUserDBReqDenied,
                        ccsLoadStatUserDBReqDenialRate,
                        ccsLoadStatUserDBReqDenialRateHighWater,
                        ccsLoadStatHCUserDBReqDenialRateHighWater
                    }
    STATUS          current
    DESCRIPTION
        "Load Statistics for Database."
    ::= { ciscoContentServicesMIBGroups 10 }

ciscoContentServicesLoadStatSessionGroup OBJECT-GROUP
    OBJECTS         {
                        ccsLoadStatSessionCreateAllowed,
                        ccsLoadStatHCSessionCreateAllowed,
                        ccsLoadStatSessionCreateAllowedRate,
                        ccsLoadStatSessionCreateAllowedRateHighWater,
                        ccsLoadStatHCSessionCreateAllowedRateHighWater,
                        ccsLoadStatSessionCreateIPCQueueDepthTolerance,
                        ccsLoadStatSessionCreateDenied,
                        ccsLoadStatHCSessionCreateDenied,
                        ccsLoadStatSessionCreateDenialRate,
                        ccsLoadStatSessionCreateDenialRateHighWater,
                        ccsLoadStatHCSessionCreateDenialRateHighWater
                    }
    STATUS          current
    DESCRIPTION
        "Load Statistics for Session."
    ::= { ciscoContentServicesMIBGroups 11 }

ciscoContentServicesLoadStatBMAGroup OBJECT-GROUP
    OBJECTS         {
                        ccsLoadStatBMAMsgsAllowed,
                        ccsLoadStatHCBMAMsgsAllowed,
                        ccsLoadStatBMAMsgsAllowedRate,
                        ccsLoadStatBMAMsgsAllowedRateHighWater,
                        ccsLoadStatHCBMAMsgsAllowedRateHighWater,
                        ccsLoadStatBMAMsgsIPCQueueDepthTolerance,
                        ccsLoadStatBMAMsgsDenied,
                        ccsLoadStatHCBMAMsgsDenied,
                        ccsLoadStatBMAMsgsDenialRate,
                        ccsLoadStatBMAMsgsDenialRateHighWater,
                        ccsLoadStatHCBMAMsgsDenialRateHighWater
                    }
    STATUS          current
    DESCRIPTION
        "Load Statistics for BMA."
    ::= { ciscoContentServicesMIBGroups 12 }

ciscoContentServicesLoadStatQuotaMgrGroup OBJECT-GROUP
    OBJECTS         {
                        ccsLoadStatQuotaMgrMsgsAllowed,
                        ccsLoadStatHCQuotaMgrMsgsAllowed,
                        ccsLoadStatQuotaMgrMsgsAllowedRate,
                        ccsLoadStatQuotaMgrMsgsAllowedRateHighWater,
                        ccsLoadStatHCQuotaMgrMsgsAllowedRateHighWater,
                        ccsLoadStatQuotaMgrMsgsIPCQueueDepthTolerance,
                        ccsLoadStatQuotaMgrMsgsDenied,
                        ccsLoadStatHCQuotaMgrMsgsDenied,
                        ccsLoadStatQuotaMgrMsgsDenialRate,
                        ccsLoadStatQuotaMgrMsgsDenialRateHighWater,
                        ccsLoadStatHCQuotaMgrMsgsDenialRateHighWater
                    }
    STATUS          current
    DESCRIPTION
        "Load Statistics for Quota Manager."
    ::= { ciscoContentServicesMIBGroups 13 }

ciscoContentServicesGlobalStatsGroupSup1 OBJECT-GROUP
    OBJECTS         {
                        ccsgsGTPBMARejected,
                        ccsgsHCGTPBMARejected,
                        ccsgsGTPBMADropped,
                        ccsgsHCGTPBMADropped,
                        ccsgsGTPBMARetransmit,
                        ccsgsHCGTPBMARetransmit,
                        ccsgsGTPQuotaMgrRejected,
                        ccsgsHCGTPQuotaMgrRejected,
                        ccsgsGTPQuotaMgrDropped,
                        ccsgsHCGTPQuotaMgrDropped,
                        ccsgsGTPQuotaMgrRetransmit,
                        ccsgsHCGTPQuotaMgrRetransmit,
                        ccsgsGTPBMARateInterval,
                        ccsgsGTPQuotaMgrRateInterval
                    }
    STATUS          current
    DESCRIPTION
        "Collection of objects providing aggregate statistics for all
        the BMAs and Quota Managers. This group augments the objects
        contained in the ciscoContentServicesGlobalStatsGroup."
    ::= { ciscoContentServicesMIBGroups 14 }

ciscoContentServicesBMAGroupSup1 OBJECT-GROUP
    OBJECTS         {
                        ccsBMAPacketRate,
                        ccsBMAAckRate
                    }
    STATUS          current
    DESCRIPTION
        "Collection of objects providing BMA statistics.
        This group augments the objects contained in the
        ciscoContentServicesBMAGroup."
    ::= { ciscoContentServicesMIBGroups 15 }

ciscoContentServicesQuotaMgrGroupSup1 OBJECT-GROUP
    OBJECTS         {
                        ccsQuotaMgrPacketRate,
                        ccsQuotaMgrAckRate
                    }
    STATUS          current
    DESCRIPTION
        "Collection of objects providing Quota Manager statistics.
        This group augments the objects contained in the
        ciscoContentServicesQuotaMgrGroup."
    ::= { ciscoContentServicesMIBGroups 16 }

ciscoContentServicesGlobalCfgGroupSup1 OBJECT-GROUP
    OBJECTS         { ccsgsUserThreshold }
    STATUS          current
    DESCRIPTION
        "Global Config objects.
        This group augments the objects contained in the
        ciscoContentServicesGlobalCfgGroup."
    ::= { ciscoContentServicesMIBGroups 17 }

ciscoContentServicesNotifEnableGroupSup1 OBJECT-GROUP
    OBJECTS         { ccsUserThresholdExceededNotifEnabled }
    STATUS          current
    DESCRIPTION
        "Notifications enable/disable flags.
        This group augments the objects contained in the
        ciscoContentServicesNotifEnableGroup"
    ::= { ciscoContentServicesMIBGroups 18 }

ciscoContentServicesNotifGroupSup1 NOTIFICATION-GROUP
   NOTIFICATIONS    { ciscoContentServicesUserThresholdExceeded }
    STATUS          current
    DESCRIPTION
        "A collection of objects providing notifications.
        This group augments the objects contained in the
        ciscoContentServicesNotifGroup."
    ::= { ciscoContentServicesMIBGroups 19 }

ciscoContentServicesGlobalCfgGroupSup2 OBJECT-GROUP
    OBJECTS         {
                        ccsAdControlAlarmUpdateTimer,
                        ccsNetServerResponseFailAlarmThreshold,
                        ccsNetServerResponseFailClearThreshold,
                        ccsNetServerFirstPayloadResponseTime,
                        ccsNetServerResponseTimeFailAlarmThreshold,
                        ccsNetServerResponseTimeFailClearThreshold,
                        ccsProtocolParseFailAlarmThreshold,
                        ccsProtocolParseFailClearThreshold
                    }
    STATUS          current
    DESCRIPTION
        "Global Config objects.
        This group augments the objects contained in the
        ciscoContentServicesGlobalCfgGroup."
    ::= { ciscoContentServicesMIBGroups 20 }

ciscoContentServicesNotifEnableGroupSup2 OBJECT-GROUP
    OBJECTS         { ccsAdControlNotifEnabled }
    STATUS          current
    DESCRIPTION
        "Notifications enable/disable flags.
        This group augments the objects contained in the
        ciscoContentServicesNotifEnableGroup"
    ::= { ciscoContentServicesMIBGroups 21 }

ciscoContentServicesNotifGroupSup2 NOTIFICATION-GROUP
   NOTIFICATIONS    {
                        ciscoContentServicesNetServerResponseFailExceeded,
                        ciscoContentServicesNetServerResponseTimeExceeded,
                        ciscoContentServicesProtocolParseFailExceeded,
                        ciscoContentServicesNetServerResponseFailAlarmCleared,
                        ciscoContentServicesNetServerResponseTimeAlarmCleared,
                        ciscoContentServicesProtocolParseFailAlarmCleared
                    }
    STATUS          current
    DESCRIPTION
        "A collection of objects providing notifications.
        This group augments the objects contained in the
        ciscoContentServicesNotifGroup."
    ::= { ciscoContentServicesMIBGroups 22 }

ciscoContentServicesNotifInfoGroup OBJECT-GROUP
    OBJECTS         {
                        ccsTPIndexNotifInfo,
                        ccsServiceNameNotifInfo,
                        ccsContentNameNotifInfo,
                        ccsPolicyNameNotifInfo,
                        ccsNetServerIpAddrTypeNotifInfo,
                        ccsNetServerIpAddrNotifInfo,
                        ccsNetServerPortNotifInfo,
                        ccsSubscriberIpAddrTypeNotifInfo,
                        ccsSubscriberIpAddrNotifInfo,
                        ccsSubscriberPortNotifInfo,
                        ccsNetServerResponseFailCountNotifInfo,
                        ccsNetServerResponseTimeFailCountNotifInfo,
                        ccsProtocolParseFailCountNotifInfo
                    }
    STATUS          current
    DESCRIPTION
        "Collection of objects providing info for notifications."
    ::= { ciscoContentServicesMIBGroups 23 }

ciscoContentServiceProtocolStatsGroup OBJECT-GROUP
    OBJECTS         {
                        ccspsTransaction,
                        ccspsHCTransaction,
                        ccspsTransactionRate,
                        ccspsTransactionRateHighWater,
                        ccspsTransactionRateHighWaterResetTime,
                        ccspsTransactionRateHighWaterTime,
                        ccspsSubOutPackets,
                        ccspsHCSubOutPackets,
                        ccspsSubOutPacketRate,
                        ccspsSubOutPacketRateHighWater,
                        ccspsSubOutPacketRateHighWaterResetTime,
                        ccspsSubOutPacketRateHighWaterTime,
                        ccspsNetOutPackets,
                        ccspsHCNetOutPackets,
                        ccspsNetOutPacketRate,
                        ccspsNetOutPacketRateHighWater,
                        ccspsNetOutPacketRateHighWaterResetTime,
                        ccspsNetOutPacketRateHighWaterTime,
                        ccspsSubOutBytes,
                        ccspsHCSubOutBytes,
                        ccspsSubOutBitRate,
                        ccspsSubOutBitRateHighWater,
                        ccspsSubOutBitRateHighWaterResetTime,
                        ccspsSubOutBitRateHighWaterTime,
                        ccspsNetOutBytes,
                        ccspsHCNetOutBytes,
                        ccspsNetOutBitRate,
                        ccspsNetOutBitRateHighWater,
                        ccspsNetOutBitRateHighWaterResetTime,
                        ccspsNetOutBitRateHighWaterTime
                    }
    STATUS          current
    DESCRIPTION
        "A collection of objects providing the traffic related protocol
        statistics."
    ::= { ciscoContentServicesMIBGroups 24 }

ciscoContentServicesLoadStatGxEventGroup OBJECT-GROUP
    OBJECTS         {
                        ccsLoadStatGxEventsAllowed,
                        ccsLoadStatHCGxEventsAllowed,
                        ccsLoadStatGxEventsAllowedRate,
                        ccsLoadStatGxEventsAllowedRateHighWater,
                        ccsLoadStatHCGxEventsAllowedRateHighWater,
                        ccsLoadStatGxEventsIPCQueueDepthTolerance,
                        ccsLoadStatGxEventsDenied,
                        ccsLoadStatHCGxEventsDenied,
                        ccsLoadStatGxEventsDenialRate,
                        ccsLoadStatGxEventsDenialRateHighWater,
                        ccsLoadStatHCGxEventsDenialRateHighWater
                    }
    STATUS          current
    DESCRIPTION
        "A collection of objects providing load statistics for Gx
        Events."
    ::= { ciscoContentServicesMIBGroups 25 }

ciscoContentServicesBillingPlanStatsGroup OBJECT-GROUP
    OBJECTS         {
                        ccsbpsSubscribers,
                        ccsbpsHCSubscribers,
                        ccsbpsSubscribersHighWater,
                        ccsbpsHCSubscribersHighWater
                    }
    STATUS          current
    DESCRIPTION
        "Collection of objects providing Billing Plan Stats.
        This group augments the objects contained in the
        ciscoContentServicesBillingPlanStatsGroup."
    ::= { ciscoContentServicesMIBGroups 26 }

END
