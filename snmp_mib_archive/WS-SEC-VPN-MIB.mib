--
-- WS-SEC-VPN-MIB.my
-- MIB generated by MG-SOFT Visual MIB Builder Version 6.0  Build 88
-- Tuesday, December 12, 2006 at 13:56:08
--

	WS-SEC-VPN-MIB DEFINITIONS ::= BEGIN
 
		IMPORTS
			OBJECT-GROUP, MODULE-COMPLIANCE			
				FROM SNMPv2-CONF			
			IpAddress, Unsigned32, OBJECT-TYPE, MODULE-IDENTITY			
				FROM SNMPv2-SMI			
			PhysAddress, DisplayString, TruthValue, DateAndTime			
				FROM SNMPv2-TC			
			wsSec			
				FROM WS-SMI;
	
	
		-- 1.3.6.1.4.1.388.14.6.1
		wsSecVpnMib MODULE-IDENTITY 
			LAST-UPDATED "200607131648Z"		-- July 13, 2006 at 16:48 GMT
			ORGANIZATION 
				"Symbol Technoliges"
			CONTACT-INFO 
				"Symbol Technologies, Inc.
				Customer Service
				Postal:
				One Symbol Plaza
				Holtsville, NY 11742-1300
				USA
				Phone: (631)-738-6213
				E-Mail: support@symbol.com
				Web:http://www.symbo.com"
			DESCRIPTION 
				"REVISION 2006012140000Z
				DESCRIPTION
				   02a02"
			REVISION "200607141826Z"		-- July 14, 2006 at 18:26 GMT
			DESCRIPTION 
				"This MIB is used for configuring IPSec VPN."
			::= { wsSec 1 }

		
	
--
-- Type definitions
--
	
		AbbrRowStatus ::= INTEGER
			{
			active(1),
			createAndGo(4),
			destroy(6)
			}

	
	
--
-- Node definitions
--
	
		-- 1.3.6.1.4.1.388.14.6.1.1
		wsSecIKEScalars OBJECT IDENTIFIER ::= { wsSecVpnMib 1 }

		
		-- 1.3.6.1.4.1.388.14.6.1.1.1
		wsSecIKEKeepAlive OBJECT-TYPE
			SYNTAX Unsigned32 (10..3600)
			UNITS "seconds"
			MAX-ACCESS read-write
			STATUS current
			DESCRIPTION
				"Description."
			::= { wsSecIKEScalars 1 }

		
		-- 1.3.6.1.4.1.388.14.6.1.1.2
		wsSecISAKMPLocalIdentity OBJECT-TYPE
			SYNTAX INTEGER
				{
				ipAddress(1),
				distinguishedName(2),
				domainName(3)
				}
			MAX-ACCESS read-write
			STATUS current
			DESCRIPTION
				"Description."
			::= { wsSecIKEScalars 2 }

		
		-- 1.3.6.1.4.1.388.14.6.1.2
		wsSecIKEPolicyTable OBJECT-TYPE
			SYNTAX SEQUENCE OF WsSecIKEPolicyEntry
			MAX-ACCESS not-accessible
			STATUS current
			DESCRIPTION
				"Description."
			::= { wsSecVpnMib 2 }

		
		-- 1.3.6.1.4.1.388.14.6.1.2.1
		wsSecIKEPolicyEntry OBJECT-TYPE
			SYNTAX WsSecIKEPolicyEntry
			MAX-ACCESS not-accessible
			STATUS current
			DESCRIPTION
				"Description."
			INDEX { wsSecIKEPolicyPriority }
			::= { wsSecIKEPolicyTable 1 }

		
		WsSecIKEPolicyEntry ::=
			SEQUENCE { 
				wsSecIKEPolicyPriority
					Unsigned32,
				wsSecIKEPolicyEncryption
					INTEGER,
				wsSecIKEPolicyHash
					INTEGER,
				wsSecIKEPolicyAuthType
					INTEGER,
				wsSecIKEPolicyDHGroup
					INTEGER,
				wsSecIKEPolicySaLifeTimeSec
					Unsigned32,
				wsSecIKEPolicyRowStatus
					AbbrRowStatus
			 }

		-- 1.3.6.1.4.1.388.14.6.1.2.1.1
		wsSecIKEPolicyPriority OBJECT-TYPE
			SYNTAX Unsigned32 (1..10001)
			MAX-ACCESS read-only
			STATUS current
			DESCRIPTION
				"Index number 10001 is reserverd for default entry
				which can not be deleted."
			::= { wsSecIKEPolicyEntry 1 }

		
		-- 1.3.6.1.4.1.388.14.6.1.2.1.2
		wsSecIKEPolicyEncryption OBJECT-TYPE
			SYNTAX INTEGER
				{
				des(1),
				tripleDes(2),
				aes(3),
				aes192(4),
				aes256(5)
				}
			MAX-ACCESS read-create
			STATUS current
			DESCRIPTION
				"Description."
			DEFVAL { des }
			::= { wsSecIKEPolicyEntry 2 }

		
		-- 1.3.6.1.4.1.388.14.6.1.2.1.3
		wsSecIKEPolicyHash OBJECT-TYPE
			SYNTAX INTEGER
				{
				sha1(1),
				md5(2)
				}
			MAX-ACCESS read-create
			STATUS current
			DESCRIPTION
				"Description."
			DEFVAL { sha1 }
			::= { wsSecIKEPolicyEntry 3 }

		
		-- 1.3.6.1.4.1.388.14.6.1.2.1.4
		wsSecIKEPolicyAuthType OBJECT-TYPE
			SYNTAX INTEGER
				{
				rsaSig(1),
				preSharedKey(2)
				}
			MAX-ACCESS read-create
			STATUS current
			DESCRIPTION
				"Description."
			DEFVAL { rsaSig }
			::= { wsSecIKEPolicyEntry 4 }

		
		-- 1.3.6.1.4.1.388.14.6.1.2.1.5
		wsSecIKEPolicyDHGroup OBJECT-TYPE
			SYNTAX INTEGER
				{
				group1(1),
				group2(2),
				group5(5)
				}
			MAX-ACCESS read-create
			STATUS current
			DESCRIPTION
				"Description."
			DEFVAL { group1 }
			::= { wsSecIKEPolicyEntry 5 }

		
		-- 1.3.6.1.4.1.388.14.6.1.2.1.6
		wsSecIKEPolicySaLifeTimeSec OBJECT-TYPE
			SYNTAX Unsigned32 (60..2147483646)
			UNITS "seconds"
			MAX-ACCESS read-create
			STATUS current
			DESCRIPTION
				"Description."
			::= { wsSecIKEPolicyEntry 6 }

		
		-- 1.3.6.1.4.1.388.14.6.1.2.1.7
		wsSecIKEPolicyRowStatus OBJECT-TYPE
			SYNTAX AbbrRowStatus
			MAX-ACCESS read-create
			STATUS current
			DESCRIPTION
				"Description."
			::= { wsSecIKEPolicyEntry 7 }

		
		-- 1.3.6.1.4.1.388.14.6.1.3
		wsSecPreSharedKeyTable OBJECT-TYPE
			SYNTAX SEQUENCE OF WsSecPreSharedKeyEntry
			MAX-ACCESS not-accessible
			STATUS current
			DESCRIPTION
				"Description."
			::= { wsSecVpnMib 3 }

		
		-- 1.3.6.1.4.1.388.14.6.1.3.1
		wsSecPreSharedKeyEntry OBJECT-TYPE
			SYNTAX WsSecPreSharedKeyEntry
			MAX-ACCESS not-accessible
			STATUS current
			DESCRIPTION
				"Description."
			INDEX { wsSecPreSharedKeyIKEPeer }
			::= { wsSecPreSharedKeyTable 1 }

		
		WsSecPreSharedKeyEntry ::=
			SEQUENCE { 
				wsSecPreSharedKeyIKEPeer
					DisplayString,
				wsSecPreSharedKeyIKEPeerIdentity
					INTEGER,
				wsSecPreSharedKeyIKEPeerKey
					OCTET STRING,
				wsSecPreSharedKeyIKEAggressive
					TruthValue,
				wsSecPreSharedKeyRowStatus
					AbbrRowStatus
			 }

		-- 1.3.6.1.4.1.388.14.6.1.3.1.1
		wsSecPreSharedKeyIKEPeer OBJECT-TYPE
			SYNTAX DisplayString
			MAX-ACCESS read-only
			STATUS current
			DESCRIPTION
				"Description.This object can be either a IP address, host name or domain name
				as indicated by the value of wsSecIKEPeerIdentity"
			::= { wsSecPreSharedKeyEntry 1 }

		
		-- 1.3.6.1.4.1.388.14.6.1.3.1.2
		wsSecPreSharedKeyIKEPeerIdentity OBJECT-TYPE
			SYNTAX INTEGER
				{
				ipAddress(1),
				distinguishedName(2),
				domainName(3)
				}
			MAX-ACCESS read-create
			STATUS current
			DESCRIPTION
				"Description."
			::= { wsSecPreSharedKeyEntry 2 }

		
		-- 1.3.6.1.4.1.388.14.6.1.3.1.3
		wsSecPreSharedKeyIKEPeerKey OBJECT-TYPE
			SYNTAX OCTET STRING (SIZE (8..255))
			MAX-ACCESS read-create
			STATUS current
			DESCRIPTION
				"Description."
			::= { wsSecPreSharedKeyEntry 3 }

		
		-- 1.3.6.1.4.1.388.14.6.1.3.1.4
		wsSecPreSharedKeyIKEAggressive OBJECT-TYPE
			SYNTAX TruthValue
			MAX-ACCESS read-create
			STATUS current
			DESCRIPTION
				"Description."
			::= { wsSecPreSharedKeyEntry 4 }

		
		-- 1.3.6.1.4.1.388.14.6.1.3.1.5
		wsSecPreSharedKeyRowStatus OBJECT-TYPE
			SYNTAX AbbrRowStatus
			MAX-ACCESS read-create
			STATUS current
			DESCRIPTION
				"All objects in the entry must be specified 
				 durng a row creation."
			::= { wsSecPreSharedKeyEntry 5 }

		
		-- 1.3.6.1.4.1.388.14.6.1.4
		wsSecTransformSetTable OBJECT-TYPE
			SYNTAX SEQUENCE OF WsSecTransformSetEntry
			MAX-ACCESS not-accessible
			STATUS current
			DESCRIPTION
				"Description."
			::= { wsSecVpnMib 4 }

		
		-- 1.3.6.1.4.1.388.14.6.1.4.1
		wsSecTransformSetEntry OBJECT-TYPE
			SYNTAX WsSecTransformSetEntry
			MAX-ACCESS not-accessible
			STATUS current
			DESCRIPTION
				"Description."
			INDEX { wsSecTransformSetName }
			::= { wsSecTransformSetTable 1 }

		
		WsSecTransformSetEntry ::=
			SEQUENCE { 
				wsSecTransformSetName
					DisplayString,
				wsSecTransformSetMode
					INTEGER,
				wsSecTransformSetAHAuth
					INTEGER,
				wsSecTransformSetEspEncr
					INTEGER,
				wsSecTransformSetEspAuth
					INTEGER,
				wsSecTransformSetRowStatus
					AbbrRowStatus
			 }

		-- 1.3.6.1.4.1.388.14.6.1.4.1.1
		wsSecTransformSetName OBJECT-TYPE
			SYNTAX DisplayString (SIZE (1..64))
			MAX-ACCESS read-only
			STATUS current
			DESCRIPTION
				"Description."
			::= { wsSecTransformSetEntry 1 }

		
		-- 1.3.6.1.4.1.388.14.6.1.4.1.2
		wsSecTransformSetMode OBJECT-TYPE
			SYNTAX INTEGER
				{
				transport(1),
				tunnel(2)
				}
			MAX-ACCESS read-create
			STATUS current
			DESCRIPTION
				"Description."
			DEFVAL { tunnel }
			::= { wsSecTransformSetEntry 2 }

		
		-- 1.3.6.1.4.1.388.14.6.1.4.1.3
		wsSecTransformSetAHAuth OBJECT-TYPE
			SYNTAX INTEGER
				{
				none(0),
				ahMd5Hmac(1),
				ahShaHmac(2)
				}
			MAX-ACCESS read-create
			STATUS current
			DESCRIPTION
				"Description."
			::= { wsSecTransformSetEntry 3 }

		
		-- 1.3.6.1.4.1.388.14.6.1.4.1.4
		wsSecTransformSetEspEncr OBJECT-TYPE
			SYNTAX INTEGER
				{
				none(0),
				espDes(3),
				esp3Des(4),
				espAes(5),
				espAes192(6),
				espAes256(7)
				}
			MAX-ACCESS read-create
			STATUS current
			DESCRIPTION
				"Description."
			::= { wsSecTransformSetEntry 4 }

		
		-- 1.3.6.1.4.1.388.14.6.1.4.1.5
		wsSecTransformSetEspAuth OBJECT-TYPE
			SYNTAX INTEGER
				{
				none(0),
				espMd5Hmac(8),
				espShaHmac(9)
				}
			MAX-ACCESS read-create
			STATUS current
			DESCRIPTION
				"Description."
			::= { wsSecTransformSetEntry 5 }

		
		-- 1.3.6.1.4.1.388.14.6.1.4.1.6
		wsSecTransformSetRowStatus OBJECT-TYPE
			SYNTAX AbbrRowStatus
			MAX-ACCESS read-create
			STATUS current
			DESCRIPTION
				"At least one of the following objects:
				   wsSecTransformSetAHAuth
				   wsSecTransformSetEspEncr
				   wsSecTransformSetEspAuth
				 must be specified durng a row creation. 
				"
			::= { wsSecTransformSetEntry 6 }

		
		-- 1.3.6.1.4.1.388.14.6.1.5
		wsSecIPSecCfgScalars OBJECT IDENTIFIER ::= { wsSecVpnMib 5 }

		
		-- 1.3.6.1.4.1.388.14.6.1.5.1
		wsSecVpnSALifeTimeSec OBJECT-TYPE
			SYNTAX Unsigned32 (90..2147483646)
			UNITS "seconds"
			MAX-ACCESS read-write
			STATUS current
			DESCRIPTION
				"Default value is 3600 seconds."
			::= { wsSecIPSecCfgScalars 1 }

		
		-- 1.3.6.1.4.1.388.14.6.1.5.2
		wsSecVpnSALifeTimeKB OBJECT-TYPE
			SYNTAX Unsigned32 (500..2147483646)
			UNITS "KBytes"
			MAX-ACCESS read-write
			STATUS current
			DESCRIPTION
				"Default value is TBD."
			::= { wsSecIPSecCfgScalars 2 }

		
		-- 1.3.6.1.4.1.388.14.6.1.6
		wsSecLocalIPAddrPoolTable OBJECT-TYPE
			SYNTAX SEQUENCE OF WsSecLocalIPAddrPoolEntry
			MAX-ACCESS not-accessible
			STATUS current
			DESCRIPTION
				"Description."
			::= { wsSecVpnMib 6 }

		
		-- 1.3.6.1.4.1.388.14.6.1.6.1
		wsSecLocalIPAddrPoolEntry OBJECT-TYPE
			SYNTAX WsSecLocalIPAddrPoolEntry
			MAX-ACCESS not-accessible
			STATUS current
			DESCRIPTION
				"Description."
			INDEX { wsSecLocalIPAddrPoolAddrRangeStart, wsSecLocalIPAddrPoolAddrRangeEnd }
			::= { wsSecLocalIPAddrPoolTable 1 }

		
		WsSecLocalIPAddrPoolEntry ::=
			SEQUENCE { 
				wsSecLocalIPAddrPoolAddrRangeStart
					IpAddress,
				wsSecLocalIPAddrPoolAddrRangeEnd
					IpAddress,
				wsSecLocalIPAddrPoolRowStatus
					AbbrRowStatus
			 }

		-- 1.3.6.1.4.1.388.14.6.1.6.1.1
		wsSecLocalIPAddrPoolAddrRangeStart OBJECT-TYPE
			SYNTAX IpAddress
			MAX-ACCESS read-only
			STATUS current
			DESCRIPTION
				"This address and wsSecLocalIPAddrPoolAddrRangeEnd
				must belong to the same subnet with subnet mask as
				255.255.255.0"
			::= { wsSecLocalIPAddrPoolEntry 1 }

		
		-- 1.3.6.1.4.1.388.14.6.1.6.1.2
		wsSecLocalIPAddrPoolAddrRangeEnd OBJECT-TYPE
			SYNTAX IpAddress
			MAX-ACCESS read-only
			STATUS current
			DESCRIPTION
				"This address and wsSecLocalIPAddrPoolAddrRangeStart 
				must belong to the same subnet with subnet mask as
				255.255.255.0"
			::= { wsSecLocalIPAddrPoolEntry 2 }

		
		-- 1.3.6.1.4.1.388.14.6.1.6.1.3
		wsSecLocalIPAddrPoolRowStatus OBJECT-TYPE
			SYNTAX AbbrRowStatus
			MAX-ACCESS read-create
			STATUS current
			DESCRIPTION
				"Description."
			::= { wsSecLocalIPAddrPoolEntry 3 }

		
		-- 1.3.6.1.4.1.388.14.6.1.7
		wsSecLocalIPAddressPoolScalars OBJECT IDENTIFIER ::= { wsSecVpnMib 7 }

		
		-- 1.3.6.1.4.1.388.14.6.1.7.1
		wsSecClientDNSServerIP OBJECT-TYPE
			SYNTAX IpAddress
			MAX-ACCESS read-write
			STATUS current
			DESCRIPTION
				"Description."
			::= { wsSecLocalIPAddressPoolScalars 1 }

		
		-- 1.3.6.1.4.1.388.14.6.1.7.2
		wsSecClientWinServerIP OBJECT-TYPE
			SYNTAX IpAddress
			MAX-ACCESS read-write
			STATUS current
			DESCRIPTION
				"Description."
			::= { wsSecLocalIPAddressPoolScalars 2 }

		
		-- 1.3.6.1.4.1.388.14.6.1.8
		wsSecCryptoMapTable OBJECT-TYPE
			SYNTAX SEQUENCE OF WsSecCryptoMapEntry
			MAX-ACCESS not-accessible
			STATUS current
			DESCRIPTION
				"Description."
			::= { wsSecVpnMib 8 }

		
		-- 1.3.6.1.4.1.388.14.6.1.8.1
		wsSecCryptoMapEntry OBJECT-TYPE
			SYNTAX WsSecCryptoMapEntry
			MAX-ACCESS not-accessible
			STATUS current
			DESCRIPTION
				"Description."
			INDEX { wsSecCryptoMapSequenceNum, wsSecCryptoMapName }
			::= { wsSecCryptoMapTable 1 }

		
		WsSecCryptoMapEntry ::=
			SEQUENCE { 
				wsSecCryptoMapSequenceNum
					Unsigned32,
				wsSecCryptoMapName
					DisplayString,
				wsSecCryptoMapACLId
					DisplayString,
				wsSecCryptoMapSALifeTimeSec
					Unsigned32,
				wsSecCryptoMapSALifeTimeKB
					Unsigned32,
				wsSecCryptoMapPFS
					INTEGER,
				wsSecCryptoMapSAPerHostEnable
					TruthValue,
				wsSecCryptoMapModeCfgEnable
					TruthValue,
				wsSecCryptoMapLocalId
					DisplayString,
				wsSecCryptoMapLocalIdType
					INTEGER,
				wsSecCryptoMapMode
					INTEGER,
				wsSecCryptoMapRemoteType
					INTEGER,
				wsSecCryptoMapRowStatus
					AbbrRowStatus
			 }

		-- 1.3.6.1.4.1.388.14.6.1.8.1.1
		wsSecCryptoMapSequenceNum OBJECT-TYPE
			SYNTAX Unsigned32 (1..1000)
			MAX-ACCESS read-only
			STATUS current
			DESCRIPTION
				"Description."
			::= { wsSecCryptoMapEntry 1 }

		
		-- 1.3.6.1.4.1.388.14.6.1.8.1.2
		wsSecCryptoMapName OBJECT-TYPE
			SYNTAX DisplayString
			MAX-ACCESS read-only
			STATUS current
			DESCRIPTION
				"The value of wsSecCryptoMapIfMappingCryptoMapName in
				the corresponding wsSecCryptoMapIfMappingEntry"
			::= { wsSecCryptoMapEntry 2 }

		
		-- 1.3.6.1.4.1.388.14.6.1.8.1.3
		wsSecCryptoMapACLId OBJECT-TYPE
			SYNTAX DisplayString (SIZE (0..64))
			MAX-ACCESS read-create
			STATUS current
			DESCRIPTION
				"Description."
			::= { wsSecCryptoMapEntry 3 }

		
		-- 1.3.6.1.4.1.388.14.6.1.8.1.4
		wsSecCryptoMapSALifeTimeSec OBJECT-TYPE
			SYNTAX Unsigned32 (90..2147483646)
			MAX-ACCESS read-create
			STATUS current
			DESCRIPTION
				"Description."
			::= { wsSecCryptoMapEntry 4 }

		
		-- 1.3.6.1.4.1.388.14.6.1.8.1.5
		wsSecCryptoMapSALifeTimeKB OBJECT-TYPE
			SYNTAX Unsigned32 (500..2147483646)
			MAX-ACCESS read-create
			STATUS current
			DESCRIPTION
				"Description."
			::= { wsSecCryptoMapEntry 5 }

		
		-- 1.3.6.1.4.1.388.14.6.1.8.1.6
		wsSecCryptoMapPFS OBJECT-TYPE
			SYNTAX INTEGER
				{
				none(0),
				group1(1),
				group2(2),
				group5(5)
				}
			MAX-ACCESS read-create
			STATUS current
			DESCRIPTION
				"Description."
			DEFVAL { none }
			::= { wsSecCryptoMapEntry 6 }

		
		-- 1.3.6.1.4.1.388.14.6.1.8.1.7
		wsSecCryptoMapSAPerHostEnable OBJECT-TYPE
			SYNTAX TruthValue
			MAX-ACCESS read-create
			STATUS current
			DESCRIPTION
				"Description."
			::= { wsSecCryptoMapEntry 7 }

		
		-- 1.3.6.1.4.1.388.14.6.1.8.1.8
		wsSecCryptoMapModeCfgEnable OBJECT-TYPE
			SYNTAX TruthValue
			MAX-ACCESS read-create
			STATUS current
			DESCRIPTION
				"Description."
			::= { wsSecCryptoMapEntry 8 }

		
		-- 1.3.6.1.4.1.388.14.6.1.8.1.9
		wsSecCryptoMapLocalId OBJECT-TYPE
			SYNTAX DisplayString
			MAX-ACCESS read-create
			STATUS current
			DESCRIPTION
				"Description."
			::= { wsSecCryptoMapEntry 9 }

		
		-- 1.3.6.1.4.1.388.14.6.1.8.1.10
		wsSecCryptoMapLocalIdType OBJECT-TYPE
			SYNTAX INTEGER
				{
				none(0),
				dn(2),
				hostName(3)
				}
			MAX-ACCESS read-create
			STATUS current
			DESCRIPTION
				"Description."
			::= { wsSecCryptoMapEntry 10 }

		
		-- 1.3.6.1.4.1.388.14.6.1.8.1.11
		wsSecCryptoMapMode OBJECT-TYPE
			SYNTAX INTEGER
				{
				main(1),
				aggressive(2)
				}
			MAX-ACCESS read-create
			STATUS current
			DESCRIPTION
				"Description."
			::= { wsSecCryptoMapEntry 11 }

		
		-- 1.3.6.1.4.1.388.14.6.1.8.1.12
		wsSecCryptoMapRemoteType OBJECT-TYPE
			SYNTAX INTEGER
				{
				xauth(1),
				l2tp(2)
				}
			MAX-ACCESS read-create
			STATUS current
			DESCRIPTION
				"Description."
			::= { wsSecCryptoMapEntry 12 }

		
		-- 1.3.6.1.4.1.388.14.6.1.8.1.13
		wsSecCryptoMapRowStatus OBJECT-TYPE
			SYNTAX AbbrRowStatus
			MAX-ACCESS read-create
			STATUS current
			DESCRIPTION
				"Description."
			::= { wsSecCryptoMapEntry 13 }

		
		-- 1.3.6.1.4.1.388.14.6.1.9
		wsSecCryptoMapPeerTable OBJECT-TYPE
			SYNTAX SEQUENCE OF WsSecCryptoMapPeerEntry
			MAX-ACCESS not-accessible
			STATUS current
			DESCRIPTION
				"Description."
			::= { wsSecVpnMib 9 }

		
		-- 1.3.6.1.4.1.388.14.6.1.9.1
		wsSecCryptoMapPeerEntry OBJECT-TYPE
			SYNTAX WsSecCryptoMapPeerEntry
			MAX-ACCESS not-accessible
			STATUS current
			DESCRIPTION
				"Description."
			INDEX { wsSecCryptoMapPeerSequenceNum, wsSecCryptoMapPeerName, wsSecCryptoMapPeerIKEPeer }
			::= { wsSecCryptoMapPeerTable 1 }

		
		WsSecCryptoMapPeerEntry ::=
			SEQUENCE { 
				wsSecCryptoMapPeerSequenceNum
					Unsigned32,
				wsSecCryptoMapPeerName
					DisplayString,
				wsSecCryptoMapPeerIKEPeer
					DisplayString,
				wsSecCryptoMapPeerRowStatus
					AbbrRowStatus
			 }

		-- 1.3.6.1.4.1.388.14.6.1.9.1.1
		wsSecCryptoMapPeerSequenceNum OBJECT-TYPE
			SYNTAX Unsigned32 (1..1000)
			MAX-ACCESS read-only
			STATUS current
			DESCRIPTION
				"The wsSecCryptoMapSequenceNum value of the 
				 corresponding wsSecCryptoMapEntry"
			::= { wsSecCryptoMapPeerEntry 1 }

		
		-- 1.3.6.1.4.1.388.14.6.1.9.1.2
		wsSecCryptoMapPeerName OBJECT-TYPE
			SYNTAX DisplayString
			MAX-ACCESS read-only
			STATUS current
			DESCRIPTION
				"Description.The wsSecCryptoMapName value of the 
				 correcponding wsSecCryptoMapEntry."
			::= { wsSecCryptoMapPeerEntry 2 }

		
		-- 1.3.6.1.4.1.388.14.6.1.9.1.3
		wsSecCryptoMapPeerIKEPeer OBJECT-TYPE
			SYNTAX DisplayString
			MAX-ACCESS read-only
			STATUS current
			DESCRIPTION
				"The wsSecPreSharedKeyIKEPeer value of the correconding 
				 wsSecPreSharedKeyEntry. "
			::= { wsSecCryptoMapPeerEntry 3 }

		
		-- 1.3.6.1.4.1.388.14.6.1.9.1.4
		wsSecCryptoMapPeerRowStatus OBJECT-TYPE
			SYNTAX AbbrRowStatus
			MAX-ACCESS read-create
			STATUS current
			DESCRIPTION
				"Description."
			::= { wsSecCryptoMapPeerEntry 4 }

		
		-- 1.3.6.1.4.1.388.14.6.1.10
		wsSecCryptoMapManualSaTable OBJECT-TYPE
			SYNTAX SEQUENCE OF WsSecCryptoMapManualSaEntry
			MAX-ACCESS not-accessible
			STATUS current
			DESCRIPTION
				"Description."
			::= { wsSecVpnMib 10 }

		
		-- 1.3.6.1.4.1.388.14.6.1.10.1
		wsSecCryptoMapManualSaEntry OBJECT-TYPE
			SYNTAX WsSecCryptoMapManualSaEntry
			MAX-ACCESS not-accessible
			STATUS current
			DESCRIPTION
				"Description."
			INDEX { wsSecCryptoMapManualSaCryptoMapSeqNum, wsSecCryptoMapManualSaCryptoMapName }
			::= { wsSecCryptoMapManualSaTable 1 }

		
		WsSecCryptoMapManualSaEntry ::=
			SEQUENCE { 
				wsSecCryptoMapManualSaCryptoMapSeqNum
					Unsigned32,
				wsSecCryptoMapManualSaCryptoMapName
					DisplayString,
				wsSecCryptoMapManualSaIKEPeer
					DisplayString,
				wsSecCryptoMapManualSaAclId
					DisplayString,
				wsSecCryptoMapManualSaInAhSpi
					Unsigned32,
				wsSecCryptoMapManualSaInAuthKey
					OCTET STRING,
				wsSecCryptoMapManualSaOutAhSpi
					Unsigned32,
				wsSecCryptoMapManualSaOutAuthKey
					OCTET STRING,
				wsSecCryptoMapManualSaInEspSpi
					Unsigned32,
				wsSecCryptoMapManualSaInEspCipherKey
					OCTET STRING,
				wsSecCryptoMapManualSaOutEspSpi
					Unsigned32,
				wsSecCryptoMapManualSaOutEspCipherKey
					OCTET STRING,
				wsSecCryptoMapManualSaTSName
					DisplayString,
				wsSecCryptoMapManualSaAhOrEsp
					INTEGER,
				wsSecCryptoMapManualSaRowStatus
					AbbrRowStatus
			 }

		-- 1.3.6.1.4.1.388.14.6.1.10.1.1
		wsSecCryptoMapManualSaCryptoMapSeqNum OBJECT-TYPE
			SYNTAX Unsigned32 (1..1000)
			MAX-ACCESS read-only
			STATUS current
			DESCRIPTION
				"Description."
			::= { wsSecCryptoMapManualSaEntry 1 }

		
		-- 1.3.6.1.4.1.388.14.6.1.10.1.2
		wsSecCryptoMapManualSaCryptoMapName OBJECT-TYPE
			SYNTAX DisplayString
			MAX-ACCESS read-only
			STATUS current
			DESCRIPTION
				"The value of wsSecCryptoMapIfMappingCryptoMapName in
				the corresponding wsSecCryptoMapIfMappingEntry"
			::= { wsSecCryptoMapManualSaEntry 2 }

		
		-- 1.3.6.1.4.1.388.14.6.1.10.1.3
		wsSecCryptoMapManualSaIKEPeer OBJECT-TYPE
			SYNTAX DisplayString
			MAX-ACCESS read-create
			STATUS current
			DESCRIPTION
				"The wsSecPreSharedKeyIKEPeer value of the 
				 corresponding wsSecPreSharedKeyTable."
			::= { wsSecCryptoMapManualSaEntry 3 }

		
		-- 1.3.6.1.4.1.388.14.6.1.10.1.4
		wsSecCryptoMapManualSaAclId OBJECT-TYPE
			SYNTAX DisplayString (SIZE (0..64))
			MAX-ACCESS read-create
			STATUS current
			DESCRIPTION
				"Description."
			::= { wsSecCryptoMapManualSaEntry 4 }

		
		-- 1.3.6.1.4.1.388.14.6.1.10.1.5
		wsSecCryptoMapManualSaInAhSpi OBJECT-TYPE
			SYNTAX Unsigned32 (256..4294967295)
			MAX-ACCESS read-create
			STATUS current
			DESCRIPTION
				"Description."
			::= { wsSecCryptoMapManualSaEntry 5 }

		
		-- 1.3.6.1.4.1.388.14.6.1.10.1.6
		wsSecCryptoMapManualSaInAuthKey OBJECT-TYPE
			SYNTAX OCTET STRING
			MAX-ACCESS read-create
			STATUS current
			DESCRIPTION
				"Description."
			::= { wsSecCryptoMapManualSaEntry 6 }

		
		-- 1.3.6.1.4.1.388.14.6.1.10.1.7
		wsSecCryptoMapManualSaOutAhSpi OBJECT-TYPE
			SYNTAX Unsigned32 (256..4294967295)
			MAX-ACCESS read-create
			STATUS current
			DESCRIPTION
				"Description."
			::= { wsSecCryptoMapManualSaEntry 7 }

		
		-- 1.3.6.1.4.1.388.14.6.1.10.1.8
		wsSecCryptoMapManualSaOutAuthKey OBJECT-TYPE
			SYNTAX OCTET STRING
			MAX-ACCESS read-create
			STATUS current
			DESCRIPTION
				"Description."
			::= { wsSecCryptoMapManualSaEntry 8 }

		
		-- 1.3.6.1.4.1.388.14.6.1.10.1.9
		wsSecCryptoMapManualSaInEspSpi OBJECT-TYPE
			SYNTAX Unsigned32 (256..4294967295)
			MAX-ACCESS read-create
			STATUS current
			DESCRIPTION
				"Description."
			::= { wsSecCryptoMapManualSaEntry 9 }

		
		-- 1.3.6.1.4.1.388.14.6.1.10.1.10
		wsSecCryptoMapManualSaInEspCipherKey OBJECT-TYPE
			SYNTAX OCTET STRING
			MAX-ACCESS read-create
			STATUS current
			DESCRIPTION
				"Description."
			::= { wsSecCryptoMapManualSaEntry 10 }

		
		-- 1.3.6.1.4.1.388.14.6.1.10.1.11
		wsSecCryptoMapManualSaOutEspSpi OBJECT-TYPE
			SYNTAX Unsigned32 (256..4294967295)
			MAX-ACCESS read-create
			STATUS current
			DESCRIPTION
				"Description."
			::= { wsSecCryptoMapManualSaEntry 11 }

		
		-- 1.3.6.1.4.1.388.14.6.1.10.1.12
		wsSecCryptoMapManualSaOutEspCipherKey OBJECT-TYPE
			SYNTAX OCTET STRING
			MAX-ACCESS read-create
			STATUS current
			DESCRIPTION
				"Description."
			::= { wsSecCryptoMapManualSaEntry 12 }

		
		-- 1.3.6.1.4.1.388.14.6.1.10.1.13
		wsSecCryptoMapManualSaTSName OBJECT-TYPE
			SYNTAX DisplayString
			MAX-ACCESS read-create
			STATUS current
			DESCRIPTION
				"A value of wsSecTransformSetName."
			::= { wsSecCryptoMapManualSaEntry 13 }

		
		-- 1.3.6.1.4.1.388.14.6.1.10.1.14
		wsSecCryptoMapManualSaAhOrEsp OBJECT-TYPE
			SYNTAX INTEGER
				{
				none(0),
				ah(1),
				esp(2)
				}
			MAX-ACCESS read-create
			STATUS current
			DESCRIPTION
				"Description."
			::= { wsSecCryptoMapManualSaEntry 14 }

		
		-- 1.3.6.1.4.1.388.14.6.1.10.1.15
		wsSecCryptoMapManualSaRowStatus OBJECT-TYPE
			SYNTAX AbbrRowStatus
			MAX-ACCESS read-create
			STATUS current
			DESCRIPTION
				"Description."
			::= { wsSecCryptoMapManualSaEntry 15 }

		
		-- 1.3.6.1.4.1.388.14.6.1.11
		wsSecCryptoMapTransformSetTable OBJECT-TYPE
			SYNTAX SEQUENCE OF WsSecCryptoMapTransformSetEntry
			MAX-ACCESS not-accessible
			STATUS current
			DESCRIPTION
				"Description."
			::= { wsSecVpnMib 11 }

		
		-- 1.3.6.1.4.1.388.14.6.1.11.1
		wsSecCryptoMapTransformSetEntry OBJECT-TYPE
			SYNTAX WsSecCryptoMapTransformSetEntry
			MAX-ACCESS not-accessible
			STATUS current
			DESCRIPTION
				"Description."
			INDEX { wsSecCryptoMapTransformCryptoMapSetSeqNum, wsSecCryptoMapTransformSetCryptoMapName, wsSecCryptoMapTransformSetName }
			::= { wsSecCryptoMapTransformSetTable 1 }

		
		WsSecCryptoMapTransformSetEntry ::=
			SEQUENCE { 
				wsSecCryptoMapTransformCryptoMapSetSeqNum
					Unsigned32,
				wsSecCryptoMapTransformSetCryptoMapName
					DisplayString,
				wsSecCryptoMapTransformSetName
					DisplayString,
				wsSecCryptoMapTransformSetRowStatus
					AbbrRowStatus
			 }

		-- 1.3.6.1.4.1.388.14.6.1.11.1.1
		wsSecCryptoMapTransformCryptoMapSetSeqNum OBJECT-TYPE
			SYNTAX Unsigned32 (1..1000)
			MAX-ACCESS read-only
			STATUS current
			DESCRIPTION
				"The wsSeqCryptoMapSequenceNum value in the 
				 corresponding wsSecCryptoMapEntry."
			::= { wsSecCryptoMapTransformSetEntry 1 }

		
		-- 1.3.6.1.4.1.388.14.6.1.11.1.2
		wsSecCryptoMapTransformSetCryptoMapName OBJECT-TYPE
			SYNTAX DisplayString
			MAX-ACCESS read-only
			STATUS current
			DESCRIPTION
				"The wsSeqCryptoMapName vlaue in the 
				 corresponding wsSecCryptoMapEntry."
			::= { wsSecCryptoMapTransformSetEntry 2 }

		
		-- 1.3.6.1.4.1.388.14.6.1.11.1.3
		wsSecCryptoMapTransformSetName OBJECT-TYPE
			SYNTAX DisplayString (SIZE (0..64))
			MAX-ACCESS read-only
			STATUS current
			DESCRIPTION
				"The wsSecTransformSetName value of the 
				 corresponding wsSecTransformSetEntry."
			::= { wsSecCryptoMapTransformSetEntry 3 }

		
		-- 1.3.6.1.4.1.388.14.6.1.11.1.4
		wsSecCryptoMapTransformSetRowStatus OBJECT-TYPE
			SYNTAX AbbrRowStatus
			MAX-ACCESS read-create
			STATUS current
			DESCRIPTION
				"Description."
			::= { wsSecCryptoMapTransformSetEntry 4 }

		
		-- 1.3.6.1.4.1.388.14.6.1.12
		wsSecCryptoMapIfMappingTable OBJECT-TYPE
			SYNTAX SEQUENCE OF WsSecCryptoMapIfMappingEntry
			MAX-ACCESS not-accessible
			STATUS current
			DESCRIPTION
				"Description."
			::= { wsSecVpnMib 12 }

		
		-- 1.3.6.1.4.1.388.14.6.1.12.1
		wsSecCryptoMapIfMappingEntry OBJECT-TYPE
			SYNTAX WsSecCryptoMapIfMappingEntry
			MAX-ACCESS not-accessible
			STATUS current
			DESCRIPTION
				"The entries are instantiated or deleted depending
				on the references from either wsSecCryptoMapManualSaTable
				or wsSecCryptoMapTable"
			INDEX { wsSecCryptoMapIfMappingCryptoMapName }
			::= { wsSecCryptoMapIfMappingTable 1 }

		
		WsSecCryptoMapIfMappingEntry ::=
			SEQUENCE { 
				wsSecCryptoMapIfMappingCryptoMapName
					DisplayString,
				wsSecCryptoMapIfMappingIfName
					DisplayString
			 }

		-- 1.3.6.1.4.1.388.14.6.1.12.1.1
		wsSecCryptoMapIfMappingCryptoMapName OBJECT-TYPE
			SYNTAX DisplayString
			MAX-ACCESS read-only
			STATUS current
			DESCRIPTION
				"Description."
			::= { wsSecCryptoMapIfMappingEntry 1 }

		
		-- 1.3.6.1.4.1.388.14.6.1.12.1.2
		wsSecCryptoMapIfMappingIfName OBJECT-TYPE
			SYNTAX DisplayString
			MAX-ACCESS read-write
			STATUS current
			DESCRIPTION
				"A layer three interface."
			::= { wsSecCryptoMapIfMappingEntry 2 }

		
		-- 1.3.6.1.4.1.388.14.6.1.13
		wsSecRadiusSvrTable OBJECT-TYPE
			SYNTAX SEQUENCE OF WsSecRadiusSvrEntry
			MAX-ACCESS not-accessible
			STATUS current
			DESCRIPTION
				"Description."
			::= { wsSecVpnMib 13 }

		
		-- 1.3.6.1.4.1.388.14.6.1.13.1
		wsSecRadiusSvrEntry OBJECT-TYPE
			SYNTAX WsSecRadiusSvrEntry
			MAX-ACCESS not-accessible
			STATUS current
			DESCRIPTION
				"Description."
			INDEX { wsSecRadiusSvrIPAddr }
			::= { wsSecRadiusSvrTable 1 }

		
		WsSecRadiusSvrEntry ::=
			SEQUENCE { 
				wsSecRadiusSvrIPAddr
					IpAddress,
				wsSecRadiusSvrType
					INTEGER,
				wsSecRadiusSvrPort
					Unsigned32,
				wsSecRadiusSvrSharedSecret
					OCTET STRING,
				wsSecRadiusSvrRowStatus
					AbbrRowStatus
			 }

		-- 1.3.6.1.4.1.388.14.6.1.13.1.1
		wsSecRadiusSvrIPAddr OBJECT-TYPE
			SYNTAX IpAddress
			MAX-ACCESS read-only
			STATUS current
			DESCRIPTION
				"Description."
			::= { wsSecRadiusSvrEntry 1 }

		
		-- 1.3.6.1.4.1.388.14.6.1.13.1.2
		wsSecRadiusSvrType OBJECT-TYPE
			SYNTAX INTEGER
				{
				primary(1),
				secondary(2)
				}
			MAX-ACCESS read-create
			STATUS current
			DESCRIPTION
				"Description."
			::= { wsSecRadiusSvrEntry 2 }

		
		-- 1.3.6.1.4.1.388.14.6.1.13.1.3
		wsSecRadiusSvrPort OBJECT-TYPE
			SYNTAX Unsigned32 (1024..65535)
			MAX-ACCESS read-create
			STATUS current
			DESCRIPTION
				"Description."
			::= { wsSecRadiusSvrEntry 3 }

		
		-- 1.3.6.1.4.1.388.14.6.1.13.1.4
		wsSecRadiusSvrSharedSecret OBJECT-TYPE
			SYNTAX OCTET STRING (SIZE (0..32))
			MAX-ACCESS read-create
			STATUS current
			DESCRIPTION
				"This object is null string when read."
			::= { wsSecRadiusSvrEntry 4 }

		
		-- 1.3.6.1.4.1.388.14.6.1.13.1.5
		wsSecRadiusSvrRowStatus OBJECT-TYPE
			SYNTAX AbbrRowStatus
			MAX-ACCESS read-create
			STATUS current
			DESCRIPTION
				"The following objects:
				   wsSecRadiusSvrType
				   wsSecRadiusSvrPort
				   wsSecRadiusSvrSharedSecret 
				 must be specified during a row creation.
				  "
			::= { wsSecRadiusSvrEntry 5 }

		
		-- 1.3.6.1.4.1.388.14.6.1.14
		wsSecRadiusSvrScalars OBJECT IDENTIFIER ::= { wsSecVpnMib 14 }

		
		-- 1.3.6.1.4.1.388.14.6.1.14.1
		wsSecRadiusSvrNasIdentifier OBJECT-TYPE
			SYNTAX DisplayString (SIZE (0..64))
			MAX-ACCESS read-write
			STATUS current
			DESCRIPTION
				"Description."
			::= { wsSecRadiusSvrScalars 1 }

		
		-- 1.3.6.1.4.1.388.14.6.1.15
		wsSecVpnUserTable OBJECT-TYPE
			SYNTAX SEQUENCE OF WsSecVpnUserEntry
			MAX-ACCESS not-accessible
			STATUS current
			DESCRIPTION
				"Description."
			::= { wsSecVpnMib 15 }

		
		-- 1.3.6.1.4.1.388.14.6.1.15.1
		wsSecVpnUserEntry OBJECT-TYPE
			SYNTAX WsSecVpnUserEntry
			MAX-ACCESS not-accessible
			STATUS current
			DESCRIPTION
				"Description."
			INDEX { wsSecVpnUserName }
			::= { wsSecVpnUserTable 1 }

		
		WsSecVpnUserEntry ::=
			SEQUENCE { 
				wsSecVpnUserName
					DisplayString,
				wsSecVpnUserPassword
					DisplayString,
				wsSecVpnUserRowStatus
					AbbrRowStatus
			 }

		-- 1.3.6.1.4.1.388.14.6.1.15.1.1
		wsSecVpnUserName OBJECT-TYPE
			SYNTAX DisplayString (SIZE (1..64))
			MAX-ACCESS read-only
			STATUS current
			DESCRIPTION
				"Description."
			::= { wsSecVpnUserEntry 1 }

		
		-- 1.3.6.1.4.1.388.14.6.1.15.1.2
		wsSecVpnUserPassword OBJECT-TYPE
			SYNTAX DisplayString (SIZE (8..21))
			MAX-ACCESS read-create
			STATUS current
			DESCRIPTION
				"Ths object returns NULL string when read."
			::= { wsSecVpnUserEntry 2 }

		
		-- 1.3.6.1.4.1.388.14.6.1.15.1.3
		wsSecVpnUserRowStatus OBJECT-TYPE
			SYNTAX AbbrRowStatus
			MAX-ACCESS read-create
			STATUS current
			DESCRIPTION
				"The object of wsSecVpnUserPassword must be specified
				 durning a row creation."
			::= { wsSecVpnUserEntry 3 }

		
		-- 1.3.6.1.4.1.388.14.6.1.16
		wsSecVpnAuth OBJECT IDENTIFIER ::= { wsSecVpnMib 16 }

		
		-- 1.3.6.1.4.1.388.14.6.1.16.1
		wsSecVPNAuthMethod OBJECT-TYPE
			SYNTAX INTEGER
				{
				none(1),
				localUserTable(2),
				radiusSvr(3)
				}
			MAX-ACCESS read-write
			STATUS current
			DESCRIPTION
				"Description."
			::= { wsSecVpnAuth 1 }

		
		-- 1.3.6.1.4.1.388.14.6.1.17
		wsSecIKESaStatsClearScalars OBJECT IDENTIFIER ::= { wsSecVpnMib 17 }

		
		-- 1.3.6.1.4.1.388.14.6.1.17.1
		wsSecIpSecClearPeerIpAddr OBJECT-TYPE
			SYNTAX DisplayString
			MAX-ACCESS read-write
			STATUS current
			DESCRIPTION
				"This object is to be used in
				conjuction with wsSecClearAction. 
				Use 0.0.0.0 as a wild card peer ip address."
			::= { wsSecIKESaStatsClearScalars 1 }

		
		-- 1.3.6.1.4.1.388.14.6.1.17.2
		wsSecClearAction OBJECT-TYPE
			SYNTAX INTEGER
				{
				clearIPSecSa(1),
				clearIKESa(2),
				clearIPSecSaAndIKESa(3)
				}
			MAX-ACCESS read-write
			STATUS current
			DESCRIPTION
				"This object is to be used in
				conjuction with wsSecClearPeerIpAddr"
			::= { wsSecIKESaStatsClearScalars 2 }

		
		-- 1.3.6.1.4.1.388.14.6.1.18
		wsSecIPSecSaStatusTable OBJECT-TYPE
			SYNTAX SEQUENCE OF WsSecIPSecSaStatusEntry
			MAX-ACCESS not-accessible
			STATUS current
			DESCRIPTION
				"Description."
			::= { wsSecVpnMib 18 }

		
		-- 1.3.6.1.4.1.388.14.6.1.18.1
		wsSecIPSecSaStatusEntry OBJECT-TYPE
			SYNTAX WsSecIPSecSaStatusEntry
			MAX-ACCESS not-accessible
			STATUS current
			DESCRIPTION
				"Description."
			INDEX { wsSecIPSecSaStatusIndex }
			::= { wsSecIPSecSaStatusTable 1 }

		
		WsSecIPSecSaStatusEntry ::=
			SEQUENCE { 
				wsSecIPSecSaStatusIndex
					Unsigned32,
				wsSecIPSecSaStatusLocalPeer
					DisplayString,
				wsSecIPSecSaStatusRemotePeer
					DisplayString,
				wsSecIPSecSaStatusEspSpiIn
					Unsigned32,
				wsSecIPSecSaStatusEspSpiOut
					Unsigned32,
				wsSecIPSecSaStatusAhSpiIn
					Unsigned32,
				wsSecIPSecSaStatusAhSpiOut
					Unsigned32,
				wsSecIPSecSaStatusAlgthmCipher
					DisplayString,
				wsSecIPSecSaStatusAlgthmMac
					DisplayString
			 }

		-- 1.3.6.1.4.1.388.14.6.1.18.1.1
		wsSecIPSecSaStatusIndex OBJECT-TYPE
			SYNTAX Unsigned32 (1..65535)
			MAX-ACCESS read-only
			STATUS current
			DESCRIPTION
				"Description."
			::= { wsSecIPSecSaStatusEntry 1 }

		
		-- 1.3.6.1.4.1.388.14.6.1.18.1.2
		wsSecIPSecSaStatusLocalPeer OBJECT-TYPE
			SYNTAX DisplayString
			MAX-ACCESS read-only
			STATUS current
			DESCRIPTION
				"Description."
			::= { wsSecIPSecSaStatusEntry 2 }

		
		-- 1.3.6.1.4.1.388.14.6.1.18.1.3
		wsSecIPSecSaStatusRemotePeer OBJECT-TYPE
			SYNTAX DisplayString
			MAX-ACCESS read-only
			STATUS current
			DESCRIPTION
				"Description."
			::= { wsSecIPSecSaStatusEntry 3 }

		
		-- 1.3.6.1.4.1.388.14.6.1.18.1.4
		wsSecIPSecSaStatusEspSpiIn OBJECT-TYPE
			SYNTAX Unsigned32
			MAX-ACCESS read-only
			STATUS current
			DESCRIPTION
				"Description."
			::= { wsSecIPSecSaStatusEntry 4 }

		
		-- 1.3.6.1.4.1.388.14.6.1.18.1.5
		wsSecIPSecSaStatusEspSpiOut OBJECT-TYPE
			SYNTAX Unsigned32
			MAX-ACCESS read-only
			STATUS current
			DESCRIPTION
				"Description."
			::= { wsSecIPSecSaStatusEntry 5 }

		
		-- 1.3.6.1.4.1.388.14.6.1.18.1.6
		wsSecIPSecSaStatusAhSpiIn OBJECT-TYPE
			SYNTAX Unsigned32
			MAX-ACCESS read-only
			STATUS current
			DESCRIPTION
				"Description."
			::= { wsSecIPSecSaStatusEntry 6 }

		
		-- 1.3.6.1.4.1.388.14.6.1.18.1.7
		wsSecIPSecSaStatusAhSpiOut OBJECT-TYPE
			SYNTAX Unsigned32
			MAX-ACCESS read-only
			STATUS current
			DESCRIPTION
				"Description."
			::= { wsSecIPSecSaStatusEntry 7 }

		
		-- 1.3.6.1.4.1.388.14.6.1.18.1.8
		wsSecIPSecSaStatusAlgthmCipher OBJECT-TYPE
			SYNTAX DisplayString
			MAX-ACCESS read-only
			STATUS current
			DESCRIPTION
				"Description."
			::= { wsSecIPSecSaStatusEntry 8 }

		
		-- 1.3.6.1.4.1.388.14.6.1.18.1.9
		wsSecIPSecSaStatusAlgthmMac OBJECT-TYPE
			SYNTAX DisplayString
			MAX-ACCESS read-only
			STATUS current
			DESCRIPTION
				"Description."
			::= { wsSecIPSecSaStatusEntry 9 }

		
		-- 1.3.6.1.4.1.388.14.6.1.19
		wsSecIKESaStatsTable OBJECT-TYPE
			SYNTAX SEQUENCE OF WsSecIKESaStatsEntry
			MAX-ACCESS not-accessible
			STATUS current
			DESCRIPTION
				"Description."
			::= { wsSecVpnMib 19 }

		
		-- 1.3.6.1.4.1.388.14.6.1.19.1
		wsSecIKESaStatsEntry OBJECT-TYPE
			SYNTAX WsSecIKESaStatsEntry
			MAX-ACCESS not-accessible
			STATUS current
			DESCRIPTION
				"Description."
			INDEX { wsSecIKESaStatIndex }
			::= { wsSecIKESaStatsTable 1 }

		
		WsSecIKESaStatsEntry ::=
			SEQUENCE { 
				wsSecIKESaStatIndex
					Unsigned32,
				wsSecIKESaStatsPhase1Done
					TruthValue,
				wsSecIKESaStatsNumOfNegotions
					Unsigned32,
				wsSecIKESaStatsNumOfBytes
					Unsigned32,
				wsSecIKESaStatsCreateDate
					DateAndTime,
				wsSecIKESaStatsEncrptAlgthm
					DisplayString,
				wsSecIKESaStatsHashAlgthm
					DisplayString,
				wsSecIKESaStatsPrfAlgthm
					DisplayString,
				wsSecIKESaStatsLocalIdentity
					DisplayString,
				wsSecIKESaStatsRemoteIdentity
					DisplayString
			 }

		-- 1.3.6.1.4.1.388.14.6.1.19.1.1
		wsSecIKESaStatIndex OBJECT-TYPE
			SYNTAX Unsigned32 (1..65535)
			MAX-ACCESS read-only
			STATUS current
			DESCRIPTION
				"Description."
			::= { wsSecIKESaStatsEntry 1 }

		
		-- 1.3.6.1.4.1.388.14.6.1.19.1.2
		wsSecIKESaStatsPhase1Done OBJECT-TYPE
			SYNTAX TruthValue
			MAX-ACCESS read-only
			STATUS current
			DESCRIPTION
				"Description."
			::= { wsSecIKESaStatsEntry 2 }

		
		-- 1.3.6.1.4.1.388.14.6.1.19.1.3
		wsSecIKESaStatsNumOfNegotions OBJECT-TYPE
			SYNTAX Unsigned32
			MAX-ACCESS read-only
			STATUS current
			DESCRIPTION
				"Description."
			::= { wsSecIKESaStatsEntry 3 }

		
		-- 1.3.6.1.4.1.388.14.6.1.19.1.4
		wsSecIKESaStatsNumOfBytes OBJECT-TYPE
			SYNTAX Unsigned32
			MAX-ACCESS read-only
			STATUS current
			DESCRIPTION
				"Description."
			::= { wsSecIKESaStatsEntry 4 }

		
		-- 1.3.6.1.4.1.388.14.6.1.19.1.5
		wsSecIKESaStatsCreateDate OBJECT-TYPE
			SYNTAX DateAndTime
			MAX-ACCESS read-only
			STATUS current
			DESCRIPTION
				"Description."
			::= { wsSecIKESaStatsEntry 5 }

		
		-- 1.3.6.1.4.1.388.14.6.1.19.1.6
		wsSecIKESaStatsEncrptAlgthm OBJECT-TYPE
			SYNTAX DisplayString
			MAX-ACCESS read-only
			STATUS current
			DESCRIPTION
				"Description."
			::= { wsSecIKESaStatsEntry 6 }

		
		-- 1.3.6.1.4.1.388.14.6.1.19.1.7
		wsSecIKESaStatsHashAlgthm OBJECT-TYPE
			SYNTAX DisplayString
			MAX-ACCESS read-only
			STATUS current
			DESCRIPTION
				"Description."
			::= { wsSecIKESaStatsEntry 7 }

		
		-- 1.3.6.1.4.1.388.14.6.1.19.1.8
		wsSecIKESaStatsPrfAlgthm OBJECT-TYPE
			SYNTAX DisplayString
			MAX-ACCESS read-only
			STATUS current
			DESCRIPTION
				"Description."
			::= { wsSecIKESaStatsEntry 8 }

		
		-- 1.3.6.1.4.1.388.14.6.1.19.1.9
		wsSecIKESaStatsLocalIdentity OBJECT-TYPE
			SYNTAX DisplayString
			MAX-ACCESS read-only
			STATUS current
			DESCRIPTION
				"Description."
			::= { wsSecIKESaStatsEntry 9 }

		
		-- 1.3.6.1.4.1.388.14.6.1.19.1.10
		wsSecIKESaStatsRemoteIdentity OBJECT-TYPE
			SYNTAX DisplayString
			MAX-ACCESS read-only
			STATUS current
			DESCRIPTION
				"Description."
			::= { wsSecIKESaStatsEntry 10 }

		
		-- 1.3.6.1.4.1.388.14.6.1.20
		wsSecVPNScalars OBJECT IDENTIFIER ::= { wsSecVpnMib 20 }

		
		-- 1.3.6.1.4.1.388.14.6.1.20.1
		wsSecVPNSetError OBJECT-TYPE
			SYNTAX DisplayString
			MAX-ACCESS read-only
			STATUS current
			DESCRIPTION
				"This object shows the error message from the previous
				 Set request to an object in this WS-SEC-VPN-MIB."
			::= { wsSecVPNScalars 1 }

		
		-- 1.3.6.1.4.1.388.14.6.1.21
		wsSecVpnConformance OBJECT IDENTIFIER ::= { wsSecVpnMib 21 }

		
		-- 1.3.6.1.4.1.388.14.6.1.21.1
		wsSecVpnCompliances OBJECT IDENTIFIER ::= { wsSecVpnConformance 1 }

		
		-- 1.3.6.1.4.1.388.14.6.1.21.1.1
		wsSecVpnCompliance MODULE-COMPLIANCE
			STATUS current
			DESCRIPTION 
				"Description."
			MODULE -- this module
				MANDATORY-GROUPS { wsSecVpnGroup }
			::= { wsSecVpnCompliances 1 }

		
		-- 1.3.6.1.4.1.388.14.6.1.22
		wsSecVpnGroups OBJECT IDENTIFIER ::= { wsSecVpnMib 22 }

		
		-- 1.3.6.1.4.1.388.14.6.1.23
		wsSecVpnGroup OBJECT-GROUP
			OBJECTS { wsSecIKEPolicyRowStatus, wsSecIKEKeepAlive, wsSecTransformSetName, wsSecTransformSetMode, wsSecTransformSetEspEncr, 
				wsSecTransformSetEspAuth, wsSecTransformSetRowStatus, wsSecVpnSALifeTimeSec, wsSecVpnSALifeTimeKB, wsSecClientDNSServerIP, 
				wsSecClientWinServerIP, wsSecCryptoMapSequenceNum, wsSecPreSharedKeyRowStatus, wsSecTransformSetAHAuth, wsSecCryptoMapName, 
				wsSecCryptoMapACLId, wsSecCryptoMapPFS, wsSecCryptoMapSAPerHostEnable, wsSecCryptoMapRowStatus, wsSecCryptoMapPeerRowStatus, 
				wsSecCryptoMapManualSaCryptoMapSeqNum, wsSecCryptoMapManualSaCryptoMapName, wsSecCryptoMapManualSaIKEPeer, wsSecCryptoMapManualSaAclId, wsSecCryptoMapManualSaInAhSpi, 
				wsSecCryptoMapManualSaOutAhSpi, wsSecCryptoMapManualSaInEspSpi, wsSecCryptoMapManualSaOutEspSpi, wsSecCryptoMapManualSaRowStatus, wsSecRadiusSvrIPAddr, 
				wsSecRadiusSvrType, wsSecRadiusSvrPort, wsSecRadiusSvrSharedSecret, wsSecRadiusSvrRowStatus, wsSecVpnUserName, 
				wsSecVpnUserPassword, wsSecVpnUserRowStatus, wsSecClearAction, wsSecIPSecSaStatusIndex, wsSecIPSecSaStatusLocalPeer, 
				wsSecIPSecSaStatusRemotePeer, wsSecIPSecSaStatusEspSpiOut, wsSecIPSecSaStatusAhSpiIn, wsSecIPSecSaStatusAhSpiOut, wsSecIPSecSaStatusAlgthmCipher, 
				wsSecIPSecSaStatusAlgthmMac, wsSecIKESaStatIndex, wsSecIKESaStatsNumOfNegotions, wsSecIKESaStatsNumOfBytes, wsSecIKESaStatsCreateDate, 
				wsSecIKESaStatsEncrptAlgthm, wsSecIKESaStatsHashAlgthm, wsSecIKESaStatsPrfAlgthm, wsSecIKESaStatsLocalIdentity, wsSecIKESaStatsRemoteIdentity, 
				wsSecIKESaStatsPhase1Done, wsSecVPNAuthMethod, wsSecCryptoMapManualSaTSName, wsSecCryptoMapModeCfgEnable, wsSecVPNSetError, 
				wsSecRadiusSvrNasIdentifier, wsSecIKEPolicySaLifeTimeSec, wsSecIKEPolicyDHGroup, wsSecIKEPolicyAuthType, wsSecIKEPolicyHash, 
				wsSecIKEPolicyEncryption, wsSecIKEPolicyPriority, wsSecCryptoMapIfMappingCryptoMapName, wsSecCryptoMapIfMappingIfName, wsSecCryptoMapTransformSetRowStatus, 
				wsSecCryptoMapTransformSetName, wsSecCryptoMapTransformSetCryptoMapName, wsSecCryptoMapPeerIKEPeer, wsSecCryptoMapPeerName, wsSecCryptoMapPeerSequenceNum, 
				wsSecLocalIPAddrPoolRowStatus, wsSecLocalIPAddrPoolAddrRangeEnd, wsSecLocalIPAddrPoolAddrRangeStart, wsSecPreSharedKeyIKEAggressive, wsSecPreSharedKeyIKEPeerKey, 
				wsSecPreSharedKeyIKEPeerIdentity, wsSecPreSharedKeyIKEPeer, wsSecISAKMPLocalIdentity, wsSecCryptoMapTransformCryptoMapSetSeqNum, wsSecIPSecSaStatusEspSpiIn, 
				wsSecIpSecClearPeerIpAddr, wsSecCryptoMapManualSaAhOrEsp, wsSecCryptoMapManualSaOutEspCipherKey, wsSecCryptoMapManualSaInEspCipherKey, wsSecCryptoMapManualSaOutAuthKey, 
				wsSecCryptoMapSALifeTimeSec, wsSecCryptoMapSALifeTimeKB, wsSecCryptoMapManualSaInAuthKey, wsSecCryptoMapMode, wsSecCryptoMapRemoteType, 
				wsSecCryptoMapLocalIdType, wsSecCryptoMapLocalId }
			STATUS current
			DESCRIPTION 
				"Description."
			::= { wsSecVpnMib 23 }

		
	
	END

--
-- WS-SEC-VPN-MIB.my
--
