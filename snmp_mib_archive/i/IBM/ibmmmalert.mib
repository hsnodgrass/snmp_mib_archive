------------------------------------------------------------------------------
------------------------------------------------------------------------------
--
-- File         : mmalert.mib
-- Description  : IBM Management Module traps
--                 MIB for traps(Alerts)
-- By           : Joe Bolan, IBM
-- Version      : 1.2
-- Date         : December 20, 2002
--
--
-- Copyright (c) 2002/2003 IBM  All Rights Reserved.
--
--
-- Contains trap descriptions for:
--  (1) Bladecenter Management Module
--
--
-- Changes History
--
-- Date       Reason
--------------------
-- 4/08/02    Lorrie - Created
-- 12/20/02   jeb - Fix priority to include recovery, move SFF to critical, text on KVM/CD
--
------------------------------------------------------------------------------
-- This MIB is used by the Management Module to describe
-- traps for alert conditions detected by the MM/Blades on Bladecenter hardware.
------------------------------------------------------------------------------
------------------------------------------------------------------------------
        BLADESPPALT-MIB DEFINITIONS ::= BEGIN


        IMPORTS
            OBJECT-TYPE                          FROM RFC-1212
            enterprises                          FROM RFC1155-SMI
            DisplayString                        FROM RFC1213-MIB
            TRAP-TYPE                            FROM RFC-1215;


        ibm            OBJECT IDENTIFIER ::=   { enterprises 2 }

        -- IBM products group

        ibmProd        OBJECT IDENTIFIER ::=   { ibm 6 }

        -- IBM Netfinity SP

        supportProcessor OBJECT IDENTIFIER ::= { ibmProd 158 }

        -- IBM Netfinity SP Alert

        ibmRemoteSupTrapMIB     OBJECT IDENTIFIER ::= { supportProcessor 2 }

----------------------------------------------------------------
-- Start: Management Module Adapter SP Alerts
----------------------------------------------------------------

        -- the rsspalt generic trap generator group

        ibmRemoteSupTrapMibObjects OBJECT IDENTIFIER ::= { ibmRemoteSupTrapMIB 1 }


        ibmSpTrapInfo OBJECT IDENTIFIER ::= { ibmRemoteSupTrapMibObjects 2 }

        ibmSpTrapDateTime  OBJECT-TYPE
                       SYNTAX  DisplayString
                       ACCESS  read-only
                       STATUS  mandatory
                       DESCRIPTION
                       "Timestamp of Local Date and Time when alert was generated"
                       ::= { ibmSpTrapInfo 1 }

        ibmSpTrapAppId    OBJECT-TYPE
                       SYNTAX  DisplayString
                       ACCESS  read-only
                       STATUS  mandatory
                       DESCRIPTION
                       "Application ID, always 'BladeCenter Management Module'"
                       ::= { ibmSpTrapInfo 2 }

        ibmSpTrapSpTxtId  OBJECT-TYPE
                       SYNTAX  DisplayString
                       ACCESS  read-only
                       STATUS  mandatory
                       DESCRIPTION
                       "SP System Identification - Text Identification"
                       ::= { ibmSpTrapInfo 3 }

        ibmSpTrapSysUuid  OBJECT-TYPE
                       SYNTAX  DisplayString
                       ACCESS  read-only
                       STATUS  mandatory
                       DESCRIPTION
                       "Host System UUID(Universal Unique ID)"
                       ::= { ibmSpTrapInfo 4 }

        ibmSpTrapSysSern  OBJECT-TYPE
                       SYNTAX  DisplayString
                       ACCESS  read-only
                       STATUS  mandatory
                       DESCRIPTION
                       "Host System Serial Number"
                       ::= { ibmSpTrapInfo 5 }

        ibmSpTrapAppType  OBJECT-TYPE
                       SYNTAX  INTEGER (1..65535)
                       ACCESS  read-only
                       STATUS  mandatory
                       DESCRIPTION
                       "Application Alert Type - Event Number ID"
                       ::= { ibmSpTrapInfo 6 }

        ibmSpTrapPriority  OBJECT-TYPE
                       SYNTAX  INTEGER (1..65535)
                       ACCESS  read-only
                       STATUS  mandatory
                       DESCRIPTION
                       "Alert Severity Value
                          - Critical Alert(0)
                          - Non-Critical Alert(2)
                          - System Alert(4)
                          - Recovery Alert(8)
                          - Informational Only Alert(255)"
                       ::= { ibmSpTrapInfo 7 }

        ibmSpTrapMsgText  OBJECT-TYPE
                       SYNTAX  DisplayString
                       ACCESS  read-only
                       STATUS  mandatory
                       DESCRIPTION
                       "Alert Message Text"
                       ::= { ibmSpTrapInfo 8 }

        ibmSpTrapHostContact  OBJECT-TYPE
                       SYNTAX  DisplayString
                       ACCESS  read-only
                       STATUS  mandatory
                       DESCRIPTION
                       "Host Contact"
                       ::= { ibmSpTrapInfo 9 }

        ibmSpTrapHostLocation  OBJECT-TYPE
                       SYNTAX  DisplayString
                       ACCESS  read-only
                       STATUS  mandatory
                       DESCRIPTION
                       "Host Location"
                       ::= { ibmSpTrapInfo 10 }

        ibmSpTrapBladeName  OBJECT-TYPE
                       SYNTAX  DisplayString
                       ACCESS  read-only
                       STATUS  mandatory
                       DESCRIPTION
                       "Blade Name"
                       ::= { ibmSpTrapInfo 11 }

        ibmSpTrapBladeSern  OBJECT-TYPE
                       SYNTAX  DisplayString
                       ACCESS  read-only
                       STATUS  mandatory
                       DESCRIPTION
                       "Blade Serial Number"
                       ::= { ibmSpTrapInfo 12 }

        ibmSpTrapBladeUuid  OBJECT-TYPE
                       SYNTAX  DisplayString
                       ACCESS  read-only
                       STATUS  mandatory
                       DESCRIPTION
                       "Blade UUID(Universal Unique ID)"
                       ::= { ibmSpTrapInfo 13 }

        -- 4.2.1.1
        ibmSpTrapTempC          TRAP-TYPE
                                ENTERPRISE  ibmRemoteSupTrapMIB
                                VARIABLES
                                  {
                                  ibmSpTrapDateTime,
                                  ibmSpTrapAppId,
                                  ibmSpTrapSpTxtId,
                                  ibmSpTrapSysUuid,
                                  ibmSpTrapSysSern,
                                  ibmSpTrapAppType,
                                  ibmSpTrapPriority,
                                  ibmSpTrapMsgText,
                                  ibmSpTrapHostContact,
                                  ibmSpTrapHostLocation,
                                  ibmSpTrapBladeName,
                                  ibmSpTrapBladeSern,
                                  ibmSpTrapBladeUuid
                                  }
                                  DESCRIPTION
                                    "Critical Alert: Temperature threshold exceeded."
                                  ::= 00

        -- 4.2.1.2
        ibmSpTrapVoltC        TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "Critical Alert: Voltage threshold exceeded."
                                ::= 01

        -- 4.2.1.3 
        ibmSpTrapTampC        TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "Critical Alert: Physical intrusion of system has occurred."
                                ::= 02

        -- 4.2.1.4
        ibmSpTrapMffC         TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "Critical Alert: Multiple fan failure."
                                ::= 03

        -- 4.2.1.5
        ibmSpTrapPsC          TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "Critical Alert: Power supply failure."
                                ::= 04

        -- 4.2.1.6
        ibmSpTrapHdC          TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "Critical Alert: Hard disk drive failure."
                                ::= 05

        -- 4.2.1.7
        ibmSpTrapVrmC         TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "Critical Alert: Voltage Regulator Module(VRM) failure."
                                ::= 06

        -- 4.2.2.2
        ibmSpTrapSffC         TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "Critical Alert: Single Fan failure."
                                ::= 11


        -- 4.2.1.8
        ibmSpTrapMsC          TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "Critical Alert: Multiple switch module failure."
                                ::= 31

        -- 4.2.1.9
        ibmSpTrapIhcC         TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "Critical Alert: Incompatible hardware configuration."
                                ::= 36

        -- 4.2.2.1
        ibmSpTrapRdpsN          TRAP-TYPE
                                ENTERPRISE  ibmRemoteSupTrapMIB
                                VARIABLES
                                  {
                                  ibmSpTrapDateTime,
                                  ibmSpTrapAppId,
                                  ibmSpTrapSpTxtId,
                                  ibmSpTrapSysUuid,
                                  ibmSpTrapSysSern,
                                  ibmSpTrapAppType,
                                  ibmSpTrapPriority,
                                  ibmSpTrapMsgText,
                                  ibmSpTrapHostContact,
                                  ibmSpTrapHostLocation,
                                  ibmSpTrapBladeName,
                                  ibmSpTrapBladeSern,
                                  ibmSpTrapBladeUuid
                                  }
                                  DESCRIPTION
                                    "Non-Critical Alert: Redundant Power Supply failure."
                                  ::= 10

        -- 4.2.2.3
        ibmSpTrapTempN        TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "Non-Critical Alert: Temperature threshold exceeded."
                                ::= 12

        -- 4.2.2.4
        ibmSpTrapVoltN        TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "Non-Critical Alert: Voltage threshold exceeded."
                                ::= 13

        -- 4.2.2.6
        ibmSpTrapRmN          TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "Non-Critical Alert: Redundant module."
                                ::= 32


        -- 5.2.14
        ibmSpTrapSecDvS       TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: Secondary Device warning."
                                ::= 15

        -- 4.2.3.1
        ibmSpTrapPostToS      TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: Post Timeout value exceeded."
                                ::= 20

        -- 4.2.3.2
        ibmSpTrapOsToS        TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: OS Timeout value exceeded."
                                ::= 21

        -- 4.2.3.3
        ibmSpTrapAppS         TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: Application Alert."
                                ::= 22

        -- 4.2.3.4
        ibmSpTrapPoffS        TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: Power Off."
                                ::= 23

        -- 4.2.3.5
        ibmSpTrapPonS         TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: Power On."
                                ::= 24

        -- 4.2.3.6
        ibmSpTrapBootS        TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: System Boot Failure."
                                ::= 25

        -- 4.2.3.7
        ibmSpTrapLdrToS       TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: OS Loader Timeout."
                                ::= 26

        -- 4.2.3.8
        ibmSpTrapPFAS         TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: Predictive Failure Analysis(PFA) information."
                                ::= 27

        -- 4.2.3.9
        ibmSpTrapKVMSwitchS   TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: Keyboard/Video/Mouse(KVM) or Medial Tray(MT) switching failure."
                                ::= 33

        -- 4.2.3.10
        ibmSpTrapSysInvS      TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: Inventory."
                                ::= 34

        -- 4.2.3.11
        ibmSpTrapSysLogS      TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: System Log 75% full."
                                ::= 35

        -- 4.2.3.12
        ibmSpTrapNwChangeS    TRAP-TYPE
                              ENTERPRISE  ibmRemoteSupTrapMIB
                              VARIABLES
                                {
                                ibmSpTrapDateTime,
                                ibmSpTrapAppId,
                                ibmSpTrapSpTxtId,
                                ibmSpTrapSysUuid,
                                ibmSpTrapSysSern,
                                ibmSpTrapAppType,
                                ibmSpTrapPriority,
                                ibmSpTrapMsgText,
                                ibmSpTrapHostContact,
                                ibmSpTrapHostLocation,
                                ibmSpTrapBladeName,
                                ibmSpTrapBladeSern,
                                ibmSpTrapBladeUuid
                                }
                                DESCRIPTION
                                  "System Alert: Network change notification."
                                ::= 37
END
