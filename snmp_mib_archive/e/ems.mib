HP-EMS DEFINITIONS ::= BEGIN

       IMPORTS
           enterprises, Integer32, IpAddress, OBJECT-TYPE, MODULE-IDENTITY,
           NOTIFICATION-TYPE
               FROM SNMPv2-SMI;

       hp                OBJECT IDENTIFIER ::= { enterprises 11 }
       nm                OBJECT IDENTIFIER ::= { hp 2 }
       system            OBJECT IDENTIFIER ::= { nm 3 }
       general           OBJECT IDENTIFIER ::= { system 1 }

       hpEMSMod MODULE-IDENTITY
            LAST-UPDATED "0309190000Z"
            ORGANIZATION "Hewlett Packard Company,
                          Manageability Solutions Lab"
            CONTACT-INFO
                    "Hewlett Packard Company
                     10955 Tantau Ave.
                     Cupertino, CA 95014"
            DESCRIPTION
                    "This MIB module describes traps generated by
                    the Event Monitor Service (EMS)."

            REVISION     "0309190000Z"
            DESCRIPTION
                    "Initial version of this MIB module."
            ::= { general 7 }
       
       hpEMSTraps 			OBJECT IDENTIFIER ::= { hpEMSMod 0 }
       hpEMSObjects 		OBJECT IDENTIFIER ::= { hpEMSMod 1 }
       
       hpEMSNotify 			OBJECT IDENTIFIER ::= { hpEMSObjects 1 }
       hpEMSMonitor		 	OBJECT IDENTIFIER ::= { hpEMSObjects 2 }

       -- HP EMS Objects use as varbinds in traps

		hpEMSResourceName OBJECT-TYPE
		    SYNTAX  OCTET STRING
		    ACCESS  read-only
		    STATUS  mandatory
		    DESCRIPTION
		           "Full EMS name of the resource being monitored"
		    ::= { hpEMSNotify 1 }

		hpEMSRequestID OBJECT-TYPE
		    SYNTAX  INTEGER
		    ACCESS  read-only
		    STATUS  mandatory
		    DESCRIPTION
		           "A unique identifier for the monitoring request"
		    ::= { hpEMSNotify 2 }

		hpEMSOperator OBJECT-TYPE
		    SYNTAX  OCTET STRING
		    ACCESS  read-only
		    STATUS  mandatory
		    DESCRIPTION
		           "Operator indicates poll, change or threshold condition 
		           operator: >, >=, <, <=, ==, !="
		    ::= { hpEMSNotify 3 }

		hpEMSResourceType OBJECT-TYPE
		    SYNTAX  INTEGER
		    ACCESS  read-only
		    STATUS  mandatory
		    DESCRIPTION
		           "Integer representing the resource type:
						3009 = String 
						3010 = Sbit32 (signed 32 bit integer)
						3011 = Ubit32 (unsigned 32 bit integer)
						3012 = Sbit64 (future use)
						3013 = Ubit64 (future use)
						3014 = Float64 (64 floating point number)
						3015 = Enumerated Type
						3016 = Error "
		    ::= { hpEMSNotify 4 }

		hpEMSResourceValue OBJECT-TYPE
		    SYNTAX  OCTET STRING
		    ACCESS  read-only
		    STATUS  mandatory
		    DESCRIPTION
		           "Quoted string representing resource value, 
		           should be converted using  the Resource Type 
		           indicated in Variable #4 
					Not applicable if Resource Type is Error"
		    ::= { hpEMSNotify 5 }

		hpEMSThresholdType OBJECT-TYPE
		    SYNTAX  INTEGER
		    ACCESS  read-only
		    STATUS  mandatory
		    DESCRIPTION
		           "Integer representing the threshold type, 
		           this is usually the same as resource type. 
		           Integer representing the threshold type:
					3009 = String 
					3010 = Sbit32 (signed 32 bit integer)
					3011 = Ubit32 (unsigned 32 bit integer)
					3012 = Sbit64 (future use)
					3013 = Ubit64 (future use)
					3014 = Float64 (64 floating point number)
					3015 = Enumerated Type
					3016 = Error 
					Not applicable if operator is poll or change; or if Resource Type is Error
					Note:  enumerated type is not supported as threshold type."
		    ::= { hpEMSNotify 6 }

		hpEMSThresholdValue OBJECT-TYPE
		    SYNTAX  OCTET STRING
		    ACCESS  read-only
		    STATUS  mandatory
		    DESCRIPTION
		           "Quoted string representing threshold value, 
		           should be converted using the Threshold Type 
		           indicated in Variable #6. 
					Not applicable if operator is poll or change; 
					or if Resource Type is Error"
		    ::= { hpEMSNotify 7 }

		hpEMSUserDataFlag OBJECT-TYPE
		    SYNTAX  INTEGER
		    ACCESS  read-only
		    STATUS  mandatory
		    DESCRIPTION
		           "Indicates that additional user data is available from EMS
					0	= no user data
					1	= user (comment) data exists"
		    ::= { hpEMSNotify 8 }

		hpEMSMonitorDataFlag OBJECT-TYPE
		    SYNTAX  INTEGER
		    ACCESS  read-only
		    STATUS  mandatory
		    DESCRIPTION
		           "Indicates that additional monitor data is available from EMS
					0	= no monitor data
					1	= monitor data exists"
		    ::= { hpEMSNotify 9 }

		hpEMSNotificationTrigger OBJECT-TYPE
		    SYNTAX  INTEGER
		    ACCESS  read-only
		    STATUS  mandatory
		    DESCRIPTION
		           "Indicates whether normal or problem event
					0	= normal 
					1	= abnormal (threshold is true)
					5	= abnormal (severity is normal)
					6	= abnormal (severity is warning)
					7	= abnormal (severity is minor)
					8	= abnormal (severity is major)
					9	= abnormal (severity is critical) "
		    ::= { hpEMSNotify 10 }

		hpEMSEventType OBJECT-TYPE
		    SYNTAX  OCTET STRING
		    ACCESS  read-only
		    STATUS  mandatory
		    DESCRIPTION
		           "String representing event type:
					Poll       (for 'At Every Interval')
					Change  (for 'When value changes')
					Normal  (for when threshold condition is not true)
					Problem  (for when threshold condition is true)
					Error "
		    ::= { hpEMSNotify 11 }

		hpEMSNotifyID OBJECT-TYPE
		    SYNTAX  INTEGER
		    ACCESS  read-only
		    STATUS  mandatory
		    DESCRIPTION
		           "Unique identifier for this particular event"
		    ::= { hpEMSNotify 12 }

		hpEMSRestartType OBJECT-TYPE
		    SYNTAX  OCTET STRING
		    ACCESS  read-only
		    STATUS  mandatory
		    DESCRIPTION
		           "REBOOT or RESTART"
		    ::= { hpEMSMonitor 1 }

		hpEMSMonitorTitle OBJECT-TYPE
		    SYNTAX  OCTET STRING
		    ACCESS  read-only
		    STATUS  mandatory
		    DESCRIPTION
		           "Title of the monitor affected by the outage"
		    ::= { hpEMSMonitor 2 }

		hpEMSCommand OBJECT-TYPE
		    SYNTAX  OCTET STRING
		    ACCESS  read-only
		    STATUS  mandatory
		    DESCRIPTION
		           "Command used to launch the monitor"
		    ::= { hpEMSMonitor 3 }

		hpEMSVendor OBJECT-TYPE
		    SYNTAX  OCTET STRING
		    ACCESS  read-only
		    STATUS  mandatory
		    DESCRIPTION
		           "Vendor who supplied the monitor"
		    ::= { hpEMSMonitor 4 }

		hpEMSVersion OBJECT-TYPE
		    SYNTAX  OCTET STRING
		    ACCESS  read-only
		    STATUS  mandatory
		    DESCRIPTION
		           "Version of the monitor"
		    ::= { hpEMSMonitor 5 }

		hpEMSPID OBJECT-TYPE
		    SYNTAX  INTEGER
		    ACCESS  read-only
		    STATUS  mandatory
		    DESCRIPTION
		           "Process ID of the monitor"
		    ::= { hpEMSMonitor 6 }

		hpEMSMonitorKey OBJECT-TYPE
		    SYNTAX  OCTET STRING
		    ACCESS  read-only
		    STATUS  mandatory
		    DESCRIPTION
		           "Unique identified for this monitor, 
		           to be used for running resdata to get list 
		           of resources affected by the monitor outage."
		    ::= { hpEMSMonitor 7 }

       -- HP EMS Traps

       hpEMSNormalEvent NOTIFICATION-TYPE
           OBJECTS    { 
           		hpEMSResourceName,
           		hpEMSRequestID,
           		hpEMSOperator,
           		hpEMSResourceType,
           		hpEMSResourceValue,
           		hpEMSThresholdType,
           		hpEMSThresholdValue,
           		hpEMSUserDataFlag,
           		hpEMSMonitorDataFlag,
           		hpEMSNotificationTrigger,
           		hpEMSEventType,
           		hpEMSNotifyID
            }
           STATUS     current
           DESCRIPTION
                   "The Event Monitoring Service (EMS) has generated an event 
					for a monitored resource.
					
					A Normal Event occurs when the value of the resource is in 
					a 'normal' state and the threshold condition is not true.
					Monitoring requests configured for initial or return 
					notification may generate this event.  Also, the initial
					notification for a Change event is 'normal'.   
					
					The data passed with the event:
					
					  1)  The name of the resource being monitored.
					
					  2)  The request id, a unique identifier for the 
					      monitoring request.  This value should be used when 
					      using resdata to retrieve additional information
					      about the event.
					
					  3)  The operator used by EMS to determine when event 
					      notifications should be sent.  Possible values 
					      include:  poll, change, >, >=, <, <=, = and !=.
					 
					  4)  The resource type, which defines the type of value 
					      being monitored.  Possible values include:  string, 
					      enumerated, integer, and float.
					 
					  5)  The resource value, which is the current value of the 
					      resource being monitored.  It is converted based on 
					      the resource type.
					
					  6)  The threshold type (usually the same as the resource
					      type) defines the type of value configured for the
					      threshold.  Possible values include: string, 
					      integer, and float.
					
					  7)  The threshold value configured for the resource being 
					      monitored.
					
					  8)  The user data flag, which indicates whether or not 
					      user data are available.  User data are comments 
					      provided by the user when the request was configured.
					      User data can be retrieved on the source node by 
					      running:
					        /opt/resmon/bin/resdata -r <resource name> \
					        -R <request id> -u 
					
					  9)  The monitor data flag, which indicates whether or not 
					      the monitor has additional data regarding the event.
					      Additional data provided by the resource monitor
					      can be retrieved on the source node by running:
					        /opt/resmon/bin/resdata -r <resource name> \
					        -R <request id> [-n <notify id>] -m 
						  
					 10)  The notification trigger indicates if the resource 
					      condition is normal or not.  For an EMSNormalEvent 
					      trap, the notification trigger is normal.
					
					 11)  The event type indicates the type of notification 
					      being sent.  The different types are:  
					        Poll    - for notification at every interval
					        Change  - for notification when the value changes
					        Normal  - for notification when the threshold
					                  condition for the resource is not true 
					        Problem - for notification when the threshold 
					                  condition for the resource is true 
					        Error   - for notification when the monitor 
					                  encountered an error determining
					                  the resource value
					
					 12)  The notify id, a unique identifier for a specific
					      notification event.  This value should be used when 
					      using resdata to retrieve additional information
					      about the event.  Monitor data can be retrieved
					      on the source node by running:
					        /opt/resmon/bin/resdata -r <resource name> \
					        -R <request id> [-n <notify id>] -m "

           ::= { hpEMSTraps 1 }

       hpEMSProblemEvent NOTIFICATION-TYPE
           OBJECTS    { 
           		hpEMSResourceName,
           		hpEMSRequestID,
           		hpEMSOperator,
           		hpEMSResourceType,
           		hpEMSResourceValue,
           		hpEMSThresholdType,
           		hpEMSThresholdValue,
           		hpEMSUserDataFlag,
           		hpEMSMonitorDataFlag,
           		hpEMSNotificationTrigger,
           		hpEMSEventType,
           		hpEMSNotifyID
            }
           STATUS     current
           DESCRIPTION
				"The Event Monitoring Service (EMS) has generated an event 
				for a monitored resource.  
				
				A Problem Event occurs when the threshold condition defined
				for the resource is true.
				
				A Change Event occurs when the monitored value changes. 
				Monitoring requests configured for notification when the
				value changes may generate this event.
				
				A Poll Event occurs regularly at the configured polling
				interval.
				
				An Error Event occurs when the value of a monitored resource
				cannot be obtained from the monitor.
				
				The data passed with the event:
				
				  1)  The name of the resource being monitored.
				
				  2)  The request id, a unique identifier for the 
				      monitoring request.  This value should be used when 
				      using resdata to retrieve additional information
				      about the event.
				
				  3)  The operator used by EMS to determine when event 
				      notifications should be sent.  Possible values 
				      include:  poll, change, >, >=, <, <=, = and !=.
				 
				  4)  The resource type, which defines the type of value 
				      being monitored.  Possible values include:  string, 
				      enumerated, integer, and float.
				 
				  5)  The resource value, which is the current value of the 
				      resource being monitored.  It is converted based on 
				      the resource type.
				
				  6)  The threshold type (usually the same as the resource
				      type) defines the type of value configured for the
				      threshold.  Possible values include: string, 
				      integer, and float.
				
				  7)  The threshold value configured for the resource being 
				      monitored.
				
				  8)  The user data flag, which indicates whether or not 
				      user data are available.  User data are comments 
				      provided by the user when the request was configured.
				      User data can be retrieved on the source node by 
				      running:
				        /opt/resmon/bin/resdata -r <resource name> \
				        -R <request id> -u 
				
				  9)  The monitor data flag, which indicates whether or not 
				      the monitor has additional data regarding the event.
				      Additional data provided by the resource monitor
				      can be retrieved on the source node by running:
				        /opt/resmon/bin/resdata -r <resource name> \
				        -R <request id> [-n <notify id>] -m 
					  
				 10)  The notification trigger indicates if the resource 
				      condition is normal or not.  For an EMSProblemEvent 
				      trap, the notification trigger is abnormal.
				
				 11)  The event type indicates the type of notification 
				      being sent.  The different types are:  
				        Poll    - for notification at every interval
				        Change  - for notification when the value changes
				        Normal  - for notification when the threshold
				                  condition for the resource is not true
				        Problem - for notification when the threshold
				                  condition for the resource is true
				        Error   - for notification when the monitor
				                  encountered an error determining
				                  the resource value
				
				 12)  The notify id, a unique identifier for a specific
				      notification event.  This value should be used when 
				      using resdata to retrieve additional information
				      about the event.  Monitor data can be retrieved
				      on the source node by running:
				        /opt/resmon/bin/resdata -r <resource name> \
				        -R <request id> [-n <notify id>] -m "
	
           ::= { hpEMSTraps 2 }
       
       hpEMSMonitorReboot NOTIFICATION-TYPE
           OBJECTS    { 
				hpEMSRestartType,
				hpEMSMonitorTitle,
				hpEMSCommand,
				hpEMSVendor,
				hpEMSVersion,
				hpEMSPID,
				hpEMSMonitorKey         
			}
           STATUS     current
           DESCRIPTION
		       "The Event Monitoring Service (EMS) has generated an event 
				for a monitored resource.
				
				A Monitor Reboot Event occurs when monitors are restarted 
				due to a system reboot.
				
				The list of resources affected by the restart can be 
				retrieved on the source node by running:
				        /opt/resmon/bin/resdata -M <key> 
				
				The data passed with the event:
				
				  1)  The restart event type, which can be restart or 
				      reboot.  For an EMSMonitorReboot trap, the restart
				      type is reboot.
				
				  2)  The title of the monitor that is restarted.
				
				  3)  The command used to restart the monitor.
				 
				  4)  The name of the vendor that provided the monitor.
				 
				  5)  The version of the monitor.
				 
				  6)  The process ID of the restarted monitor process.
				
				  7)  The monitor key, which may be used with the -M option 
				      to the resdata command to return the list of resources 
				      being monitored by the restarted monitor.
				      The list of resources can be retrieved on the source
				      node by running:
				        /opt/resmon/bin/resdata -M <monitor key> "
	
           ::= { hpEMSTraps 3 }
      

       hpEMSMonitorRestart NOTIFICATION-TYPE
           OBJECTS    { 
				hpEMSRestartType,
				hpEMSMonitorTitle,
				hpEMSCommand,
				hpEMSVendor,
				hpEMSVersion,
				hpEMSPID,
				hpEMSMonitorKey         
			}
           STATUS     current
           DESCRIPTION
				"The Event Monitoring Service (EMS) has generated an event 
				for a monitored resource.
				
				A Monitor Restart Event occurs when EMS detects that a 
				required monitor is no longer running, and restarts the 
				monitor.
				
				The list of resources affected by the restart can be 
				retrieved on the source node by running:
				        /opt/resmon/bin/resdata -M <key> 
				
				The data passed with the event:
				
				  1)  The restart event type, which can be restart or 
				      reboot.  For an EMSMonitorRestart trap, the restart
				      type is restart.
				
				  2)  The title of the monitor that is restarted.
				
				  3)  The command used to restart the monitor.
				 
				  4)  The name of the vendor that provided the monitor.
				 
				  5)  The version of the monitor.
				 
				  6)  The process ID of the restarted monitor process.
				
				  7)  The monitor key, which may be used with the -M option 
				      to the resdata command to return the list of resources 
				      being monitored by the restarted monitor.
				      The list of resources can be retrieved on the source
				      node by running:
				        /opt/resmon/bin/resdata -M <monitor key> "
	
           ::= { hpEMSTraps 4 }

       hpEMSNormalSevEvent NOTIFICATION-TYPE
           OBJECTS    { 
           		hpEMSResourceName,
           		hpEMSRequestID,
           		hpEMSOperator,
           		hpEMSResourceType,
           		hpEMSResourceValue,
           		hpEMSThresholdType,
           		hpEMSThresholdValue,
           		hpEMSUserDataFlag,
           		hpEMSMonitorDataFlag,
           		hpEMSNotificationTrigger,
           		hpEMSEventType,
           		hpEMSNotifyID
            }
           STATUS     current
           DESCRIPTION
			"The Event Monitoring Service (EMS) has generated an event 
			for a monitored resource.  
			
			A Problem Event occurs when the threshold condition defined
			for the resource is true.
			
			A Change Event occurs when the monitored value changes. 
			Monitoring requests configured for notification when the
			value changes may generate this event.
			
			A Poll Event occurs regularly at the configured polling
			interval.
			
			An Error Event occurs when the value of a monitored resource
			cannot be obtained from the monitor.
			
			The data passed with the event:
			
			  1)  The name of the resource being monitored.
			
			  2)  The request id, a unique identifier for the 
			      monitoring request.  This value should be used when 
			      using resdata to retrieve additional information
			      about the event.
			
			  3)  The operator used by EMS to determine when event 
			      notifications should be sent.  Possible values 
			      include:  poll, change, >, >=, <, <=, = and !=.
			 
			  4)  The resource type, which defines the type of value 
			      being monitored.  Possible values include:  string, 
			      enumerated, integer, and float.
 
			  5)  The resource value, which is the current value of the 
			      resource being monitored.  It is converted based on 
			      the resource type.
			
			  6)  The threshold type (usually the same as the resource
			      type) defines the type of value configured for the
			      threshold.  Possible values include: string, 
			      integer, and float.
			
			  7)  The threshold value configured for the resource being 
			      monitored.
			
			  8)  The user data flag, which indicates whether or not 
			      user data are available.  User data are comments 
			      provided by the user when the request was configured.
			      User data can be retrieved on the source node by 
			      running:
			        /opt/resmon/bin/resdata -r <resource name> \
			        -R <request id> -u 
			
			  9)  The monitor data flag, which indicates whether or not 
			      the monitor has additional data regarding the event.
			      Additional data provided by the resource monitor
			      can be retrieved on the source node by running:
			        /opt/resmon/bin/resdata -r <resource name> \
			        -R <request id> [-n <notify id>] -m 
				  
			 10)  The notification trigger indicates if the resource 
			      condition is normal or not.  For an EMSProblemEvent 
			      trap, the notification trigger is abnormal.
			
			 11)  The event type indicates the type of notification 
			      being sent.  The different types are:  
			        Poll    - for notification at every interval
			        Change  - for notification when the value changes
			        Normal  - for notification when the threshold
			                  condition for the resource is not true
			        Problem - for notification when the threshold
			                  condition for the resource is true
			        Error   - for notification when the monitor
			                  encountered an error determining
			                  the resource value

			 12)  The notify id, a unique identifier for a specific
			      notification event.  This value should be used when 
			      using resdata to retrieve additional information
			      about the event.  Monitor data can be retrieved
			      on the source node by running:
			        /opt/resmon/bin/resdata -r <resource name> \
			        -R <request id> [-n <notify id>] -m "

           ::= { hpEMSTraps 5 }

       hpEMSWarningEvent NOTIFICATION-TYPE
           OBJECTS    { 
           		hpEMSResourceName,
           		hpEMSRequestID,
           		hpEMSOperator,
           		hpEMSResourceType,
           		hpEMSResourceValue,
           		hpEMSThresholdType,
           		hpEMSThresholdValue,
           		hpEMSUserDataFlag,
           		hpEMSMonitorDataFlag,
           		hpEMSNotificationTrigger,
           		hpEMSEventType,
           		hpEMSNotifyID
            }
           STATUS     current
           DESCRIPTION
			"The Event Monitoring Service (EMS) has generated an event 
			for a monitored resource.  
			
			A Problem Event occurs when the threshold condition defined
			for the resource is true.
			
			A Change Event occurs when the monitored value changes. 
			Monitoring requests configured for notification when the
			value changes may generate this event.
			
			A Poll Event occurs regularly at the configured polling
			interval.
			
			An Error Event occurs when the value of a monitored resource
			cannot be obtained from the monitor.
			
			The data passed with the event:
			
			  1)  The name of the resource being monitored.
			
			  2)  The request id, a unique identifier for the 
			      monitoring request.  This value should be used when 
			      using resdata to retrieve additional information
			      about the event.
			
			  3)  The operator used by EMS to determine when event 
			      notifications should be sent.  Possible values 
			      include:  poll, change, >, >=, <, <=, = and !=.
			 
			  4)  The resource type, which defines the type of value 
			      being monitored.  Possible values include:  string, 
			      enumerated, integer, and float.
			 
			  5)  The resource value, which is the current value of the 
			      resource being monitored.  It is converted based on 
			      the resource type.
			
			  6)  The threshold type (usually the same as the resource
			      type) defines the type of value configured for the
			      threshold.  Possible values include: string, 
			      integer, and float.

			  7)  The threshold value configured for the resource being 
			      monitored.
			
			  8)  The user data flag, which indicates whether or not 
			      user data are available.  User data are comments 
			      provided by the user when the request was configured.
			      User data can be retrieved on the source node by 
			      running:
			        /opt/resmon/bin/resdata -r <resource name> \
			        -R <request id> -u 
			
			  9)  The monitor data flag, which indicates whether or not 
			      the monitor has additional data regarding the event.
			      Additional data provided by the resource monitor
			      can be retrieved on the source node by running:
			        /opt/resmon/bin/resdata -r <resource name> \
			        -R <request id> [-n <notify id>] -m 
				  
			 10)  The notification trigger indicates if the resource 
			      condition is normal or not.  For an EMSProblemEvent 
			      trap, the notification trigger is abnormal.
			
			 11)  The event type indicates the type of notification 
			      being sent.  The different types are:  
			        Poll    - for notification at every interval
			        Change  - for notification when the value changes
			        Normal  - for notification when the threshold
			                  condition for the resource is not true
			        Problem - for notification when the threshold
			                  condition for the resource is true
			        Error   - for notification when the monitor
			                  encountered an error determining
			                  the resource value
			
			 12)  The notify id, a unique identifier for a specific
			      notification event.  This value should be used when 
			      using resdata to retrieve additional information
			      about the event.  Monitor data can be retrieved
			      on the source node by running:
			        /opt/resmon/bin/resdata -r <resource name> \
			        -R <request id> [-n <notify id>] -m "

           ::= { hpEMSTraps 6 }
           
       hpEMSMinorEvent NOTIFICATION-TYPE
           OBJECTS    { 
           		hpEMSResourceName,
           		hpEMSRequestID,
           		hpEMSOperator,
           		hpEMSResourceType,
           		hpEMSResourceValue,
           		hpEMSThresholdType,
           		hpEMSThresholdValue,
           		hpEMSUserDataFlag,
           		hpEMSMonitorDataFlag,
           		hpEMSNotificationTrigger,
           		hpEMSEventType,
           		hpEMSNotifyID
            }
           STATUS     current
           DESCRIPTION
			"The Event Monitoring Service (EMS) has generated an event 
			for a monitored resource.  
			
			A Problem Event occurs when the threshold condition defined
			for the resource is true.
			
			A Change Event occurs when the monitored value changes. 
			Monitoring requests configured for notification when the
			value changes may generate this event.
			
			A Poll Event occurs regularly at the configured polling
			interval.
			
			An Error Event occurs when the value of a monitored resource
			cannot be obtained from the monitor.
			
			The data passed with the event:
			
			  1)  The name of the resource being monitored.
			
			  2)  The request id, a unique identifier for the 
			      monitoring request.  This value should be used when 
			      using resdata to retrieve additional information
			      about the event.
			
			  3)  The operator used by EMS to determine when event 
			      notifications should be sent.  Possible values 
			      include:  poll, change, >, >=, <, <=, = and !=.
			 
			  4)  The resource type, which defines the type of value 
			      being monitored.  Possible values include:  string, 
			      enumerated, integer, and float.
			 
			  5)  The resource value, which is the current value of the 
			      resource being monitored.  It is converted based on 
			      the resource type.
			
			  6)  The threshold type (usually the same as the resource
			      type) defines the type of value configured for the
			      threshold.  Possible values include: string, 
			      integer, and float.

			  7)  The threshold value configured for the resource being 
			      monitored.
			
			  8)  The user data flag, which indicates whether or not 
			      user data are available.  User data are comments 
			      provided by the user when the request was configured.
			      User data can be retrieved on the source node by 
			      running:
			        /opt/resmon/bin/resdata -r <resource name> \
			        -R <request id> -u 
			
			  9)  The monitor data flag, which indicates whether or not 
			      the monitor has additional data regarding the event.
			      Additional data provided by the resource monitor
			      can be retrieved on the source node by running:
			        /opt/resmon/bin/resdata -r <resource name> \
			        -R <request id> [-n <notify id>] -m 
				  
			 10)  The notification trigger indicates if the resource 
			      condition is normal or not.  For an EMSProblemEvent 
			      trap, the notification trigger is abnormal.
			
			 11)  The event type indicates the type of notification 
			      being sent.  The different types are:  
			        Poll    - for notification at every interval
			        Change  - for notification when the value changes
			        Normal  - for notification when the threshold
			                  condition for the resource is not true
			        Problem - for notification when the threshold
			                  condition for the resource is true
			        Error   - for notification when the monitor
			                  encountered an error determining
			                  the resource value
			
			 12)  The notify id, a unique identifier for a specific
			      notification event.  This value should be used when 
			      using resdata to retrieve additional information
			      about the event.  Monitor data can be retrieved
			      on the source node by running:
			        /opt/resmon/bin/resdata -r <resource name> \
			        -R <request id> [-n <notify id>] -m "
	
           ::= { hpEMSTraps 7 }
           
       hpEMSMajorEvent NOTIFICATION-TYPE
           OBJECTS    { 
           		hpEMSResourceName,
           		hpEMSRequestID,
           		hpEMSOperator,
           		hpEMSResourceType,
           		hpEMSResourceValue,
           		hpEMSThresholdType,
           		hpEMSThresholdValue,
           		hpEMSUserDataFlag,
           		hpEMSMonitorDataFlag,
           		hpEMSNotificationTrigger,
           		hpEMSEventType,
           		hpEMSNotifyID
            }
           STATUS     current
           DESCRIPTION
			"The Event Monitoring Service (EMS) has generated an event 
			for a monitored resource.  
			
			A Problem Event occurs when the threshold condition defined
			for the resource is true.
			
			A Change Event occurs when the monitored value changes. 
			Monitoring requests configured for notification when the
			value changes may generate this event.
			
			A Poll Event occurs regularly at the configured polling
			interval.
			
			An Error Event occurs when the value of a monitored resource
			cannot be obtained from the monitor.
			
			The data passed with the event:
			
			  1)  The name of the resource being monitored.
			
			  2)  The request id, a unique identifier for the 
			      monitoring request.  This value should be used when 
			      using resdata to retrieve additional information
			      about the event.
			
			  3)  The operator used by EMS to determine when event 
			      notifications should be sent.  Possible values 
			      include:  poll, change, >, >=, <, <=, = and !=.
			 
			  4)  The resource type, which defines the type of value 
			      being monitored.  Possible values include:  string, 
			      enumerated, integer, and float.
			 
			  5)  The resource value, which is the current value of the 
			      resource being monitored.  It is converted based on 
			      the resource type.
			
			  6)  The threshold type (usually the same as the resource
			      type) defines the type of value configured for the
			      threshold.  Possible values include: string, 
			      integer, and float.

			  7)  The threshold value configured for the resource being 
			      monitored.
			
			  8)  The user data flag, which indicates whether or not 
			      user data are available.  User data are comments 
			      provided by the user when the request was configured.
			      User data can be retrieved on the source node by 
			      running:
			        /opt/resmon/bin/resdata -r <resource name> \
			        -R <request id> -u 
			
			  9)  The monitor data flag, which indicates whether or not 
			      the monitor has additional data regarding the event.
			      Additional data provided by the resource monitor
			      can be retrieved on the source node by running:
			        /opt/resmon/bin/resdata -r <resource name> \
			        -R <request id> [-n <notify id>] -m 
				  
			 10)  The notification trigger indicates if the resource 
			      condition is normal or not.  For an EMSProblemEvent 
			      trap, the notification trigger is abnormal.
			
			 11)  The event type indicates the type of notification 
			      being sent.  The different types are:  
			        Poll    - for notification at every interval
			        Change  - for notification when the value changes
			        Normal  - for notification when the threshold
			                  condition for the resource is not true
			        Problem - for notification when the threshold
			                  condition for the resource is true
			        Error   - for notification when the monitor
			                  encountered an error determining
			                  the resource value
			
			 12)  The notify id, a unique identifier for a specific
			      notification event.  This value should be used when 
			      using resdata to retrieve additional information
			      about the event.  Monitor data can be retrieved
			      on the source node by running:
			        /opt/resmon/bin/resdata -r <resource name> \
			        -R <request id> [-n <notify id>] -m "
	
           ::= { hpEMSTraps 8 }
           
       hpEMSCriticalEvent NOTIFICATION-TYPE
           OBJECTS    { 
           		hpEMSResourceName,
           		hpEMSRequestID,
           		hpEMSOperator,
           		hpEMSResourceType,
           		hpEMSResourceValue,
           		hpEMSThresholdType,
           		hpEMSThresholdValue,
           		hpEMSUserDataFlag,
           		hpEMSMonitorDataFlag,
           		hpEMSNotificationTrigger,
           		hpEMSEventType,
           		hpEMSNotifyID
            }
           STATUS     current
           DESCRIPTION
			"The Event Monitoring Service (EMS) has generated an event 
			for a monitored resource.  
			
			A Problem Event occurs when the threshold condition defined
			for the resource is true.
			
			A Change Event occurs when the monitored value changes. 
			Monitoring requests configured for notification when the
			value changes may generate this event.
			
			A Poll Event occurs regularly at the configured polling
			interval.
			
			An Error Event occurs when the value of a monitored resource
			cannot be obtained from the monitor.
			
			The data passed with the event:
			
			  1)  The name of the resource being monitored.
			
			  2)  The request id, a unique identifier for the 
			      monitoring request.  This value should be used when 
			      using resdata to retrieve additional information
			      about the event.
			
			  3)  The operator used by EMS to determine when event 
			      notifications should be sent.  Possible values 
			      include:  poll, change, >, >=, <, <=, = and !=.
			 
			  4)  The resource type, which defines the type of value 
			      being monitored.  Possible values include:  string, 
			      enumerated, integer, and float.
			 
			  5)  The resource value, which is the current value of the 
			      resource being monitored.  It is converted based on 
			      the resource type.
			
			  6)  The threshold type (usually the same as the resource
			      type) defines the type of value configured for the
			      threshold.  Possible values include: string, 
			      integer, and float.

			  7)  The threshold value configured for the resource being 
			      monitored.
			
			  8)  The user data flag, which indicates whether or not 
			      user data are available.  User data are comments 
			      provided by the user when the request was configured.
			      User data can be retrieved on the source node by 
			      running:
			        /opt/resmon/bin/resdata -r <resource name> \
			        -R <request id> -u 
			
			  9)  The monitor data flag, which indicates whether or not 
			      the monitor has additional data regarding the event.
			      Additional data provided by the resource monitor
			      can be retrieved on the source node by running:
			        /opt/resmon/bin/resdata -r <resource name> \
			        -R <request id> [-n <notify id>] -m 
				  
			 10)  The notification trigger indicates if the resource 
			      condition is normal or not.  For an EMSProblemEvent 
			      trap, the notification trigger is abnormal.
			
			 11)  The event type indicates the type of notification 
			      being sent.  The different types are:  
			        Poll    - for notification at every interval
			        Change  - for notification when the value changes
			        Normal  - for notification when the threshold
			                  condition for the resource is not true
			        Problem - for notification when the threshold
			                  condition for the resource is true
			        Error   - for notification when the monitor
			                  encountered an error determining
			                  the resource value
			
			 12)  The notify id, a unique identifier for a specific
			      notification event.  This value should be used when 
			      using resdata to retrieve additional information
			      about the event.  Monitor data can be retrieved
			      on the source node by running:
			        /opt/resmon/bin/resdata -r <resource name> \
			        -R <request id> [-n <notify id>] -m "
	
           ::= { hpEMSTraps 9 }

END
