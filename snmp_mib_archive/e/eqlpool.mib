-- Mib files packaged on  Thu Feb 25 14:37:59 EST 2010 for Storage Array Firmware V4.3.5 (R115269)

--FROM SNMP-FRAMEWORK-MIB; 
-- RFC 2571  
  
--  These are from draft-ietf-ops-rfc2851-update-00.txt  
--  You will have to work out the details with your own  
--  compiler being because they are so new. 

     
--equalLogic   OBJECT IDENTIFIER ::= { enterprises 12740 } 
-- assigned by IANA to EqualLogic.  
EQLSTORAGEPOOL-MIB DEFINITIONS  ::= BEGIN   
IMPORTS  
    MODULE-IDENTITY, OBJECT-TYPE, Unsigned32, Counter64, Integer32,TimeTicks,  enterprises, IpAddress 
            FROM SNMPv2-SMI  
	 DateAndTime, RowPointer       
				FROM SNMPv2-TC
    TruthValue, RowStatus, DisplayString    
            FROM SNMPv2-TC
    equalLogic
            FROM EQUALLOGIC-SMI
    eqlGroupId, eqlStorageGroupAdminAccountIndex, UTFString
            FROM EQLGROUP-MIB;

eqlStoragePoolModule MODULE-IDENTITY      
	LAST-UPDATED "201002251937Z"
    ORGANIZATION  "EqualLogic Inc."
    CONTACT-INFO      
        "Contact: Customer Support
         Postal:  EqualLogic Inc
                  9 Townsend st., Nashua, NH 03063           
         Tel:     +1 603-579-9762             
         E-mail:  support@equallogic.com
         WEB:     www.equallogic.com"

    DESCRIPTION          
        "Equallogic Inc. Storage Array volume information 

        Copyright (c) 2002-2008 by Dell, Inc. 
        
        All rights reserved.  This software may not be copied, disclosed, 
        transferred, or used except in accordance with a license granted 
        by Dell, Inc.  This software embodies proprietary information 
        and trade secrets of Dell, Inc. 
        "

    -- Revision history, in reverse chronological order
    REVISION    "200503170000Z"         -- 05-Mar-17
    DESCRIPTION "Initial revision"    
    ::= { enterprises equalLogic(12740) 16 }     


eqlStoragePoolObjects OBJECT IDENTIFIER ::=  { eqlStoragePoolModule 1 }   
eqlStoragePoolNotifications OBJECT IDENTIFIER ::= { eqlStoragePoolModule 2 }   
eqlStoragePoolConformance OBJECT IDENTIFIER ::=  { eqlStoragePoolModule 3 } 
     
--***********************************************************************************
-- Textual conventions

SiteIndex ::= TEXTUAL-CONVENTION
    DISPLAY-HINT "d"
    STATUS       current
    DESCRIPTION
            "This textual convention defines a greater
            than zero value used to identify an external group
            operating autonomously from the local group."
    SYNTAX       Integer32 (1..2147483647)

SiteIndexOrZero ::= TEXTUAL-CONVENTION
    DISPLAY-HINT "d"
    STATUS       current
    DESCRIPTION
            "This textual convention is an extension of the
            SiteIndex convention.  The latter defines a greater
            than zero value used to identify an external group
            operating autonomously from the local group. This extension permits the
            additional value of zero.  the value zero is object-specific
            and must therefore be defined as part of the description of
            any object which uses this syntax.  Examples of the usage of
            zero might include situations where the site is unknown or not 
            relevant"
    SYNTAX       Integer32 (0..2147483647)


--***********************************************************************************


eqlStoragePoolTable OBJECT-TYPE      
    SYNTAX          SEQUENCE OF EqlStoragePoolEntry      
    MAX-ACCESS      not-accessible      
    STATUS          current      
    DESCRIPTION     "EqualLogic-Persistent Storage Pool Table.
                     This table contains a list of storage pools in a group and their attributes." 
    ::=    { eqlStoragePoolObjects 1 }     


eqlStoragePoolEntry OBJECT-TYPE      
    SYNTAX          EqlStoragePoolEntry      
    MAX-ACCESS      not-accessible      
    STATUS          current      
    DESCRIPTION     "An entry (row) containing storage pool info."
    INDEX           { eqlGroupId, eqlStoragePoolIndex }
    ::=   { eqlStoragePoolTable 1}     

EqlStoragePoolEntry ::= 
    SEQUENCE { 
        eqlStoragePoolIndex               Unsigned32,
        eqlStoragePoolRowStatus           RowStatus,
        eqlStoragePoolName                OCTET STRING,
        eqlStoragePoolDefaultFlag         TruthValue,
        eqlStoragePoolRAIDConfigWaitFlag  TruthValue,
        eqlStoragePoolShouldEvalMask      Unsigned32,
        eqlStoragePoolLastBalance         Unsigned32,
        eqlStoragePoolDescription         DisplayString,
	eqlStoragePoolLeadMemberId        Unsigned32,
        eqlStoragePoolUUID                OCTET STRING,
	eqlStoragePoolExecMergeTo         Unsigned32
    }

eqlStoragePoolIndex OBJECT-TYPE      
    SYNTAX          Unsigned32
    MAX-ACCESS      not-accessible
    STATUS          current
    DESCRIPTION     "This field specifies a unique index for identifying a storage pool."
    ::= { eqlStoragePoolEntry 1 }

eqlStoragePoolRowStatus OBJECT-TYPE      
    SYNTAX          RowStatus    
    MAX-ACCESS      read-create      
    STATUS          current      
    DESCRIPTION     "This field is used indicate the status of this entry."  
    ::= { eqlStoragePoolEntry 2 }  

eqlStoragePoolName OBJECT-TYPE      
    SYNTAX          OCTET STRING (SIZE (1..64))    
    MAX-ACCESS      read-create
    STATUS          current      
    DESCRIPTION     "EQL-SECONDARY-KEY
                     This field specifies a user friendly name for a storage pool.
                     The name must be unique within a group.
                     The name must not contain spaces or special characters.
                     The name can be up to 64 characters in length."
    DEFVAL           { "default" }
    ::=  {  eqlStoragePoolEntry 3 }  

eqlStoragePoolDefaultFlag OBJECT-TYPE      
    SYNTAX          TruthValue
    MAX-ACCESS      read-create
    STATUS          current      
    DESCRIPTION     "This field specifies if this storage pool is the default pool.  TRUE == default pool."
    DEFVAL          { true }
    ::=  {  eqlStoragePoolEntry 4 } 

eqlStoragePoolRAIDConfigWaitFlag OBJECT-TYPE      
    SYNTAX          TruthValue
    MAX-ACCESS      read-write
    STATUS          current      
    DESCRIPTION     "This field specifies if the system should wait for a 
                     configured RAID-set before allowing volumes to be
                     created."
    DEFVAL          { false }
    ::=  {  eqlStoragePoolEntry 5 } 

eqlStoragePoolShouldEvalMask OBJECT-TYPE      
    SYNTAX          Unsigned32
    MAX-ACCESS      read-only
    STATUS          current      
    DESCRIPTION     "This field specifies one or more reasons (32-bit mask) the pool should be evaluated."
    ::=  {  eqlStoragePoolEntry 6 } 
          
eqlStoragePoolLastBalance OBJECT-TYPE      
    SYNTAX          Unsigned32
    MAX-ACCESS      read-only 
    STATUS          current      
    DESCRIPTION     "This field specifies a timestamp of the last time the pool was balanced."
    ::=   { eqlStoragePoolEntry 7 }

eqlStoragePoolDescription OBJECT-TYPE      
    SYNTAX          DisplayString (SIZE(0..128))
    MAX-ACCESS      read-write
    STATUS          current
    DESCRIPTION     "This field contains a description of the storage pool."
    ::=  {  eqlStoragePoolEntry 8 }

eqlStoragePoolLeadMemberId OBJECT-TYPE
    SYNTAX          Unsigned32
    MAX-ACCESS      read-write
    STATUS          current
    DESCRIPTION     "This field specifies the member id of the pool lead."
    ::=  {  eqlStoragePoolEntry 9 }

eqlStoragePoolUUID OBJECT-TYPE      
    SYNTAX          OCTET STRING (SIZE (16))     
    MAX-ACCESS      read-only      
    STATUS          current      
    DESCRIPTION     "EQL-SECONDARY-KEY 
                     This field is for internal use only."  
    ::=  { eqlStoragePoolEntry 10 }

eqlStoragePoolExecMergeTo OBJECT-TYPE      
    SYNTAX          Unsigned32
    MAX-ACCESS      read-write
    STATUS          current
    DESCRIPTION     "This field, when non-zero, specifies the index of the storage pool that this pool is being merged into."
    ::= { eqlStoragePoolEntry 11 }

---*************************************************************  

eqlStoragePoolStatsTable OBJECT-TYPE      
    SYNTAX          SEQUENCE OF EqlStoragePoolStatsEntry      
    MAX-ACCESS      not-accessible      
    STATUS          current      
    DESCRIPTION     "EqualLogic-Dynamic Storage Pool Statistics Table.
                     This table contains a list of pools in a group and their statistics." 
    ::=    { eqlStoragePoolObjects 2 }     


eqlStoragePoolStatsEntry OBJECT-TYPE      
    SYNTAX          EqlStoragePoolStatsEntry      
    MAX-ACCESS      not-accessible      
    STATUS          current      
    DESCRIPTION     "An entry (row) containing storage pool stats."
    AUGMENTS        { eqlStoragePoolEntry }
    ::=   { eqlStoragePoolStatsTable 1}     

EqlStoragePoolStatsEntry ::= 
    SEQUENCE { 
        eqlStoragePoolStatsSpace                Counter64,
        eqlStoragePoolStatsSpaceUsed            Counter64,      
        eqlStoragePoolStatsFreeSpace            Counter64,
        eqlStoragePoolStatsReplicationSpace     Counter64,      
        eqlStoragePoolStatsReplicationSpaceUsed Counter64,      
        eqlStoragePoolStatsReplicationFreeSpace Counter64,      
        eqlStoragePoolStatsMemberNumOnline      Integer32,      
        eqlStoragePoolStatsMemberCount          Integer32,
        eqlStoragePoolStatsSnapshotReserved     Counter64,
        eqlStoragePoolStatsSnapshotUsed         Counter64,
        eqlStoragePoolStatsSnapshotNumInUse     Integer32,
        eqlStoragePoolStatsSnapshotNumOnline    Integer32,
        eqlStoragePoolStatsSnapshotCount        Integer32,
        eqlStoragePoolStatsVolumeNumInUse       Integer32,
        eqlStoragePoolStatsVolumeNumOnline      Integer32,
        eqlStoragePoolStatsVolumeCount          Integer32,
        eqlStoragePoolStatsDelegatedSpace       Counter64,
        eqlStoragePoolStatsDelegatedSpaceUsed   Counter64,
        eqlStoragePoolStatsMembersInUse         Integer32,
        eqlStoragePoolStatsVolumeSubscribed     Counter64,
        eqlStoragePoolStatsVolumeSpaceAllocated Counter64,
        eqlStoragePoolStatsFailbackSpace        Counter64,
        eqlStoragePoolStatsThinProvFreeSpace    Counter64,
        eqlStoragePoolStatsConnectionCount      Integer32,
        eqlStoragePoolStatsSnapshotResvFreeSpace Counter64
    }

eqlStoragePoolStatsSpace OBJECT-TYPE      
    SYNTAX          Counter64
    MAX-ACCESS      read-only      
    STATUS          current      
    DESCRIPTION     "This field specifies how many MB of space comprises this storage pool.
                     This is a dynamic value, it is not Administrator setable."
    ::=  { eqlStoragePoolStatsEntry 1 }

eqlStoragePoolStatsSpaceUsed OBJECT-TYPE      
    SYNTAX          Counter64     
    MAX-ACCESS      read-only      
    STATUS          current      
    DESCRIPTION     "This field specifies the space used by volumes in this pool. The value is represented in MB.
                     This is a dynamic value, it is not Administrator setable."
    ::=  { eqlStoragePoolStatsEntry 2 }

eqlStoragePoolStatsFreeSpace OBJECT-TYPE      
    SYNTAX          Counter64     
    MAX-ACCESS      read-only      
    STATUS          current      
    DESCRIPTION     "This field specifies how many MB of space is available in this storage pool.
                     This is a dynamic value, it is not Administrator setable."
    ::=  { eqlStoragePoolStatsEntry 3 }

eqlStoragePoolStatsReplicationSpace OBJECT-TYPE      
    SYNTAX          Counter64     
    MAX-ACCESS      read-only      
    STATUS          current      
    DESCRIPTION     "This field specifies how many MB of space is allocated for replication in this storage pool.
                     This is a dynamic value, it is not Administrator setable."
    ::=  { eqlStoragePoolStatsEntry 4 }

eqlStoragePoolStatsReplicationSpaceUsed OBJECT-TYPE      
    SYNTAX          Counter64     
    MAX-ACCESS      read-only      
    STATUS          current      
    DESCRIPTION     "This field specifies how many MB of space is currently utilized by replication in this storage pool.
                     This is a dynamic value, it is not Administrator setable."
    ::=  { eqlStoragePoolStatsEntry 5 }

eqlStoragePoolStatsReplicationFreeSpace OBJECT-TYPE      
    SYNTAX          Counter64     
    MAX-ACCESS      read-only      
    STATUS          current      
    DESCRIPTION     "This field specifies how many MB of space is available to replication in this storage pool.
                     This is a dynamic value, it is not Administrator setable."
    ::=  { eqlStoragePoolStatsEntry 6 }

eqlStoragePoolStatsMemberNumOnline OBJECT-TYPE      
    SYNTAX          Integer32     
    MAX-ACCESS      read-only      
    STATUS          current      
    DESCRIPTION     "This field idicates how many members are online in this storage pool.
                     This is a dynamic value, it is not Administrator setable."
    ::=  { eqlStoragePoolStatsEntry 7 }

eqlStoragePoolStatsMemberCount OBJECT-TYPE      
    SYNTAX          Integer32     
    MAX-ACCESS      read-only      
    STATUS          current      
    DESCRIPTION     "This field indicates how many total members are in this storage pool.
                     This is a dynamic value, it is not Administrator setable."
    ::=  { eqlStoragePoolStatsEntry 8 }

eqlStoragePoolStatsSnapshotReserved OBJECT-TYPE      
    SYNTAX          Counter64 
    MAX-ACCESS      read-only      
    STATUS          current      
    DESCRIPTION     "This field specifies how many MB of snapshot space is reserved in this storage pool.
                     This is a dynamic value, it is not Administrator setable."
    ::=  { eqlStoragePoolStatsEntry 9 }

eqlStoragePoolStatsSnapshotUsed OBJECT-TYPE      
    SYNTAX          Counter64 
    MAX-ACCESS      read-only      
    STATUS          current      
    DESCRIPTION     "This field specifies how many MB of snapshot space is currently utilized in this storage pool.
                     This is a dynamic value, it is not Administrator setable."
    ::=  { eqlStoragePoolStatsEntry 10 }

eqlStoragePoolStatsSnapshotNumInUse OBJECT-TYPE      
    SYNTAX          Integer32     
    MAX-ACCESS      read-only      
    STATUS          current      
    DESCRIPTION     "This field idicates how many snapshots are currently in use in this storage pool.
                     This is a dynamic value, it is not Administrator setable."
    ::=  { eqlStoragePoolStatsEntry 11 }

eqlStoragePoolStatsSnapshotNumOnline OBJECT-TYPE      
    SYNTAX          Integer32     
    MAX-ACCESS      read-only      
    STATUS          current      
    DESCRIPTION     "This field idicates how many snapshots are online in this storage pool.
                     This is a dynamic value, it is not Administrator setable."
    ::=  { eqlStoragePoolStatsEntry 12 }

eqlStoragePoolStatsSnapshotCount OBJECT-TYPE      
    SYNTAX          Integer32     
    MAX-ACCESS      read-only      
    STATUS          current      
    DESCRIPTION     "This field indicates how many total snapshots are in this storage pool.
                     This is a dynamic value, it is not Administrator setable."
    ::=  { eqlStoragePoolStatsEntry 13 }

eqlStoragePoolStatsVolumeNumInUse OBJECT-TYPE      
    SYNTAX          Integer32     
    MAX-ACCESS      read-only      
    STATUS          current      
    DESCRIPTION     "This field idicates how many volumes are currently in use in this storage pool.
                     This is a dynamic value, it is not Administrator setable."
    ::=  { eqlStoragePoolStatsEntry 14 }

eqlStoragePoolStatsVolumeNumOnline OBJECT-TYPE      
    SYNTAX          Integer32     
    MAX-ACCESS      read-only      
    STATUS          current      
    DESCRIPTION     "This field idicates how many volumes are online in this storage pool.
                     This is a dynamic value, it is not Administrator setable."
    ::=  { eqlStoragePoolStatsEntry 15 }

eqlStoragePoolStatsVolumeCount OBJECT-TYPE      
    SYNTAX          Integer32     
    MAX-ACCESS      read-only      
    STATUS          current      
    DESCRIPTION     "This field indicates how many total volumes are in this storage pool.
                     This is a dynamic value, it is not Administrator setable."
    ::=  { eqlStoragePoolStatsEntry 16 }

eqlStoragePoolStatsDelegatedSpace OBJECT-TYPE      
    SYNTAX          Counter64     
    MAX-ACCESS      read-only      
    STATUS          current      
    DESCRIPTION     "This field indicates the total delegated space for partners in this pool.
                     This is a dynamic value, it is not Administrator setable."
    ::=  { eqlStoragePoolStatsEntry 17 }


eqlStoragePoolStatsDelegatedSpaceUsed OBJECT-TYPE      
    SYNTAX          Counter64     
    MAX-ACCESS      read-only      
    STATUS          current      
    DESCRIPTION     "This field indicates the total delegated space used by partners in this pool.
                     This is a dynamic value, it is not Administrator setable."
    ::=  { eqlStoragePoolStatsEntry 18 }

eqlStoragePoolStatsMembersInUse OBJECT-TYPE      
    SYNTAX          Integer32     
    MAX-ACCESS      read-only      
    STATUS          current      
    DESCRIPTION     "This field indicates the total members of online+offline members in this group.
                     This is a dynamic value, it is not Administrator setable."
    ::=  { eqlStoragePoolStatsEntry 19 }

eqlStoragePoolStatsVolumeSubscribed OBJECT-TYPE      
    SYNTAX          Counter64     
    UNITS           "MB"
    MAX-ACCESS      read-only      
    STATUS          current      
    DESCRIPTION     "This field specifies the total subscribed space for all volumes in this pool. For a thin provisioned volume, 
                     subscribed space is the advertised space. For a regular volume, subscribed space is the volume size.
                     The value of this field will be equal to sum of eqliscsiVolumeSize field for all volumes in this pool."
    ::=  { eqlStoragePoolStatsEntry 20 }

eqlStoragePoolStatsVolumeSpaceAllocated OBJECT-TYPE      
    SYNTAX          Counter64     
    UNITS           "MB"
    MAX-ACCESS      read-only      
    STATUS          current      
    DESCRIPTION     "The value of this object represents the sum of actual materialized pages for all volumes in the pool."
    ::=  { eqlStoragePoolStatsEntry 21 }

eqlStoragePoolStatsFailbackSpace OBJECT-TYPE      
    SYNTAX          Counter64     
    UNITS           "MB"
    MAX-ACCESS      read-only      
    STATUS          current      
    DESCRIPTION     "This field represents the amount of space consumed by fail-back replicasets in this pool."
    ::=  { eqlStoragePoolStatsEntry 22 }

eqlStoragePoolStatsThinProvFreeSpace OBJECT-TYPE      
    SYNTAX          Counter64     
    UNITS           "MB"
    MAX-ACCESS      read-only      
    STATUS          current      
    DESCRIPTION     "This field represents the amount of space available for Thin Provisioned Volumes in this pool."
    ::=  { eqlStoragePoolStatsEntry 23 }

eqlStoragePoolStatsConnectionCount OBJECT-TYPE      
    SYNTAX          Integer32   
    MAX-ACCESS      read-only      
    STATUS          current      
    DESCRIPTION     "This field gives the number of iSCSI connections that are currently connected to volumes in this pool."
    ::=  { eqlStoragePoolStatsEntry 24 }

eqlStoragePoolStatsSnapshotResvFreeSpace OBJECT-TYPE      
    SYNTAX          Counter64     
    UNITS           "MB"
    MAX-ACCESS      read-only      
    STATUS          current      
    DESCRIPTION     "This field specifies how many MB of space is available to Snapshots in this storage pool.
                     This is a dynamic value, it is not Administrator setable."
    ::=  { eqlStoragePoolStatsEntry 25 }

---*************************************************************  

eqlStoragePoolAdminAccountTable OBJECT-TYPE      
    SYNTAX          SEQUENCE OF EqlStoragePoolAdminAccountEntry      
    MAX-ACCESS      not-accessible      
    STATUS          current      
    DESCRIPTION     "EqualLogic-Persistent Admin Account Storage Pool Table.
                     This table contains a list of privilege matchings of administrative
                     accounts and the pools those administrators have access to."
    ::=    { eqlStoragePoolObjects 3 }     

eqlStoragePoolAdminAccountEntry OBJECT-TYPE      
    SYNTAX          EqlStoragePoolAdminAccountEntry      
    MAX-ACCESS      not-accessible      
    STATUS          current      
    DESCRIPTION     "An entry (row) containing mapping of administrative accounts and their
                     pool access."
    INDEX           { eqlGroupId, eqlStoragePoolIndex, eqlStorageGroupAdminAccountIndex }
    ::=   { eqlStoragePoolAdminAccountTable 1}

EqlStoragePoolAdminAccountEntry ::= 
    SEQUENCE { 
        eqlStoragePoolAdminAccountRowStatus      RowStatus
    }

eqlStoragePoolAdminAccountRowStatus OBJECT-TYPE      
    SYNTAX          RowStatus    
    MAX-ACCESS      read-create      
    STATUS          current      
    DESCRIPTION     "This field is used indicate the status of this entry."  
    ::= { eqlStoragePoolAdminAccountEntry 1 }  

--******************************************************************

eqlAdminAccountStoragePoolTable OBJECT-TYPE
    SYNTAX          SEQUENCE OF EqlAdminAccountStoragePoolEntry
    MAX-ACCESS      not-accessible
    STATUS          current
    DESCRIPTION     "EqualLogic-Dynamic table indicating the access an administrator
                     has to a storage pool."
    ::= { eqlStoragePoolObjects 4 }

eqlAdminAccountStoragePoolEntry OBJECT-TYPE
    SYNTAX          EqlAdminAccountStoragePoolEntry
    MAX-ACCESS      not-accessible
    STATUS          current
    DESCRIPTION     "An entry (row) containing the access privilege."
    INDEX           {  eqlGroupId, eqlStorageGroupAdminAccountIndex, eqlStoragePoolIndex }
    ::=   { eqlAdminAccountStoragePoolTable 1 }

EqlAdminAccountStoragePoolEntry ::=
    SEQUENCE {
        eqlAdminAccountStoragePoolAccess         INTEGER
    }

eqlAdminAccountStoragePoolAccess OBJECT-TYPE
    SYNTAX          INTEGER {
                         read-only (1),
                         read-write (2)
                    }
    MAX-ACCESS      read-only
    STATUS          current
    DESCRIPTION     "The administrative permission to a storage pool."
    ::=   { eqlAdminAccountStoragePoolEntry 1 }

--******************************************************************
    
eqlStoragePoolOpsTable OBJECT-TYPE
    SYNTAX  SEQUENCE OF EqlStoragePoolOpsEntry
    MAX-ACCESS    not-accessible
    STATUS        current
    DESCRIPTION   "EqualLogic-Persistent Storage Pool Operations Table."
    ::=  {  eqlStoragePoolObjects 5 }
    
eqlStoragePoolOpsEntry OBJECT-TYPE
    SYNTAX        EqlStoragePoolOpsEntry
    MAX-ACCESS    not-accessible  
    STATUS        current  
    DESCRIPTION   "An entry (row) containing storage pool configuration"
    INDEX  { eqlGroupId, eqlStoragePoolIndex, eqlStoragePoolOpsIndex } 
    ::=    { eqlStoragePoolOpsTable 1 }
    
EqlStoragePoolOpsEntry ::=
    SEQUENCE {
        eqlStoragePoolOpsIndex                       Unsigned32,
        eqlStoragePoolOpsRowStatus                   RowStatus,
        eqlStoragePoolOpsOperation                   INTEGER,
        eqlStoragePoolOpsStoragePoolDestinationIndex Unsigned32
    }                
    
eqlStoragePoolOpsIndex OBJECT-TYPE
    SYNTAX          Unsigned32
    MAX-ACCESS      not-accessible  
    STATUS          current
    DESCRIPTION     "This field unique identifies an operation withing a storage pool."
    ::=  {  eqlStoragePoolOpsEntry 1 }
    
eqlStoragePoolOpsRowStatus OBJECT-TYPE
    SYNTAX          RowStatus
    MAX-ACCESS      read-create
    STATUS          current
    DESCRIPTION     "This field is used indicate the status of this entry."
    ::= { eqlStoragePoolOpsEntry 2 }
    
eqlStoragePoolOpsOperation OBJECT-TYPE
    SYNTAX INTEGER {
        none(0),
        delete(1)   
    }
    MAX-ACCESS     read-write
    STATUS         current
    DESCRIPTION    "The current operation for this drive group
                        0 - no operation
                        1 - delete/merge"
    ::=  {  eqlStoragePoolOpsEntry 3 }

eqlStoragePoolOpsStoragePoolDestinationIndex OBJECT-TYPE
    SYNTAX          Unsigned32
    MAX-ACCESS      read-write
    STATUS          current
    DESCRIPTION     "This field unique identifies the destination Storage Pool."
    DEFVAL          { 1 }
    ::=  {  eqlStoragePoolOpsEntry 4 }

END
