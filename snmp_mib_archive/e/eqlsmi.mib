-- Mib files packaged on  Thu Feb 25 14:37:59 EST 2010 for Storage Array Firmware V4.3.5 (R115269)

EQUALLOGIC-SMI DEFINITIONS  ::= BEGIN
IMPORTS
    DisplayString , TruthValue, RowStatus, RowPointer, TEXTUAL-CONVENTION
            FROM SNMPv2-TC
    MODULE-IDENTITY, OBJECT-TYPE, Integer32, Unsigned32, enterprises, IpAddress, TimeTicks, Counter32
            FROM SNMPv2-SMI;

equalLogic MODULE-IDENTITY
	LAST-UPDATED "201002251937Z"
    ORGANIZATION  "EqualLogic Inc."
    CONTACT-INFO
        "Contact: Customer Support
         Postal:  EqualLogic Inc
                  110 Spit Brook Rd, ZKO2., Nashua, NH 03062
         Tel:     +1 603-579-9762
         E-mail:  support@equallogic.com
         WEB:     www.equallogic.com"

    DESCRIPTION
        "Equallogic Inc. group information

        Copyright (c) 2002-2008 by Dell, Inc. 
        
        All rights reserved.  This software may not be copied, disclosed, 
        transferred, or used except in accordance with a license granted 
        by Dell, Inc.  This software embodies proprietary information 
        and trade secrets of Dell, Inc. 
        "


    -- Revision history, in reverse chronological order
    REVISION   "200805202109Z"      -- 20-May-08
    DESCRIPTION "Initial revision"
    ::= { enterprises 12740 }


END
