--
-- WS-SW-MAC-NAME.my
-- MIB generated by MG-SOFT Visual MIB Builder Version 6.0  Build 88
-- Tuesday, June 03, 2008 at 13:37:34
--

	WS-SW-MAC-NAME DEFINITIONS ::= BEGIN
 
		IMPORTS
			OBJECT-GROUP, MODULE-COMPLIANCE			
				FROM SNMPv2-CONF			
			OBJECT-TYPE, MODULE-IDENTITY			
				FROM SNMPv2-SMI			
			DisplayString, PhysAddress			
				FROM SNMPv2-TC			
			wsSwMacName			
				FROM WS-SW-SMI			
			AbbrevRowStatus			
				FROM WS-TYPE-MIB;
	
	
		-- 1.3.6.1.4.1.388.14.2.10.1
		wsSwMacNameMibModule MODULE-IDENTITY 
			LAST-UPDATED "200806021134Z"		-- June 02, 2008 at 11:34 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"MAC Name Configuration and Status."
			REVISION "200806021148Z"		-- June 02, 2008 at 11:48 GMT
			DESCRIPTION 
				"01a01
				Initial revision."
			::= { wsSwMacName 1 }

		
	
	
	
--
-- Node definitions
--
	
		-- 1.3.6.1.4.1.388.14.2.10.1.1
		wsSwMacNameMIB OBJECT IDENTIFIER ::= { wsSwMacNameMibModule 1 }

		
		-- 1.3.6.1.4.1.388.14.2.10.1.1.1
		wsSwMacNameTable OBJECT-TYPE
			SYNTAX SEQUENCE OF WsSwMacNameEntry
			MAX-ACCESS not-accessible
			STATUS current
			DESCRIPTION
				"Table of MAC names."
			::= { wsSwMacNameMIB 1 }

		
		-- 1.3.6.1.4.1.388.14.2.10.1.1.1.1
		wsSwMacNameEntry OBJECT-TYPE
			SYNTAX WsSwMacNameEntry
			MAX-ACCESS not-accessible
			STATUS current
			DESCRIPTION
				"An entry in the table."
			INDEX { wsSwMacNameAddr }
			::= { wsSwMacNameTable 1 }

		
		WsSwMacNameEntry ::=
			SEQUENCE { 
				wsSwMacNameAddr
					PhysAddress,
				wsSwMacNameName
					DisplayString,
				wsSwMacNameRowStatus
					AbbrevRowStatus
			 }

		-- 1.3.6.1.4.1.388.14.2.10.1.1.1.1.1
		wsSwMacNameAddr OBJECT-TYPE
			SYNTAX PhysAddress
			MAX-ACCESS read-only
			STATUS current
			DESCRIPTION
				"The MAC address."
			::= { wsSwMacNameEntry 1 }

		
		-- 1.3.6.1.4.1.388.14.2.10.1.1.1.1.2
		wsSwMacNameName OBJECT-TYPE
			SYNTAX DisplayString (SIZE (1..64))
			MAX-ACCESS read-create
			STATUS current
			DESCRIPTION
				"The MAC name. It needs to be unique.
				
				MAC name can contain any alphanumeric character
				except for the extended characters that are listed below:
				- Backslash (\)
				- Slash mark (/)
				- Colon (:)
				- Asterisk (*)
				- Question mark (?)
				- Double Quote
				- Less than sign (<)
				- Vertical bar (|)
				
				MAC name can contain a period '.', but cannot start
				with a period."
			::= { wsSwMacNameEntry 2 }

		
		-- 1.3.6.1.4.1.388.14.2.10.1.1.1.1.3
		wsSwMacNameRowStatus OBJECT-TYPE
			SYNTAX AbbrevRowStatus
			MAX-ACCESS read-create
			STATUS current
			DESCRIPTION
				"The Row status. All columns must be supplied to create a row."
			::= { wsSwMacNameEntry 3 }

		
		-- 1.3.6.1.4.1.388.14.2.10.1.1.100
		wsSwMacNameConf OBJECT IDENTIFIER ::= { wsSwMacNameMIB 100 }

		
		-- 1.3.6.1.4.1.388.14.2.10.1.1.100.1
		wsSwMacNameGroups OBJECT IDENTIFIER ::= { wsSwMacNameConf 1 }

		
		-- 1.3.6.1.4.1.388.14.2.10.1.1.100.1.1
		wsSwMacNameObjectGroup OBJECT-GROUP
			OBJECTS { wsSwMacNameAddr, wsSwMacNameName, wsSwMacNameRowStatus }
			STATUS current
			DESCRIPTION 
				" "
			::= { wsSwMacNameGroups 1 }

		
		-- 1.3.6.1.4.1.388.14.2.10.1.1.100.2
		wsSwMacNameCompls OBJECT IDENTIFIER ::= { wsSwMacNameConf 2 }

		
		-- 1.3.6.1.4.1.388.14.2.10.1.1.100.2.1
		wsSwMacNameCompliance MODULE-COMPLIANCE
			STATUS current
			DESCRIPTION 
				" "
			MODULE -- this module
				MANDATORY-GROUPS { wsSwMacNameObjectGroup }
			::= { wsSwMacNameCompls 1 }

		
	
	END

--
-- WS-SW-MAC-NAME.my
--
