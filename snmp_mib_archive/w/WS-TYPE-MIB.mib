--
-- WS-TYPE-MIB.my
-- MIB generated by MG-SOFT Visual MIB Builder Version 6.0  Build 88
-- Tuesday, August 12, 2008 at 11:10:12
--

	WS-TYPE-MIB DEFINITIONS ::= BEGIN
 
		IMPORTS
			Unsigned32
				FROM SNMPv2-SMI			
			TEXTUAL-CONVENTION			
				FROM SNMPv2-TC;
	
	
--
-- Type definitions
--
	
-- This datatype always means that the MIB variable is
-- a simple ENUM that when written to 'doActionRightNow', 
-- causes the described action to take place, (much like 
-- a button pressed in a UI).
-- 
-- Such a value does NOT remain in state 'doActionRightNow'
-- while the operation is in-process, but instead when read 
-- always returns 'idleState'.
		DoActionNow ::= INTEGER
			{
			doActionRightNow(1),
			idleState(2)
			}

-- Values of this type are passwords.  They can be written,
-- but when read, they return a 0-length string.
		Password ::= OCTET STRING

-- In order to make the switch's implementation of 
-- numerous tables simpler, tables using this datatype
-- have a fixed number of entries with fixed indices.
-- In such tables, no entries may be added or deleted, 
-- but the pre-existing rows can be enabled or disabled 
-- using the value declared with this datatype.
		StaticRowEnable ::= INTEGER
			{
			enable(1),
			disable(2)
			}

		PartsPer10k ::= Unsigned32 (0..10000)
-- This datatype is used for all percentage values that have
-- interesting tenths and hundreths, (such as 1.37%).  SNMP
-- cannot report decimals, only whole numbers.  Values of 
-- this datatype are expressed not as parts-per-100, (percent),
-- but as parts-per-10000.
-- 
-- Said another way, values of this type are percent 
-- multiplied by 100.
-- 
-- For example, 1.37% would be reported as 137.
-- 
-- In order to make the switch's implementation of some
-- dynamic tables simpler, tables using this datatype
-- use an abbreviated form of RowStatus.
-- 
-- Only CreateAndGo and Destroy states are supported.
-- 
-- On row creation, a single SET-PDU must contain all
-- the required values, including this value set to
-- createAndGo.  (This greatly simplifies row validation
-- for the switch).
-- 
-- Setting this value to Destroy causes the corresponding
-- row to be deleted.
-- 
		AbbrevRowStatus ::= INTEGER
			{
			createAndGo(4),
			destroy(6)
			}

		ScaleBy100 ::= Unsigned32
-- This datatype is used for all values that have interesting 
-- tenths and hundreths, (such as 2.48).  SNMP cannot report 
-- decimals, only whole numbers.  Values of this datatype are 
-- scaled (muliplied) by 100.
-- 
-- For example, 2.48 would be reported as 248.
-- This datatype always means that the MIB variable is
-- a simple ENUM that when written to 'doActionRightNow', 
-- causes the described action to take place, (much like 
-- a button pressed in a UI).
-- 
-- Such a value DOES remain in state 'doActionRightNow'
-- while the operation is in-process;  when the operation is
-- completed, it will then return the value 'idleState'.
		DoActionShowProgress ::= INTEGER
			{
			doActionRightNow(1),
			idleState(2)
			}

-- Values of this type are keys, expressed in hexadecimal as
-- a sequence of characters '0'..'9' plus 'A'..'F'.
-- 
-- Unless otherwise noted, the default value for variables of
-- this type is all-0s.
-- 
-- Values of this type are passwords.  They can be written,
-- but when read, they return a 0-length string.
		HexPassword ::= OCTET STRING

		TransmitRate ::= BITS
			{
			null(0),
			rate1Mb(1),
			rate2Mb(2),
			rate5pt5Mb(3),
			rate6Mb(4),
			rate9Mb(5),
			rate11Mb(6),
			rate12Mb(7),
			rate18Mb(8),
			rate22Mb(9),
			rate24Mb(10),
			rate36Mb(11),
			rate48Mb(12),
			rate54Mb(13)
			}

		RadioType ::= INTEGER
			{
			radio802dot11A(1),
			radio802dot11B(2),
			radio802dot11BG(3),
			radio802dot11FH(4),
			radio802dot11AN(5),
			radio802dot11BGN(6)
			}

--  
-- 
		SinglePointer ::= INTEGER (0..255)

		MultiPointer63 ::= BITS
			{
			null(0),
			referToEntry001(1),
			referToEntry002(2),
			referToEntry003(3),
			referToEntry004(4),
			referToEntry005(5),
			referToEntry006(6),
			referToEntry007(7),
			referToEntry008(8),
			referToEntry009(9),
			referToEntry010(10),
			referToEntry011(11),
			referToEntry012(12),
			referToEntry013(13),
			referToEntry014(14),
			referToEntry015(15),
			referToEntry016(16),
			referToEntry017(17),
			referToEntry018(18),
			referToEntry019(19),
			referToEntry020(20),
			referToEntry021(21),
			referToEntry022(22),
			referToEntry023(23),
			referToEntry024(24),
			referToEntry025(25),
			referToEntry026(26),
			referToEntry027(27),
			referToEntry028(28),
			referToEntry029(29),
			referToEntry030(30),
			referToEntry031(31),
			referToEntry032(32),
			referToEntry033(33),
			referToEntry034(34),
			referToEntry035(35),
			referToEntry036(36),
			referToEntry037(37),
			referToEntry038(38),
			referToEntry039(39),
			referToEntry040(40),
			referToEntry041(41),
			referToEntry042(42),
			referToEntry043(43),
			referToEntry044(44),
			referToEntry045(45),
			referToEntry046(46),
			referToEntry047(47),
			referToEntry048(48),
			referToEntry049(49),
			referToEntry050(50),
			referToEntry051(51),
			referToEntry052(52),
			referToEntry053(53),
			referToEntry054(54),
			referToEntry055(55),
			referToEntry056(56),
			referToEntry057(57),
			referToEntry058(58),
			referToEntry059(59),
			referToEntry060(60),
			referToEntry061(61),
			referToEntry062(62),
			referToEntry063(63)
			}

		MultiPointer64 ::= BITS
			{
			referToEntry001(0),
			referToEntry002(1),
			referToEntry003(2),
			referToEntry004(3),
			referToEntry005(4),
			referToEntry006(5),
			referToEntry007(6),
			referToEntry008(7),
			referToEntry009(8),
			referToEntry010(9),
			referToEntry011(10),
			referToEntry012(11),
			referToEntry013(12),
			referToEntry014(13),
			referToEntry015(14),
			referToEntry016(15),
			referToEntry017(16),
			referToEntry018(17),
			referToEntry019(18),
			referToEntry020(19),
			referToEntry021(20),
			referToEntry022(21),
			referToEntry023(22),
			referToEntry024(23),
			referToEntry025(24),
			referToEntry026(25),
			referToEntry027(26),
			referToEntry028(27),
			referToEntry029(28),
			referToEntry030(29),
			referToEntry031(30),
			referToEntry032(31),
			referToEntry033(32),
			referToEntry034(33),
			referToEntry035(34),
			referToEntry036(35),
			referToEntry037(36),
			referToEntry038(37),
			referToEntry039(38),
			referToEntry040(39),
			referToEntry041(40),
			referToEntry042(41),
			referToEntry043(42),
			referToEntry044(43),
			referToEntry045(44),
			referToEntry046(45),
			referToEntry047(46),
			referToEntry048(47),
			referToEntry049(48),
			referToEntry050(49),
			referToEntry051(50),
			referToEntry052(51),
			referToEntry053(52),
			referToEntry054(53),
			referToEntry055(54),
			referToEntry056(55),
			referToEntry057(56),
			referToEntry058(57),
			referToEntry059(58),
			referToEntry060(59),
			referToEntry061(60),
			referToEntry062(61),
			referToEntry063(62),
			referToEntry064(63)
			}

		MultiPointer255 ::= BITS
			{
			null(0),
			referToEntry001(1),
			referToEntry002(2),
			referToEntry003(3),
			referToEntry004(4),
			referToEntry005(5),
			referToEntry006(6),
			referToEntry007(7),
			referToEntry008(8),
			referToEntry009(9),
			referToEntry010(10),
			referToEntry011(11),
			referToEntry012(12),
			referToEntry013(13),
			referToEntry014(14),
			referToEntry015(15),
			referToEntry016(16),
			referToEntry017(17),
			referToEntry018(18),
			referToEntry019(19),
			referToEntry020(20),
			referToEntry021(21),
			referToEntry022(22),
			referToEntry023(23),
			referToEntry024(24),
			referToEntry025(25),
			referToEntry026(26),
			referToEntry027(27),
			referToEntry028(28),
			referToEntry029(29),
			referToEntry030(30),
			referToEntry031(31),
			referToEntry032(32),
			referToEntry033(33),
			referToEntry034(34),
			referToEntry035(35),
			referToEntry036(36),
			referToEntry037(37),
			referToEntry038(38),
			referToEntry039(39),
			referToEntry040(40),
			referToEntry041(41),
			referToEntry042(42),
			referToEntry043(43),
			referToEntry044(44),
			referToEntry045(45),
			referToEntry046(46),
			referToEntry047(47),
			referToEntry048(48),
			referToEntry049(49),
			referToEntry050(50),
			referToEntry051(51),
			referToEntry052(52),
			referToEntry053(53),
			referToEntry054(54),
			referToEntry055(55),
			referToEntry056(56),
			referToEntry057(57),
			referToEntry058(58),
			referToEntry059(59),
			referToEntry060(60),
			referToEntry061(61),
			referToEntry062(62),
			referToEntry063(63),
			referToEntry064(64),
			referToEntry065(65),
			referToEntry066(66),
			referToEntry067(67),
			referToEntry068(68),
			referToEntry069(69),
			referToEntry070(70),
			referToEntry071(71),
			referToEntry072(72),
			referToEntry073(73),
			referToEntry074(74),
			referToEntry075(75),
			referToEntry076(76),
			referToEntry077(77),
			referToEntry078(78),
			referToEntry079(79),
			referToEntry080(80),
			referToEntry081(81),
			referToEntry082(82),
			referToEntry083(83),
			referToEntry084(84),
			referToEntry085(85),
			referToEntry086(86),
			referToEntry087(87),
			referToEntry088(88),
			referToEntry089(89),
			referToEntry090(90),
			referToEntry091(91),
			referToEntry092(92),
			referToEntry093(93),
			referToEntry094(94),
			referToEntry095(95),
			referToEntry096(96),
			referToEntry097(97),
			referToEntry098(98),
			referToEntry099(99),
			referToEntry100(100),
			referToEntry101(101),
			referToEntry102(102),
			referToEntry103(103),
			referToEntry104(104),
			referToEntry105(105),
			referToEntry106(106),
			referToEntry107(107),
			referToEntry108(108),
			referToEntry109(109),
			referToEntry110(110),
			referToEntry111(111),
			referToEntry112(112),
			referToEntry113(113),
			referToEntry114(114),
			referToEntry115(115),
			referToEntry116(116),
			referToEntry117(117),
			referToEntry118(118),
			referToEntry119(119),
			referToEntry120(120),
			referToEntry121(121),
			referToEntry122(122),
			referToEntry123(123),
			referToEntry124(124),
			referToEntry125(125),
			referToEntry126(126),
			referToEntry127(127),
			referToEntry128(128),
			referToEntry129(129),
			referToEntry130(130),
			referToEntry131(131),
			referToEntry132(132),
			referToEntry133(133),
			referToEntry134(134),
			referToEntry135(135),
			referToEntry136(136),
			referToEntry137(137),
			referToEntry138(138),
			referToEntry139(139),
			referToEntry140(140),
			referToEntry141(141),
			referToEntry142(142),
			referToEntry143(143),
			referToEntry144(144),
			referToEntry145(145),
			referToEntry146(146),
			referToEntry147(147),
			referToEntry148(148),
			referToEntry149(149),
			referToEntry150(150),
			referToEntry151(151),
			referToEntry152(152),
			referToEntry153(153),
			referToEntry154(154),
			referToEntry155(155),
			referToEntry156(156),
			referToEntry157(157),
			referToEntry158(158),
			referToEntry159(159),
			referToEntry160(160),
			referToEntry161(161),
			referToEntry162(162),
			referToEntry163(163),
			referToEntry164(164),
			referToEntry165(165),
			referToEntry166(166),
			referToEntry167(167),
			referToEntry168(168),
			referToEntry169(169),
			referToEntry170(170),
			referToEntry171(171),
			referToEntry172(172),
			referToEntry173(173),
			referToEntry174(174),
			referToEntry175(175),
			referToEntry176(176),
			referToEntry177(177),
			referToEntry178(178),
			referToEntry179(179),
			referToEntry180(180),
			referToEntry181(181),
			referToEntry182(182),
			referToEntry183(183),
			referToEntry184(184),
			referToEntry185(185),
			referToEntry186(186),
			referToEntry187(187),
			referToEntry188(188),
			referToEntry189(189),
			referToEntry190(190),
			referToEntry191(191),
			referToEntry192(192),
			referToEntry193(193),
			referToEntry194(194),
			referToEntry195(195),
			referToEntry196(196),
			referToEntry197(197),
			referToEntry198(198),
			referToEntry199(199),
			referToEntry200(200),
			referToEntry201(201),
			referToEntry202(202),
			referToEntry203(203),
			referToEntry204(204),
			referToEntry205(205),
			referToEntry206(206),
			referToEntry207(207),
			referToEntry208(208),
			referToEntry209(209),
			referToEntry210(210),
			referToEntry211(211),
			referToEntry212(212),
			referToEntry213(213),
			referToEntry214(214),
			referToEntry215(215),
			referToEntry216(216),
			referToEntry217(217),
			referToEntry218(218),
			referToEntry219(219),
			referToEntry220(220),
			referToEntry221(221),
			referToEntry222(222),
			referToEntry223(223),
			referToEntry224(224),
			referToEntry225(225),
			referToEntry226(226),
			referToEntry227(227),
			referToEntry228(228),
			referToEntry229(229),
			referToEntry230(230),
			referToEntry231(231),
			referToEntry232(232),
			referToEntry233(233),
			referToEntry234(234),
			referToEntry235(235),
			referToEntry236(236),
			referToEntry237(237),
			referToEntry238(238),
			referToEntry239(239),
			referToEntry240(240),
			referToEntry241(241),
			referToEntry242(242),
			referToEntry243(243),
			referToEntry244(244),
			referToEntry245(245),
			referToEntry246(246),
			referToEntry247(247),
			referToEntry248(248),
			referToEntry249(249),
			referToEntry250(250),
			referToEntry251(251),
			referToEntry252(252),
			referToEntry253(253),
			referToEntry254(254),
			referToEntry255(255)
			}

		MultiPointer256 ::= BITS
			{
			referToEntry001(0),
			referToEntry002(1),
			referToEntry003(2),
			referToEntry004(3),
			referToEntry005(4),
			referToEntry006(5),
			referToEntry007(6),
			referToEntry008(7),
			referToEntry009(8),
			referToEntry010(9),
			referToEntry011(10),
			referToEntry012(11),
			referToEntry013(12),
			referToEntry014(13),
			referToEntry015(14),
			referToEntry016(15),
			referToEntry017(16),
			referToEntry018(17),
			referToEntry019(18),
			referToEntry020(19),
			referToEntry021(20),
			referToEntry022(21),
			referToEntry023(22),
			referToEntry024(23),
			referToEntry025(24),
			referToEntry026(25),
			referToEntry027(26),
			referToEntry028(27),
			referToEntry029(28),
			referToEntry030(29),
			referToEntry031(30),
			referToEntry032(31),
			referToEntry033(32),
			referToEntry034(33),
			referToEntry035(34),
			referToEntry036(35),
			referToEntry037(36),
			referToEntry038(37),
			referToEntry039(38),
			referToEntry040(39),
			referToEntry041(40),
			referToEntry042(41),
			referToEntry043(42),
			referToEntry044(43),
			referToEntry045(44),
			referToEntry046(45),
			referToEntry047(46),
			referToEntry048(47),
			referToEntry049(48),
			referToEntry050(49),
			referToEntry051(50),
			referToEntry052(51),
			referToEntry053(52),
			referToEntry054(53),
			referToEntry055(54),
			referToEntry056(55),
			referToEntry057(56),
			referToEntry058(57),
			referToEntry059(58),
			referToEntry060(59),
			referToEntry061(60),
			referToEntry062(61),
			referToEntry063(62),
			referToEntry064(63),
			referToEntry065(64),
			referToEntry066(65),
			referToEntry067(66),
			referToEntry068(67),
			referToEntry069(68),
			referToEntry070(69),
			referToEntry071(70),
			referToEntry072(71),
			referToEntry073(72),
			referToEntry074(73),
			referToEntry075(74),
			referToEntry076(75),
			referToEntry077(76),
			referToEntry078(77),
			referToEntry079(78),
			referToEntry080(79),
			referToEntry081(80),
			referToEntry082(81),
			referToEntry083(82),
			referToEntry084(83),
			referToEntry085(84),
			referToEntry086(85),
			referToEntry087(86),
			referToEntry088(87),
			referToEntry089(88),
			referToEntry090(89),
			referToEntry091(90),
			referToEntry092(91),
			referToEntry093(92),
			referToEntry094(93),
			referToEntry095(94),
			referToEntry096(95),
			referToEntry097(96),
			referToEntry098(97),
			referToEntry099(98),
			referToEntry100(99),
			referToEntry101(100),
			referToEntry102(101),
			referToEntry103(102),
			referToEntry104(103),
			referToEntry105(104),
			referToEntry106(105),
			referToEntry107(106),
			referToEntry108(107),
			referToEntry109(108),
			referToEntry110(109),
			referToEntry111(110),
			referToEntry112(111),
			referToEntry113(112),
			referToEntry114(113),
			referToEntry115(114),
			referToEntry116(115),
			referToEntry117(116),
			referToEntry118(117),
			referToEntry119(118),
			referToEntry120(119),
			referToEntry121(120),
			referToEntry122(121),
			referToEntry123(122),
			referToEntry124(123),
			referToEntry125(124),
			referToEntry126(125),
			referToEntry127(126),
			referToEntry128(127),
			referToEntry129(128),
			referToEntry130(129),
			referToEntry131(130),
			referToEntry132(131),
			referToEntry133(132),
			referToEntry134(133),
			referToEntry135(134),
			referToEntry136(135),
			referToEntry137(136),
			referToEntry138(137),
			referToEntry139(138),
			referToEntry140(139),
			referToEntry141(140),
			referToEntry142(141),
			referToEntry143(142),
			referToEntry144(143),
			referToEntry145(144),
			referToEntry146(145),
			referToEntry147(146),
			referToEntry148(147),
			referToEntry149(148),
			referToEntry150(149),
			referToEntry151(150),
			referToEntry152(151),
			referToEntry153(152),
			referToEntry154(153),
			referToEntry155(154),
			referToEntry156(155),
			referToEntry157(156),
			referToEntry158(157),
			referToEntry159(158),
			referToEntry160(159),
			referToEntry161(160),
			referToEntry162(161),
			referToEntry163(162),
			referToEntry164(163),
			referToEntry165(164),
			referToEntry166(165),
			referToEntry167(166),
			referToEntry168(167),
			referToEntry169(168),
			referToEntry170(169),
			referToEntry171(170),
			referToEntry172(171),
			referToEntry173(172),
			referToEntry174(173),
			referToEntry175(174),
			referToEntry176(175),
			referToEntry177(176),
			referToEntry178(177),
			referToEntry179(178),
			referToEntry180(179),
			referToEntry181(180),
			referToEntry182(181),
			referToEntry183(182),
			referToEntry184(183),
			referToEntry185(184),
			referToEntry186(185),
			referToEntry187(186),
			referToEntry188(187),
			referToEntry189(188),
			referToEntry190(189),
			referToEntry191(190),
			referToEntry192(191),
			referToEntry193(192),
			referToEntry194(193),
			referToEntry195(194),
			referToEntry196(195),
			referToEntry197(196),
			referToEntry198(197),
			referToEntry199(198),
			referToEntry200(199),
			referToEntry201(200),
			referToEntry202(201),
			referToEntry203(202),
			referToEntry204(203),
			referToEntry205(204),
			referToEntry206(205),
			referToEntry207(206),
			referToEntry208(207),
			referToEntry209(208),
			referToEntry210(209),
			referToEntry211(210),
			referToEntry212(211),
			referToEntry213(212),
			referToEntry214(213),
			referToEntry215(214),
			referToEntry216(215),
			referToEntry217(216),
			referToEntry218(217),
			referToEntry219(218),
			referToEntry220(219),
			referToEntry221(220),
			referToEntry222(221),
			referToEntry223(222),
			referToEntry224(223),
			referToEntry225(224),
			referToEntry226(225),
			referToEntry227(226),
			referToEntry228(227),
			referToEntry229(228),
			referToEntry230(229),
			referToEntry231(230),
			referToEntry232(231),
			referToEntry233(232),
			referToEntry234(233),
			referToEntry235(234),
			referToEntry236(235),
			referToEntry237(236),
			referToEntry238(237),
			referToEntry239(238),
			referToEntry240(239),
			referToEntry241(240),
			referToEntry242(241),
			referToEntry243(242),
			referToEntry244(243),
			referToEntry245(244),
			referToEntry246(245),
			referToEntry247(246),
			referToEntry248(247),
			referToEntry249(248),
			referToEntry250(249),
			referToEntry251(250),
			referToEntry252(251),
			referToEntry253(252),
			referToEntry254(253),
			referToEntry255(254),
			referToEntry256(255)
			}

		MultiPointer512 ::= BITS
			{
			referToEntry001(0),
			referToEntry002(1),
			referToEntry003(2),
			referToEntry004(3),
			referToEntry005(4),
			referToEntry006(5),
			referToEntry007(6),
			referToEntry008(7),
			referToEntry009(8),
			referToEntry010(9),
			referToEntry011(10),
			referToEntry012(11),
			referToEntry013(12),
			referToEntry014(13),
			referToEntry015(14),
			referToEntry016(15),
			referToEntry017(16),
			referToEntry018(17),
			referToEntry019(18),
			referToEntry020(19),
			referToEntry021(20),
			referToEntry022(21),
			referToEntry023(22),
			referToEntry024(23),
			referToEntry025(24),
			referToEntry026(25),
			referToEntry027(26),
			referToEntry028(27),
			referToEntry029(28),
			referToEntry030(29),
			referToEntry031(30),
			referToEntry032(31),
			referToEntry033(32),
			referToEntry034(33),
			referToEntry035(34),
			referToEntry036(35),
			referToEntry037(36),
			referToEntry038(37),
			referToEntry039(38),
			referToEntry040(39),
			referToEntry041(40),
			referToEntry042(41),
			referToEntry043(42),
			referToEntry044(43),
			referToEntry045(44),
			referToEntry046(45),
			referToEntry047(46),
			referToEntry048(47),
			referToEntry049(48),
			referToEntry050(49),
			referToEntry051(50),
			referToEntry052(51),
			referToEntry053(52),
			referToEntry054(53),
			referToEntry055(54),
			referToEntry056(55),
			referToEntry057(56),
			referToEntry058(57),
			referToEntry059(58),
			referToEntry060(59),
			referToEntry061(60),
			referToEntry062(61),
			referToEntry063(62),
			referToEntry064(63),
			referToEntry065(64),
			referToEntry066(65),
			referToEntry067(66),
			referToEntry068(67),
			referToEntry069(68),
			referToEntry070(69),
			referToEntry071(70),
			referToEntry072(71),
			referToEntry073(72),
			referToEntry074(73),
			referToEntry075(74),
			referToEntry076(75),
			referToEntry077(76),
			referToEntry078(77),
			referToEntry079(78),
			referToEntry080(79),
			referToEntry081(80),
			referToEntry082(81),
			referToEntry083(82),
			referToEntry084(83),
			referToEntry085(84),
			referToEntry086(85),
			referToEntry087(86),
			referToEntry088(87),
			referToEntry089(88),
			referToEntry090(89),
			referToEntry091(90),
			referToEntry092(91),
			referToEntry093(92),
			referToEntry094(93),
			referToEntry095(94),
			referToEntry096(95),
			referToEntry097(96),
			referToEntry098(97),
			referToEntry099(98),
			referToEntry100(99),
			referToEntry101(100),
			referToEntry102(101),
			referToEntry103(102),
			referToEntry104(103),
			referToEntry105(104),
			referToEntry106(105),
			referToEntry107(106),
			referToEntry108(107),
			referToEntry109(108),
			referToEntry110(109),
			referToEntry111(110),
			referToEntry112(111),
			referToEntry113(112),
			referToEntry114(113),
			referToEntry115(114),
			referToEntry116(115),
			referToEntry117(116),
			referToEntry118(117),
			referToEntry119(118),
			referToEntry120(119),
			referToEntry121(120),
			referToEntry122(121),
			referToEntry123(122),
			referToEntry124(123),
			referToEntry125(124),
			referToEntry126(125),
			referToEntry127(126),
			referToEntry128(127),
			referToEntry129(128),
			referToEntry130(129),
			referToEntry131(130),
			referToEntry132(131),
			referToEntry133(132),
			referToEntry134(133),
			referToEntry135(134),
			referToEntry136(135),
			referToEntry137(136),
			referToEntry138(137),
			referToEntry139(138),
			referToEntry140(139),
			referToEntry141(140),
			referToEntry142(141),
			referToEntry143(142),
			referToEntry144(143),
			referToEntry145(144),
			referToEntry146(145),
			referToEntry147(146),
			referToEntry148(147),
			referToEntry149(148),
			referToEntry150(149),
			referToEntry151(150),
			referToEntry152(151),
			referToEntry153(152),
			referToEntry154(153),
			referToEntry155(154),
			referToEntry156(155),
			referToEntry157(156),
			referToEntry158(157),
			referToEntry159(158),
			referToEntry160(159),
			referToEntry161(160),
			referToEntry162(161),
			referToEntry163(162),
			referToEntry164(163),
			referToEntry165(164),
			referToEntry166(165),
			referToEntry167(166),
			referToEntry168(167),
			referToEntry169(168),
			referToEntry170(169),
			referToEntry171(170),
			referToEntry172(171),
			referToEntry173(172),
			referToEntry174(173),
			referToEntry175(174),
			referToEntry176(175),
			referToEntry177(176),
			referToEntry178(177),
			referToEntry179(178),
			referToEntry180(179),
			referToEntry181(180),
			referToEntry182(181),
			referToEntry183(182),
			referToEntry184(183),
			referToEntry185(184),
			referToEntry186(185),
			referToEntry187(186),
			referToEntry188(187),
			referToEntry189(188),
			referToEntry190(189),
			referToEntry191(190),
			referToEntry192(191),
			referToEntry193(192),
			referToEntry194(193),
			referToEntry195(194),
			referToEntry196(195),
			referToEntry197(196),
			referToEntry198(197),
			referToEntry199(198),
			referToEntry200(199),
			referToEntry201(200),
			referToEntry202(201),
			referToEntry203(202),
			referToEntry204(203),
			referToEntry205(204),
			referToEntry206(205),
			referToEntry207(206),
			referToEntry208(207),
			referToEntry209(208),
			referToEntry210(209),
			referToEntry211(210),
			referToEntry212(211),
			referToEntry213(212),
			referToEntry214(213),
			referToEntry215(214),
			referToEntry216(215),
			referToEntry217(216),
			referToEntry218(217),
			referToEntry219(218),
			referToEntry220(219),
			referToEntry221(220),
			referToEntry222(221),
			referToEntry223(222),
			referToEntry224(223),
			referToEntry225(224),
			referToEntry226(225),
			referToEntry227(226),
			referToEntry228(227),
			referToEntry229(228),
			referToEntry230(229),
			referToEntry231(230),
			referToEntry232(231),
			referToEntry233(232),
			referToEntry234(233),
			referToEntry235(234),
			referToEntry236(235),
			referToEntry237(236),
			referToEntry238(237),
			referToEntry239(238),
			referToEntry240(239),
			referToEntry241(240),
			referToEntry242(241),
			referToEntry243(242),
			referToEntry244(243),
			referToEntry245(244),
			referToEntry246(245),
			referToEntry247(246),
			referToEntry248(247),
			referToEntry249(248),
			referToEntry250(249),
			referToEntry251(250),
			referToEntry252(251),
			referToEntry253(252),
			referToEntry254(253),
			referToEntry255(254),
			referToEntry256(255),
			referToEntry257(256),
			referToEntry258(257),
			referToEntry259(258),
			referToEntry260(259),
			referToEntry261(260),
			referToEntry262(261),
			referToEntry263(262),
			referToEntry264(263),
			referToEntry265(264),
			referToEntry266(265),
			referToEntry267(266),
			referToEntry268(267),
			referToEntry269(268),
			referToEntry270(269),
			referToEntry271(270),
			referToEntry272(271),
			referToEntry273(272),
			referToEntry274(273),
			referToEntry275(274),
			referToEntry276(275),
			referToEntry277(276),
			referToEntry278(277),
			referToEntry279(278),
			referToEntry280(279),
			referToEntry281(280),
			referToEntry282(281),
			referToEntry283(282),
			referToEntry284(283),
			referToEntry285(284),
			referToEntry286(285),
			referToEntry287(286),
			referToEntry288(287),
			referToEntry289(288),
			referToEntry290(289),
			referToEntry291(290),
			referToEntry292(291),
			referToEntry293(292),
			referToEntry294(293),
			referToEntry295(294),
			referToEntry296(295),
			referToEntry297(296),
			referToEntry298(297),
			referToEntry299(298),
			referToEntry300(299),
			referToEntry301(300),
			referToEntry302(301),
			referToEntry303(302),
			referToEntry304(303),
			referToEntry305(304),
			referToEntry306(305),
			referToEntry307(306),
			referToEntry308(307),
			referToEntry309(308),
			referToEntry310(309),
			referToEntry311(310),
			referToEntry312(311),
			referToEntry313(312),
			referToEntry314(313),
			referToEntry315(314),
			referToEntry316(315),
			referToEntry317(316),
			referToEntry318(317),
			referToEntry319(318),
			referToEntry320(319),
			referToEntry321(320),
			referToEntry322(321),
			referToEntry323(322),
			referToEntry324(323),
			referToEntry325(324),
			referToEntry326(325),
			referToEntry327(326),
			referToEntry328(327),
			referToEntry329(328),
			referToEntry330(329),
			referToEntry331(330),
			referToEntry332(331),
			referToEntry333(332),
			referToEntry334(333),
			referToEntry335(334),
			referToEntry336(335),
			referToEntry337(336),
			referToEntry338(337),
			referToEntry339(338),
			referToEntry340(339),
			referToEntry341(340),
			referToEntry342(341),
			referToEntry343(342),
			referToEntry344(343),
			referToEntry345(344),
			referToEntry346(345),
			referToEntry347(346),
			referToEntry348(347),
			referToEntry349(348),
			referToEntry350(349),
			referToEntry351(350),
			referToEntry352(351),
			referToEntry353(352),
			referToEntry354(353),
			referToEntry355(354),
			referToEntry356(355),
			referToEntry357(356),
			referToEntry358(357),
			referToEntry359(358),
			referToEntry360(359),
			referToEntry361(360),
			referToEntry362(361),
			referToEntry363(362),
			referToEntry364(363),
			referToEntry365(364),
			referToEntry366(365),
			referToEntry367(366),
			referToEntry368(367),
			referToEntry369(368),
			referToEntry370(369),
			referToEntry371(370),
			referToEntry372(371),
			referToEntry373(372),
			referToEntry374(373),
			referToEntry375(374),
			referToEntry376(375),
			referToEntry377(376),
			referToEntry378(377),
			referToEntry379(378),
			referToEntry380(379),
			referToEntry381(380),
			referToEntry382(381),
			referToEntry383(382),
			referToEntry384(383),
			referToEntry385(384),
			referToEntry386(385),
			referToEntry387(386),
			referToEntry388(387),
			referToEntry389(388),
			referToEntry390(389),
			referToEntry391(390),
			referToEntry392(391),
			referToEntry393(392),
			referToEntry394(393),
			referToEntry395(394),
			referToEntry396(395),
			referToEntry397(396),
			referToEntry398(397),
			referToEntry399(398),
			referToEntry400(399),
			referToEntry401(400),
			referToEntry402(401),
			referToEntry403(402),
			referToEntry404(403),
			referToEntry405(404),
			referToEntry406(405),
			referToEntry407(406),
			referToEntry408(407),
			referToEntry409(408),
			referToEntry410(409),
			referToEntry411(410),
			referToEntry412(411),
			referToEntry413(412),
			referToEntry414(413),
			referToEntry415(414),
			referToEntry416(415),
			referToEntry417(416),
			referToEntry418(417),
			referToEntry419(418),
			referToEntry420(419),
			referToEntry421(420),
			referToEntry422(421),
			referToEntry423(422),
			referToEntry424(423),
			referToEntry425(424),
			referToEntry426(425),
			referToEntry427(426),
			referToEntry428(427),
			referToEntry429(428),
			referToEntry430(429),
			referToEntry431(430),
			referToEntry432(431),
			referToEntry433(432),
			referToEntry434(433),
			referToEntry435(434),
			referToEntry436(435),
			referToEntry437(436),
			referToEntry438(437),
			referToEntry439(438),
			referToEntry440(439),
			referToEntry441(440),
			referToEntry442(441),
			referToEntry443(442),
			referToEntry444(443),
			referToEntry445(444),
			referToEntry446(445),
			referToEntry447(446),
			referToEntry448(447),
			referToEntry449(448),
			referToEntry450(449),
			referToEntry451(450),
			referToEntry452(451),
			referToEntry453(452),
			referToEntry454(453),
			referToEntry455(454),
			referToEntry456(455),
			referToEntry457(456),
			referToEntry458(457),
			referToEntry459(458),
			referToEntry460(459),
			referToEntry461(460),
			referToEntry462(461),
			referToEntry463(462),
			referToEntry464(463),
			referToEntry465(464),
			referToEntry466(465),
			referToEntry467(466),
			referToEntry468(467),
			referToEntry469(468),
			referToEntry470(469),
			referToEntry471(470),
			referToEntry472(471),
			referToEntry473(472),
			referToEntry474(473),
			referToEntry475(474),
			referToEntry476(475),
			referToEntry477(476),
			referToEntry478(477),
			referToEntry479(478),
			referToEntry480(479),
			referToEntry481(480),
			referToEntry482(481),
			referToEntry483(482),
			referToEntry484(483),
			referToEntry485(484),
			referToEntry486(485),
			referToEntry487(486),
			referToEntry488(487),
			referToEntry489(488),
			referToEntry490(489),
			referToEntry491(490),
			referToEntry492(491),
			referToEntry493(492),
			referToEntry494(493),
			referToEntry495(494),
			referToEntry496(495),
			referToEntry497(496),
			referToEntry498(497),
			referToEntry499(498),
			referToEntry500(499),
			referToEntry501(500),
			referToEntry502(501),
			referToEntry503(502),
			referToEntry504(503),
			referToEntry505(504),
			referToEntry506(505),
			referToEntry507(506),
			referToEntry508(507),
			referToEntry509(508),
			referToEntry510(509),
			referToEntry511(510),
			referToEntry512(511)
			}

	
--
-- Textual conventions
--
	
		SmtpNotifyBitMap ::= TEXTUAL-CONVENTION
			STATUS current
			DESCRIPTION 
				"Bit map for e-mail notification of traps.
				
				Bit position:
				The Least Significant Bit corresponds to the first trap in a trap group.
				The next bit corresponds to the next trap in the same group and so on.
				Unused bits are ignored.
				
				Bit values:
				1 - E-mail notification is enabled.
				0 - E-mail notification is disabled."
			SYNTAX OCTET STRING (SIZE (8))

	
	END

--
-- WS-TYPE-MIB.my
--
