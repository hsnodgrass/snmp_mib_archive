-- ****************************************************************************
--      The Wyse Enterprise number is 714
--  09/09/99 ble    Changed to compile with other MIB compilers.
--  07/28/99 ble	Added new trap error code: LS_FAIL_BADKEY
--  07/09/99 mla	Add detail descriptions on wbt3UsersTable
--  07/07/99 mla	Add wbt3RDPConnModifiable, wbt3ICAConnModifiable AND wbt3TermConnModifiable
--	07/01/99 ble	Update wbt3UsersTable, Mib revision to 1.8
--					objects in wbt3DispCharacteristic group can be set.
--					added wbt3DispUseDDC.
--	06/29/99 mla	Update wbt3ConnectionsTable, Mib revision to 1.7
--  06/16/99 ble	Added new trap error code: LS_INVALID_BOOTSTRAP
--  06/03/99 ble	Updated Mib revision 1.6
--  05/30/99 ble	Added new trap error code: LS_FAIL_PARAMINIFILENOTFOUND
--  05/17/99 ble    Added wbt3TermConnVTEmuModel, wbt3TermConnIBM3270EmuModel, 
--                  wbt3TermConnIBM5250EmuModel and wbt3TermConnScript.
--  05/11/99 ble    Changed wbt3UserName in wbt3Security group to wbt3AutoLoginUserName.
--                  Added new wbt3ResetToFactoryDefault object under wbt3Administration\
--                  wbt3Action to reset the terminal to factory-default settings.
--                  Added new trap error code: LS_FAIL_RESET_DEFAULTFACTORY 
--                  Added new wbt3TermConnections under wbt3Connections.              
--  04/29/99 ble    Added wbt3CharacterRepeatDelay, wbt3CharacterRepeatRate, 
--					wbt3NetworkSpeed.
--  04/21/99 ble    Moved wbt3Users group under wbt3Administration group to wbt3 group.
--  04/20/99 ble    Created new group wbt3Connections and moved the wbt3ConnectionsTable
--                  from wbt3Network. Changed all TcpIp to Network for future uses with
--                  different protocol than TCP and added wbt3NetworkProtocol.
--  04/05/99 ble    Added wbt3Security group under wbt3Administration
--  03/28/99 ble    Changed wbt3BuildInfo to be displayed as table.
--                  enhancements. Added new groups: wbt3Users, wbt3connections.
--  02/25/99 ble    Added DNS and WINS objects under wbt3Network group.
--                  Added new keyboards local under wbt3kbLanguage.
--  02/10/99 ble    Added wbt3EnergySavers object under wbt3Display group.
--  01/20/99 ble    enhancements. Added new groups: wbt3Apps, wbt3DHCPoptionIDs,
--                  wbt3TouchScreen and wbt3InfoLocation. 
--  01/07/99 ble    enhancements. Added new groups: wbt3Network, wbt3Trapservers, 
--                  wbt3FTPsetting...
--	10/20/98 sjl	Change product id to 3 for 3000 series
--      Last Modified 09/09/99
--      The ASN.1 prefix to, and including the Wyse Enterprise is:
--              1.3.6.1.4.1.714
--      See wbtmib.txt for the tree structure of the wyse MIB described in this 
--      document
-- ****************************************************************************

WYSE-MIB DEFINITIONS ::= BEGIN

    IMPORTS
        enterprises	FROM RFC1155-SMI
        DisplayString 	FROM RFC1213-MIB
        OBJECT-TYPE   	FROM RFC-1212
        TRAP-TYPE     	FROM RFC-1215;
                        
    wyse                OBJECT IDENTIFIER ::= { enterprises 714 }

    -- groups in wyse
        
    Product           OBJECT IDENTIFIER ::= { wyse 1 }     

-- ****************************************************************************
-- the Product group
--
--      The wyse enterprise     (1.3.6.4.1.714)
--        Product Group         (1.3.6.4.1.714.1)
--
-- Implementation of the Product group is mandatory for all SNMP agents supporting
-- the wyse MIB
-- ****************************************************************************

    -- groups in Product
    Old                 OBJECT IDENTIFIER ::= {Product 1}
    ThinClient             OBJECT IDENTIFIER ::= {Product 2}

-- ****************************************************************************
-- the Old group
--     
--      The wyse enterprise     (1.3.6.4.1.714)
--        Product Group         (1.3.6.4.1.714.1)
--          Old Group           (1.3.6.4.1.714.1.1)
-- This is old MIB mainly for X5 & Netbox
-- No official document can be found about this group.  The only information we
-- could get in this tree is Netbox's product number. It seems that nothing
-- has been defined under Netbox's subtree
-- ****************************************************************************

   -- groups in Old 
   Wysenet              OBJECT IDENTIFIER ::= {Old 1}


-- ****************************************************************************
-- the ThinClient group
--
--      The wyse enterprise     (1.3.6.4.1.714)
--        Product Group         (1.3.6.4.1.714.1)
--          ThinClient Group    (1.3.6.4.1.714.1.2)
--
-- Implementation of the ThinClient group is mandatory for all ThinClient products
-- with SNMP agents which supports the wyse MIB
-- ****************************************************************************

    -- groups in ThinClient

    wbt3              OBJECT IDENTIFIER ::= {ThinClient 3}

-- ****************************************************************************
-- the wbt3 group
--
--      The wyse enterprise   (1.3.6.4.1.714)
--        Product Group       (1.3.6.4.1.714.1)
--          ThinClient Group  (1.3.6.4.1.714.1.2)
--            wbt3 Group      (1.3.6.4.1.714.1.2.3)
--
-- Implementation of the wbt3 group is mandatory for all wbt3 products
-- with SNMP agents which supports the wyse MIB
-- ****************************************************************************
 
    -- group in wbt3

    wbt3Memory          OBJECT IDENTIFIER ::= {wbt3 1}
    wbt3PCCard          OBJECT IDENTIFIER ::= {wbt3 2}
    wbt3IODevice	 	OBJECT IDENTIFIER ::= {wbt3 3}
    wbt3Display         OBJECT IDENTIFIER ::= {wbt3 4}
    wbt3DhcpInfo		OBJECT IDENTIFIER ::= {wbt3 5}
    wbt3BuildInfo		OBJECT IDENTIFIER ::= {wbt3 6}
    wbt3CustomFields	OBJECT IDENTIFIER ::= {wbt3 7}
    wbt3Administration	OBJECT IDENTIFIER ::= {wbt3 8}
    wbt3TrapsInfo		OBJECT IDENTIFIER ::= {wbt3 9}
    wbt3MibRev			OBJECT IDENTIFIER ::= {wbt3 10}
    wbt3Network			OBJECT IDENTIFIER ::= {wbt3 11}
    wbt3Apps			OBJECT IDENTIFIER ::= {wbt3 12}
    wbt3Connections		OBJECT IDENTIFIER ::= {wbt3 13}
	wbt3Users			 OBJECT IDENTIFIER ::= {wbt3 14}


-- ****************************************************************************
-- the wbt3Memory group
--
--      The wyse enterprise      (1.3.6.4.1.714)
--        Product Group          (1.3.6.4.1.714.1)
--          ThinClient Group     (1.3.6.4.1.714.1.2)
--            wbt3 Group         (1.3.6.4.1.714.1.2.3)
--              wbt3Memory Group (1.3.6.4.1.714.1.2.3.1)
--
-- Implementation of the wbt3Memory group is mandatory for all ThinClient2 products
-- with SNMP agents which supports the wyse MIB
-- ****************************************************************************

    -- group in wbt3Memory

    wbt3Ram              OBJECT IDENTIFIER ::= {wbt3Memory 1}
    wbt3Rom              OBJECT IDENTIFIER ::= {wbt3Memory 2}

-- ****************************************************************************
-- the wbt3Ram group
--
--      The wyse enterprise      (1.3.6.4.1.714)
--        Product Group          (1.3.6.4.1.714.1)
--          ThinClient Group     (1.3.6.4.1.714.1.2)
--            wbt3 Group         (1.3.6.4.1.714.1.2.3)
--              wbt3Memory Group (1.3.6.4.1.714.1.2.3.1)
--                wbt3Ram Group  (1.3.6.4.1.714.1.2.3.1.1)
--
-- Implementation of the wbt3Ram group is mandatory for all ThinClient2 products
-- with SNMP agents which supports the wyse MIB
-- ****************************************************************************

wbt3RamNum       OBJECT-TYPE
        SYNTAX  INTEGER(1..65535)
        ACCESS  read-only
        STATUS  mandatory
        DESCRIPTION
                "The number of Ram presents in this system"
        ::={wbt3Ram 1}

wbt3RamTable  OBJECT-TYPE
        SYNTAX  SEQUENCE OF wbt3RamEntry
        ACCESS  not-accessible
        STATUS  mandatory
        DESCRIPTION
                "A list of Ram entries, number of entries is given by the
                 value of wbt3RamNum"
        ::={wbt3Ram 2}

wbt3RamEntry  OBJECT-TYPE
        SYNTAX  wbt3RamEntry
        ACCESS  not-accessible
        STATUS  mandatory
        DESCRIPTION
                "A Ram entity present in this system"
        INDEX   {wbt3RamIndex}
        ::={wbt3RamTable 1}
        
wbt3RamEntry ::=
        SEQUENCE {
                wbt3RamIndex
                INTEGER,
                wbt3RamType
                INTEGER,
                wbt3RamSize
                INTEGER
        }

wbt3RamIndex  OBJECT-TYPE
        SYNTAX  INTEGER
        ACCESS  read-only
        STATUS  mandatory
        DESCRIPTION
                "A unique value for each Ram entity present in this system.
                 Its value ranges between 1 and the value of wbt3RamNum"
        ::={wbt3RamEntry 1}

wbt3RamType   OBJECT-TYPE
        SYNTAX  INTEGER {
                        base(1),         
                        video(2),
                        extend(3)
                }
        ACCESS  read-only
        STATUS  mandatory
        DESCRIPTION
                "The type of Ram 
                 Currently defined numbers are:
                        base(1)         
                        video(2)
                        extend(3)"
        ::={wbt3RamEntry 2}

wbt3RamSize      OBJECT-TYPE
        SYNTAX  INTEGER
        ACCESS  read-only
        STATUS  mandatory
        DESCRIPTION
                "Total size of this ram entity in bytes"
        ::={wbt3RamEntry 3}


-- ****************************************************************************
-- the wbt3Rom group
--
--      The wyse enterprise      (1.3.6.4.1.714)
--        Product Group          (1.3.6.4.1.714.1)
--          ThinClient Group     (1.3.6.4.1.714.1.2)
--            wbt3 Group         (1.3.6.4.1.714.1.2.3)
--              wbt3Memory Group (1.3.6.4.1.714.1.2.3.1)
--                wbt3Rom Group  (1.3.6.4.1.714.1.2.3.1.2)
--
-- Implementation of the wbt3Rom group is mandatory for all ThinClient2 products
-- with SNMP agents which supports the wyse MIB
-- ****************************************************************************

wbt3RomNum       OBJECT-TYPE
        SYNTAX  INTEGER(1..65535)
        ACCESS  read-only
        STATUS  mandatory
        DESCRIPTION
                "The number of Rom entity presents in this system"
        ::={wbt3Rom 1}

wbt3RomTable  OBJECT-TYPE
        SYNTAX  SEQUENCE OF wbt3RomEntry
        ACCESS  not-accessible
        STATUS  mandatory
        DESCRIPTION
                "A list of Rom entries, number of entries is given by the
                 value of wbt3RomNum"
        ::={wbt3Rom 2}

wbt3RomEntry  OBJECT-TYPE
        SYNTAX  wbt3RomEntry
        ACCESS  not-accessible
        STATUS  mandatory
        DESCRIPTION
                "A Rom entity present in this system"
        INDEX   {wbt3RomIndex}
        ::={wbt3RomTable 1}
        
wbt3RomEntry ::=
        SEQUENCE {
                wbt3RomIndex
                INTEGER,
                wbt3RomType
                INTEGER,
                wbt3RomSize
                INTEGER
        }

wbt3RomIndex  OBJECT-TYPE
        SYNTAX  INTEGER
        ACCESS  read-only
        STATUS  mandatory
        DESCRIPTION
                "A unique value for each Rom entity present in this system.
                 Its value ranges between 1 and the value of wbt3RomNum"
        ::={wbt3RomEntry 1}

wbt3RomType   OBJECT-TYPE
        SYNTAX  INTEGER {
                        boot(1),
                        os(2),
                        option(3) }
        ACCESS  read-only
        STATUS  mandatory
        DESCRIPTION
                "The type of Rom 
                 Currently defined numbers are:
                        boot(1)
                        os(2)
                        option(3)"
        ::={wbt3RomEntry 2}

wbt3RomSize      OBJECT-TYPE
        SYNTAX  INTEGER
        ACCESS  read-only
        STATUS  mandatory
        DESCRIPTION
                "Total size of this Rom entity in bytes"
        ::={wbt3RomEntry 3}



-- ****************************************************************************
-- the wbt3PCCard group
--
--      The wyse enterprise      (1.3.6.4.1.714)
--        Product Group          (1.3.6.4.1.714.1)
--          ThinClient Group     (1.3.6.4.1.714.1.2)
--            wbt3 Group         (1.3.6.4.1.714.1.2.3)
--              wbt3PCCard Group (1.3.6.4.1.714.1.2.3.2)
--
-- Implementation of the wbt3PCCard group is mandatory for all ThinClient2 products
-- with SNMP agents which supports the wyse MIB
-- ****************************************************************************

wbt3PCCardNum    OBJECT-TYPE
        SYNTAX  INTEGER(1..65535)
        ACCESS  read-only
        STATUS  mandatory
        DESCRIPTION
                "The number of PCCard slots presents in this system"
        ::={wbt3PCCard 1}

wbt3PCCardTable  OBJECT-TYPE
        SYNTAX  SEQUENCE OF wbt3PCCardEntry
        ACCESS  not-accessible
        STATUS  mandatory
        DESCRIPTION
                "A list of PCCard entries, number of entries is given by the
                 value of wbt3PCCardNum"
        ::={wbt3PCCard 2}

wbt3PCCardEntry  OBJECT-TYPE
        SYNTAX  wbt3PCCardEntry
        ACCESS  not-accessible
        STATUS  mandatory
        DESCRIPTION
                "A PCCard slot present in this system"
        INDEX   {wbt3PCCardIndex}
        ::={wbt3PCCardTable 1}
        
wbt3PCCardEntry ::=
        SEQUENCE {
                wbt3PCCardIndex
                INTEGER,
                wbt3PCCardType
                INTEGER,
                wbt3PCCardVendor
                DisplayString
        }

wbt3PCCardIndex  OBJECT-TYPE
        SYNTAX  INTEGER
        ACCESS  read-only
        STATUS  mandatory
        DESCRIPTION
                "A unique value for each PCCard slot present in this system.
                 Its value ranges between 1 and the value of wbt3PCCardNum"
        ::={wbt3PCCardEntry 1}

wbt3PCCardType   OBJECT-TYPE
        SYNTAX  INTEGER {
                        empty(256),        	-- the PCCard slot is empty
                        multifunction(0),   -- a multi function PCCard card is currently in the PCCard slot 
                        memory(1),    
                        serial_port-modem(2),
						parallel_port(3),
                        fixed_disk(4),
						video_adaptor(5),
						lan_adapter(6),
						AIMS(7)
                }
        ACCESS  read-only
        STATUS  mandatory
        DESCRIPTION
                "The type of PCCard card currently plugged in this PCCard slot.
                 Currently defined numbers are:
                        empty(65535),        	-- the PCCard slot is empty
                        multifunction(0),       -- a multi function PCCard card is currently in the PCCard slot 
                        memory(1),    
                        modem(2),
			parallel_port(3),
                        fixed_disk(4),
			video_adaptor(5),
			lan_adapter(6),
			AIMS(7)"
        ::={wbt3PCCardEntry 2}

wbt3PCCardVendor OBJECT-TYPE
        SYNTAX  DisplayString
        ACCESS  read-only
        STATUS  mandatory
        DESCRIPTION
                "A textual description of the vendor of the PCCard card currently
                 plugged in this slot. e.g. 'Eicon DIVA PC Card'"
        ::={wbt3PCCardEntry 3}

-- ****************************************************************************
-- the wbt3IODevice Group
--
--      The wyse enterprise        (1.3.6.4.1.714)
--        Product Group            (1.3.6.4.1.714.1)
--          ThinClient Group       (1.3.6.4.1.714.1.2)
--            wbt3 Group           (1.3.6.4.1.714.1.2.3)
--              wbt3IODevice Group (1.3.6.4.1.714.1.2.3.3)
--
-- Implementation of the wbt3IODevice Group is mandatory for all ThinClient2 products
-- with SNMP agents which supports the wyse MIB
-- ****************************************************************************

wbt3IODevAttached  OBJECT-TYPE
        SYNTAX  INTEGER(1..4294967295)
        ACCESS  read-only
        STATUS  mandatory
        DESCRIPTION
                "A 32bit value which indicates the input devices currently
                 attached to the unit.
                 bit 0  - set if keyboard attached
                 bit 1  - set if mouse driver loaded
                 bit 2  - set if micro touch screen attached
		 bit 3  - set if elo touch screen attached
		 bit 4  - set if lightpen attached
		 bit 5  - set if floppy drive attached"
        ::={wbt3IODevice 1}

wbt3kbLanguage  OBJECT-TYPE
        SYNTAX  INTEGER {
						English-US(0),
						English-UK(1),
						French(2),
						German(3),
						Spanish(4),
						Italian(5),
						Swedish(6),
						Danish(7),
						Norwegian(8),
						Dutch(9),
						Belgian-French(10),
						Finnish(11),
						Swiss-French(12),
						Swiss-German(13),
						Japanese(14),
   						Canadian-French(15),
   						Belgian-Dutch(16),
  						Portuguese(17),
					   	Brazilian-ABNT(18),
						Italian-142(19),
						Latin-American(20),
						US-International(21),
						Canadian-FR-Multi(22),
					    Canadian-Eng-Multi(23),
					    Spanish-Variation(24)
						}
        ACCESS  read-write
        STATUS  mandatory
        DESCRIPTION
                "The language setting for the keyboard attached to this terminal"
        ::={wbt3IODevice 2}

wbt3CharacterRepeatDelay    OBJECT-TYPE
        SYNTAX  INTEGER {
                        R250(250),
                        R500(500),
						R750(750),
						R1000(1000)
						}
        ACCESS  read-write
        STATUS  mandatory
        DESCRIPTION
                "Indicates the delay time between each character."
        ::={wbt3IODevice 3}

wbt3CharacterRepeatRate    OBJECT-TYPE
        SYNTAX  INTEGER(0..31)
        ACCESS  read-write
        STATUS  mandatory
        DESCRIPTION
                "Indicates repeat rate between each character in the range of 0 to 31 at 1 interval."
        ::={wbt3IODevice 4}


-- ****************************************************************************
-- the wbt3Display Group
--
--      The wyse enterprise       (1.3.6.4.1.714)
--        Product Group           (1.3.6.4.1.714.1)
--          ThinClient Group      (1.3.6.4.1.714.1.2)
--            wbt3 Group          (1.3.6.4.1.714.1.2.3)
--              wbt3Display Group (1.3.6.4.1.714.1.2.3.4)
--
-- Implementation of the wbt3Display Group is mandatory for all ThinClient2 products
-- with SNMP agents which supports the wyse MIB
-- ****************************************************************************

    -- group in wbt3Display

    wbt3DispCharacteristic OBJECT IDENTIFIER ::= {wbt3Display 1}
    wbt3DispCapability   OBJECT IDENTIFIER ::= {wbt3Display 2}

	wbt3EnergySaver    OBJECT-TYPE
        SYNTAX  INTEGER {
                        None(0),
                        screenSaver(1),
						monitorOff(2)
						}
        ACCESS  read-write
        STATUS  mandatory
        DESCRIPTION
                "Indicates which energy saver is in use."
        ::={wbt3Display 3}

	wbt3ScreenTimeOut  OBJECT-TYPE
        SYNTAX  INTEGER(1..1440)
        ACCESS  read-write
        STATUS  mandatory
        DESCRIPTION
                "Indicates the time (in minutes) of non-activity to trigger
				 the screen saver."
        ::={wbt3Display 4}

	wbt3TouchScreen  OBJECT-TYPE
        SYNTAX  INTEGER {
                        None(0),
                        COM1(1),
						COM2(2)
						}
        ACCESS  read-write
        STATUS  mandatory
        DESCRIPTION
                "If the terminal has a touch screen, indicates to which port it is attached"
        ::={wbt3Display 5}

-- ****************************************************************************
-- the wbt3DispCharacteristic Group
--
--      The wyse enterprise                    (1.3.6.4.1.714)
--        Product Group                        (1.3.6.4.1.714.1)
--          ThinClient Group                   (1.3.6.4.1.714.1.2)
--            wbt3 Group                       (1.3.6.4.1.714.1.2.3)
--              wbt3Display Group              (1.3.6.4.1.714.1.2.3.4)
--                wbt3DispCharacteristic Group (1.3.6.4.1.714.1.2.3.4.1)
--
-- Implementation of the wbt3DispCharacteristic Group is mandatory for all ThinClient2 products
-- with SNMP agents which supports the wyse MIB
-- ****************************************************************************
wbt3DispFreq  OBJECT-TYPE
        SYNTAX  INTEGER(1..256)
        ACCESS  read-write
        STATUS  mandatory
        DESCRIPTION
                "A 8bit value which indicates the current display frequency in Hz.
				Available display frequency values for Leo: 60/75/85 Hz, 
				for Mars/Midway: 60/75 Hz. 
				wbt3DispFreq can not be set if use DDC is on."
        ::={wbt3DispCharacteristic 1}

wbt3DispHorizPix OBJECT-TYPE
        SYNTAX  INTEGER(1..65535)
        ACCESS  read-write
        STATUS  mandatory
        DESCRIPTION
                "A 16bit value which indicates the current number of horizontal pixels.
				Available display horizontal pixel values 
				for Leo: 640/800/1024/1280 (1280 only with 60 Hz) pixels, 
				for Mars/Midway: 640/800/1024. 
				wbt3DispHorizPix can not be set if use DDC is on."
        ::={wbt3DispCharacteristic 2}

wbt3DispVertPix  OBJECT-TYPE
        SYNTAX  INTEGER(1..65535)
        ACCESS  read-write
        STATUS  mandatory
        DESCRIPTION
                "A 16bit value which indicates the current number of vertical pixels.
				Available display vertical pixel values 
				for Leo: 480/600/768/1024 (1024 only with 60 Hz) pixels, 
				for Mars/Midway: 480/600/768. 
				wbt3DispVertPix can not be set if use DDC is on."
        ::={wbt3DispCharacteristic 3}

wbt3DispColor    OBJECT-TYPE
        SYNTAX  INTEGER
        ACCESS  read-only
        STATUS  mandatory
        DESCRIPTION
                "Current display color depth"
        ::={wbt3DispCharacteristic 4}

wbt3DispUseDDC    OBJECT-TYPE
        SYNTAX  INTEGER {
                        No(0),
                        Yes(1) 
						}
        ACCESS  read-write
        STATUS  mandatory
        DESCRIPTION
                "Automatic select the best available resolution and refresh rate.
				If selected Yes, the wbt3DispHorizPix, wbt3VertPix and wbt3DispFreq
				options can not be set.
				Use DDC is not available for Mars platform."
        ::={wbt3DispCharacteristic 5}

-- ****************************************************************************
-- the wbt3DispCapability Group
--
--      The wyse enterprise                (1.3.6.4.1.714)
--        Product Group                    (1.3.6.4.1.714.1)
--          ThinClient Group               (1.3.6.4.1.714.1.2)
--            wbt3 Group                   (1.3.6.4.1.714.1.2.3)
--              wbt3Display Group          (1.3.6.4.1.714.1.2.3.4)
--                wbt3DispCapability Group (1.3.6.4.1.714.1.2.3.4.2)
--
-- Implementation of the wbt3DispCapability Group is mandatory for all ThinClient2 products
-- with SNMP agents which supports the wyse MIB
-- ****************************************************************************
wbt3DispFreqMax  OBJECT-TYPE
        SYNTAX  INTEGER(1..256)
        ACCESS  read-only
        STATUS  mandatory
        DESCRIPTION
                "A 8bit value which indicates the display frequency in Hz for maximum resolution"
        ::={wbt3DispCapability 1}

wbt3DispHorizPixMax      OBJECT-TYPE
        SYNTAX  INTEGER(1..65535)
        ACCESS  read-only
        STATUS  mandatory
        DESCRIPTION
                "A 16bit value which indicates the maximum number of horizontal pixels"
        ::={wbt3DispCapability 2}

wbt3DispVertPixMax       OBJECT-TYPE
        SYNTAX  INTEGER(1..65535)
        ACCESS  read-only
        STATUS  mandatory
        DESCRIPTION
                "A 16bit value which indicates the maximum number of vertical pixels"
        ::={wbt3DispCapability 3}

wbt3DispColorMax OBJECT-TYPE
        SYNTAX  INTEGER
        ACCESS  read-only
        STATUS  mandatory
        DESCRIPTION
                "Maximum display color depth"
        ::={wbt3DispCapability 4}

-- ****************************************************************************
-- the wbt3DhcpInfo Group
--
--      The wyse enterprise        (1.3.6.4.1.714)
--        Product Group            (1.3.6.4.1.714.1)
--          ThinClient Group       (1.3.6.4.1.714.1.2)
--            wbt3 Group           (1.3.6.4.1.714.1.2.3)
--              wbt3DhcpInfo Group (1.3.6.4.1.714.1.2.3.5)
--
-- Implementation of the wbt3DhcpInfo Group is mandatory for all ThinClient2
-- products with SNMP agents which supports the wyse MIB
-- ****************************************************************************

wbt3DhcpInfoNum  OBJECT-TYPE
        SYNTAX  INTEGER(1..65535)
        ACCESS  read-only
        STATUS  mandatory
        DESCRIPTION
                "The number of entries in DHCP information table, this number equals to the number 
                 of currently initialized network interfaces (exclude loopback) in the terminal"
        ::={wbt3DhcpInfo 1}

wbt3DhcpInfoTable  OBJECT-TYPE
        SYNTAX  SEQUENCE OF wbt3DhcpInfoEntry
        ACCESS  not-accessible
        STATUS  mandatory
        DESCRIPTION
                "A list of DHCP information table entry, Each entry lists the information
                 obtained from DHCP server through a specific network interface in the terminal.
                 The number of entries is given by the value of wbt3DhcpInfoNum"
        ::={wbt3DhcpInfo 2}

-- group in wbt3DhcpInfo
wbt3DHCPoptionIDs      OBJECT IDENTIFIER 	::= {wbt3DhcpInfo 3}

wbt3DhcpInfoEntry  OBJECT-TYPE
        SYNTAX  wbt3DhcpInfoEntry
        ACCESS  not-accessible
        STATUS  mandatory
        DESCRIPTION
                "An interface with a DHCP information table entry on this system"
        INDEX   {wbt3DhcpInfoIndex}
        ::={wbt3DhcpInfoTable 1}
        
wbt3DhcpInfoEntry ::=
        SEQUENCE {
                wbt3DhcpInfoIndex
                INTEGER,
                wbt3InterfaceNum
                INTEGER,
                wbt3ServerIP
                DisplayString,
                wbt3Username1
                DisplayString,
                wbt3Domain
                DisplayString,
                wbt3Password
                INTEGER,
                wbt3CommandLine
                DisplayString,
                wbt3WorkingDir
                DisplayString,
                wbt3FileServer
                DisplayString,
                wbt3FileRootPath
                DisplayString,
                wbt3TrapServerList
                DisplayString,
                wbt3SetCommunity
                INTEGER
        }

wbt3DhcpInfoIndex  OBJECT-TYPE
        SYNTAX  INTEGER
        ACCESS  read-only
        STATUS  mandatory
        DESCRIPTION
                "A unique value for this DHCP information table, Its value ranges
                 between 1 and the value of wbt3DhcpInfoNum."
        ::={wbt3DhcpInfoEntry 1}

wbt3InterfaceNum OBJECT-TYPE
        SYNTAX  INTEGER
        ACCESS  read-only
        STATUS  mandatory
        DESCRIPTION
                "The interface number through which the dhcp info is obtained"
        ::={wbt3DhcpInfoEntry 2}


wbt3ServerIP     OBJECT-TYPE
        SYNTAX  DisplayString
        ACCESS  read-only
        STATUS  mandatory
        DESCRIPTION
                "WinFrame/WTS Server IP address, (Option 155)"
        ::={wbt3DhcpInfoEntry 3}

wbt3Username1   OBJECT-TYPE
        SYNTAX  DisplayString
        ACCESS  read-only
        STATUS  mandatory
        DESCRIPTION
                "Account to logon to WinFrame/WTS Server, (Option 156)"
        ::={wbt3DhcpInfoEntry 4}

wbt3Domain       OBJECT-TYPE
        SYNTAX  DisplayString
        ACCESS  read-only
        STATUS  mandatory
        DESCRIPTION
                "Domain to authenticate account defined by wbt3Username, (Option 157)"
        ::={wbt3DhcpInfoEntry 5}

wbt3Password     OBJECT-TYPE
        SYNTAX  INTEGER {
                        NoPassword(0),
                        Password(1)                }
        ACCESS  read-only
        STATUS  mandatory
        DESCRIPTION
                "0=No Password;1=Has Password, (Option 158)"
        ::={wbt3DhcpInfoEntry 6}

wbt3CommandLine  OBJECT-TYPE
        SYNTAX  DisplayString
        ACCESS  read-only
        STATUS  mandatory
        DESCRIPTION
                "Application to use when connecting to a WinFrame/WTS Server, (Option 159)"
        ::={wbt3DhcpInfoEntry 7}

wbt3WorkingDir   OBJECT-TYPE
        SYNTAX  DisplayString
        ACCESS  read-only
        STATUS  mandatory
        DESCRIPTION
                "Working Directory for application defined by wbt3CommandLine, (Option 160)"
        ::={wbt3DhcpInfoEntry 8}

wbt3FileServer   OBJECT-TYPE
        SYNTAX  DisplayString
        ACCESS  read-only
        STATUS  mandatory
        DESCRIPTION
                "File server where ROM images are located, (Option 161)"
        ::={wbt3DhcpInfoEntry 9}

wbt3FileRootPath OBJECT-TYPE
        SYNTAX  DisplayString
        ACCESS  read-only
        STATUS  mandatory
        DESCRIPTION
                "Absolute path name for ROM image parent directory, (Option 162)"
        ::={wbt3DhcpInfoEntry 10}

wbt3TrapServerList OBJECT-TYPE
        SYNTAX  DisplayString
        ACCESS  read-only
        STATUS  mandatory
        DESCRIPTION
                "A list of host IPs which should receive SNMP trap from the terminal (Option 163)"
        ::={wbt3DhcpInfoEntry 11}

wbt3SetCommunity OBJECT-TYPE
        SYNTAX  INTEGER {
                        Ignored(0),
                        Provided(1),
                        NotProvided(2) }

        ACCESS  read-only
        STATUS  mandatory
        DESCRIPTION
                "SNMP Set Community (Option 164):
                 0 - dhcp supplied set community is ignored,
                     local configuration takes precedence;
                 1 - provided by DHCP server and being used;
                 2 - not provided by DHCP server, default set community is used"
        ::={wbt3DhcpInfoEntry 12}

wbt3RDPstartApp OBJECT-TYPE
        SYNTAX  DisplayString
        ACCESS  read-only
        STATUS  mandatory
        DESCRIPTION
                "RDP option: Startup Application (Default Option 165)"
        ::={wbt3DhcpInfoEntry 13}

wbt3EmulationMode OBJECT-TYPE
        SYNTAX  DisplayString
        ACCESS  read-only
        STATUS  mandatory
        DESCRIPTION
                "Terminal Emulation option: Emulation Mode (Default Option 166)"
        ::={wbt3DhcpInfoEntry 14}

wbt3TerminalID OBJECT-TYPE
        SYNTAX  DisplayString
        ACCESS  read-only
        STATUS  mandatory
        DESCRIPTION
                "Terminal Emulation option: Terminal ID (Default Option 167)"
        ::={wbt3DhcpInfoEntry 15}

wbt3VirtualPortServer OBJECT-TYPE
        SYNTAX  DisplayString
        ACCESS  read-only
        STATUS  mandatory
        DESCRIPTION
                "Virtual Port option: Virtual Port Server (Default Option 168)"
        ::={wbt3DhcpInfoEntry 16}


-- ****************************************************************************
-- the wbt3DHCPoptionIDs Group
--
--      The wyse enterprise					(1.3.6.4.1.714)
--        Product Group						(1.3.6.4.1.714.1)
--          ThinClient Group				(1.3.6.4.1.714.1.2)
--            wbt3 Group					(1.3.6.4.1.714.1.2.3)
--              wbt3DhcpInfo Group			(1.3.6.4.1.714.1.2.3.5)
--                wbt3DHCPoptionIDs Group	(1.3.6.4.1.714.1.2.3.5.3)
--
-- Implementation of the wbt3DhcpInfo Group is mandatory for all ThinClient
-- products with SNMP agents which supports the wyse MIB
-- ****************************************************************************

RemoteServer  OBJECT-TYPE
        SYNTAX  INTEGER(128..254)
        ACCESS  read-write
        STATUS  mandatory
        DESCRIPTION
                "Common option: Remote Server (Default Option 155)"
        ::={wbt3DHCPoptionIDs 1}

LogonUserName  OBJECT-TYPE
        SYNTAX  INTEGER(128..254)
        ACCESS  read-write
        STATUS  mandatory
        DESCRIPTION
                "Common option: Logon User Name (Default Option 156)"
        ::={wbt3DHCPoptionIDs 2}

Domain  OBJECT-TYPE
        SYNTAX  INTEGER(128..254)
        ACCESS  read-write
        STATUS  mandatory
        DESCRIPTION
                "Common option: Domain (Default Option 157)"
        ::={wbt3DHCPoptionIDs 3}

Password  OBJECT-TYPE
        SYNTAX  INTEGER(128..254)
        ACCESS  read-write
        STATUS  mandatory
        DESCRIPTION
                "Common option: Login Password (Default Option 158)"
        ::={wbt3DHCPoptionIDs 4}

CommandLine  OBJECT-TYPE
        SYNTAX  INTEGER(128..254)
        ACCESS  read-write
        STATUS  mandatory
        DESCRIPTION
                "Common option: Command Line (Default Option 159)"
        ::={wbt3DHCPoptionIDs 5}

WorkingDirectory  OBJECT-TYPE
        SYNTAX  INTEGER(128..254)
        ACCESS  read-write
        STATUS  mandatory
        DESCRIPTION
                "Common option: Working Directory (Default Option 160)"
        ::={wbt3DHCPoptionIDs 6}

FTPFileServer  OBJECT-TYPE
        SYNTAX  INTEGER(128..254)
        ACCESS  read-write
        STATUS  mandatory
        DESCRIPTION
                "FTP option: File Server (Default Option 161)"
        ::={wbt3DHCPoptionIDs 8}

FTPRootPath  OBJECT-TYPE
        SYNTAX  INTEGER(128..254)
        ACCESS  read-write
        STATUS  mandatory
        DESCRIPTION
                "FTP option: File Root Path (Default Option 162)"
        ::={wbt3DHCPoptionIDs 9}

TrapServerList  OBJECT-TYPE
        SYNTAX  INTEGER(128..254)
        ACCESS  read-write
        STATUS  mandatory
        DESCRIPTION
                "SNMP option: Trap Server IP List (Default Option 163)"
        ::={wbt3DHCPoptionIDs 10}

SetCommunity  OBJECT-TYPE
        SYNTAX  INTEGER(128..254)
        ACCESS  read-write
        STATUS  mandatory
        DESCRIPTION
                "SNMP option: Set Community (Default Option 164)"
        ::={wbt3DHCPoptionIDs 11}

RDPStartupApp  OBJECT-TYPE
        SYNTAX  INTEGER(128..254)
        ACCESS  read-write
        STATUS  mandatory
        DESCRIPTION
                "RDP option: Startup Application (Default Option 165)"
        ::={wbt3DHCPoptionIDs 7}

EmulationMode  OBJECT-TYPE
        SYNTAX  INTEGER(128..254)
        ACCESS  read-write
        STATUS  mandatory
        DESCRIPTION
                "Terminal Emulation option: Emulation Mode (Default Option 166)"
        ::={wbt3DHCPoptionIDs 12}

TerminalID  OBJECT-TYPE
        SYNTAX  INTEGER(128..254)
        ACCESS  read-write
        STATUS  mandatory
        DESCRIPTION
                "Terminal Emulation option: Terminal ID (Default Option 167)"
        ::={wbt3DHCPoptionIDs 13}

VirtualPortServer  OBJECT-TYPE
        SYNTAX  INTEGER(128..254)
        ACCESS  read-write
        STATUS  mandatory
        DESCRIPTION
                "Virtual Port option: Virtual Port Server (Default Option 168)"
        ::={wbt3DHCPoptionIDs 14}

-- ****************************************************************************
-- the wbt3BuildInfo Group
--
--      The wyse enterprise         (1.3.6.4.1.714)
--        Product Group             (1.3.6.4.1.714.1)
--          ThinClient Group        (1.3.6.4.1.714.1.2)
--            wbt3 Group            (1.3.6.4.1.714.1.2.3)
--              wbt3BuildInfo Group (1.3.6.4.1.714.1.2.3.6)
--
-- Implementation of the wbt3BuildInfo Group is mandatory for all ThinClient2
-- products with SNMP agents which supports the wyse MIB
-- ****************************************************************************

    -- group in wbt3BuildInfo

    wbt3CurrentInfo      OBJECT IDENTIFIER ::= {wbt3BuildInfo 1}
    wbt3DhcpUpdateInfo   OBJECT IDENTIFIER ::= {wbt3BuildInfo 2}

-- ****************************************************************************
-- the wbt3CurrentInfo Group
--
--      The wyse enterprise             (1.3.6.4.1.714)
--        Product Group                 (1.3.6.4.1.714.1)
--          ThinClient Group            (1.3.6.4.1.714.1.2)
--            wbt3 Group                (1.3.6.4.1.714.1.2.3)
--              wbt3BuildInfo Group     (1.3.6.4.1.714.1.2.3.6)
--                wbt3CurrentInfo Group (1.3.6.4.1.714.1.2.3.6.1)
--
-- Implementation of the wbt3CurrentInfo Group is mandatory for all ThinClient2
-- products with SNMP agents which supports the wyse MIB
-- ****************************************************************************

wbt3CurInfoNum   OBJECT-TYPE
        SYNTAX  INTEGER(1..65535)
        ACCESS  read-only
        STATUS  mandatory
        DESCRIPTION
                "Number of rom images reside in the terminal currently, include main & application"
        ::={wbt3CurrentInfo 1}

wbt3CurInfoTable OBJECT-TYPE
        SYNTAX  SEQUENCE OF wbt3CurInfoEntry
        ACCESS  not-accessible
        STATUS  mandatory
        DESCRIPTION
                "A table of build info for each rom image, number of entries
                 is given by the value of wbt3CurInfoNum"
        ::={wbt3CurrentInfo 2}

wbt3CurInfoEntry OBJECT-TYPE
        SYNTAX  wbt3CurInfoEntry
        ACCESS  not-accessible
        STATUS  mandatory
        DESCRIPTION
                "A rom image present in this terminal"
        INDEX   {wbt3CurInfoIndex}
        ::={wbt3CurInfoTable 1}
        
wbt3CurInfoEntry ::=
        SEQUENCE {
                wbt3CurInfoIndex
                INTEGER,
                wbt3CurBuildNum
                DisplayString,
                wbt3CurOEMBuildNum
                DisplayString,
                wbt3CurModBuildDate
                DisplayString,
                wbt3CurOEM
                DisplayString,
                wbt3CurHWPlatform
                DisplayString,
                wbt3CurOS
                DisplayString
        }

wbt3CurInfoIndex OBJECT-TYPE
        SYNTAX  INTEGER
        ACCESS  read-only
        STATUS  mandatory
        DESCRIPTION
                "A unique value for this rom image.  Its value ranges between
                 1 and the value of wbt3CurInfoNum.."
        ::={wbt3CurInfoEntry 1}

wbt3CurBuildNum  OBJECT-TYPE
        SYNTAX  DisplayString
        ACCESS  read-only
        STATUS  mandatory
        DESCRIPTION
                "Build number of a rom image currently on the terminal"
        ::={wbt3CurInfoEntry 2}

wbt3CurOEMBuildNum  OBJECT-TYPE
        SYNTAX  DisplayString
        ACCESS  read-only
        STATUS  mandatory
        DESCRIPTION
                "Build number of flash ROM image currently on the terminal for OEM"
        ::={wbt3CurInfoEntry 3}

wbt3CurModBuildDate OBJECT-TYPE
        SYNTAX  DisplayString
        ACCESS  read-only
        STATUS  mandatory
        DESCRIPTION
                "Date that ROM image currently on the terminal was created"
        ::={wbt3CurInfoEntry 4}

wbt3CurOEM       OBJECT-TYPE
        SYNTAX  DisplayString
        ACCESS  read-only
        STATUS  mandatory
        DESCRIPTION
                "Name of OEM who's ROM image is defined by wbt3OEMBuildNum"
        ::={wbt3CurInfoEntry 5}

wbt3CurHWPlatform OBJECT-TYPE
        SYNTAX  DisplayString
        ACCESS  read-only
        STATUS  mandatory
        DESCRIPTION
                "OS installed on the terminal"
        ::={wbt3CurInfoEntry 6}

wbt3CurOS        OBJECT-TYPE
        SYNTAX  DisplayString
        ACCESS  read-only
        STATUS  mandatory
        DESCRIPTION
                "OS installed on the terminal"
        ::={wbt3CurInfoEntry 7}

-- ****************************************************************************
-- the wbt3DhcpUpdateInfo Group
--
--      The wyse enterprise                (1.3.6.4.1.714)
--        Product Group                    (1.3.6.4.1.714.1)
--          ThinClient Group               (1.3.6.4.1.714.1.2)
--            wbt3 Group                   (1.3.6.4.1.714.1.2.3)
--              wbt3BuildInfo Group        (1.3.6.4.1.714.1.2.3.6)
--                wbt3DhcpUpdateInfo Group (1.3.6.4.1.714.1.2.3.6.2)
--
-- Implementation of the wbt3DhcpUpdateInfo Group is mandatory for all ThinClient2
-- products with SNMP agents which supports the wyse MIB
-- ****************************************************************************

wbt3DUpInfoNum   OBJECT-TYPE
        SYNTAX  INTEGER(1..65535)
        ACCESS  read-only
        STATUS  mandatory
        DESCRIPTION
                "Number of rom images reside in the terminal currently, include main & application"
        ::={wbt3DhcpUpdateInfo 1}

wbt3DUpInfoTable OBJECT-TYPE
        SYNTAX  SEQUENCE OF wbt3DUpInfoEntry
        ACCESS  not-accessible
        STATUS  mandatory
        DESCRIPTION
                "A table of build info for each rom image, number of entries
                 is given by the value of wbt3DUpInfoNum"
        ::={wbt3DhcpUpdateInfo 2}

wbt3DUpInfoEntry OBJECT-TYPE
        SYNTAX  wbt3DUpInfoEntry
        ACCESS  not-accessible
        STATUS  mandatory
        DESCRIPTION
                "A rom image present in this terminal"
        INDEX   {wbt3DUpInfoIndex}
        ::={wbt3DUpInfoTable 1}
        
wbt3DUpInfoEntry ::=
        SEQUENCE {
                wbt3DUpInfoIndex
                INTEGER,
                wbt3DUpBuildNum
                DisplayString,
                wbt3DUpOEMBuildNum
                DisplayString,
                wbt3DUpModBuildDate
                DisplayString
        }

wbt3DUpInfoIndex OBJECT-TYPE
        SYNTAX  INTEGER
        ACCESS  read-only
        STATUS  mandatory
        DESCRIPTION
                "A unique value for this rom image.  Its value ranges between
                 1 and the value of wbt3DUpInfoNum.."
        ::={wbt3DUpInfoEntry 1}

wbt3DUpBuildNum  OBJECT-TYPE
        SYNTAX  DisplayString
        ACCESS  read-only
        STATUS  mandatory
        DESCRIPTION
                "Build number of the updated ROM image"
        ::={wbt3DUpInfoEntry 2}

wbt3DUpOEMBuildNum OBJECT-TYPE
        SYNTAX  DisplayString
        ACCESS  read-only
        STATUS  mandatory
        DESCRIPTION
                "Build number of the updated ROM image for OEM"
        ::={wbt3DUpInfoEntry 3}

wbt3DUpModBuildDate OBJECT-TYPE
        SYNTAX  DisplayString
        ACCESS  read-only
        STATUS  mandatory
        DESCRIPTION
                "Date that update image was last modified"
        ::={wbt3DUpInfoEntry 4}

wbt3DUpOEMBuildDate OBJECT-TYPE
        SYNTAX  DisplayString
        ACCESS  read-only
        STATUS  mandatory
        DESCRIPTION
                "Date that update image was last modified for OEM"
        ::={wbt3DUpInfoEntry 5}


-- ****************************************************************************
-- the wbt3CustomFields Group
--
--      The wyse enterprise            (1.3.6.4.1.714)
--        Product Group                (1.3.6.4.1.714.1)
--          ThinClient Group           (1.3.6.4.1.714.1.2)
--            wbt3 Group               (1.3.6.4.1.714.1.2.3)
--              wbt3CustomFields Group (1.3.6.4.1.714.1.2.3.7)
--
-- Implementation of the wbt3CustomFields Group is mandatory for all ThinClient2
-- products with SNMP agents which supports the wyse MIB
-- ****************************************************************************

wbt3CustomField1 OBJECT-TYPE
        SYNTAX  DisplayString
        ACCESS  read-write
        STATUS  mandatory
        DESCRIPTION
                "First custom field"
        ::={wbt3CustomFields 1}

wbt3CustomField2 OBJECT-TYPE
        SYNTAX  DisplayString
        ACCESS  read-write
        STATUS  mandatory
        DESCRIPTION
                "Second custom field"
        ::={wbt3CustomFields 2}

wbt3CustomField3 OBJECT-TYPE
        SYNTAX  DisplayString
        ACCESS  read-write
        STATUS  mandatory
        DESCRIPTION
                "Third custom field"
        ::={wbt3CustomFields 3}

-- ****************************************************************************
-- the wbt3Administration Group
--
--      The wyse enterprise              (1.3.6.4.1.714)
--        Product Group                  (1.3.6.4.1.714.1)
--          ThinClient Group             (1.3.6.4.1.714.1.2)
--            wbt3 Group                 (1.3.6.4.1.714.1.2.3)
--              wbt3Administration Group (1.3.6.4.1.714.1.2.3.8)
--
-- Implementation of the wbt3Administration Group is mandatory for all ThinClient2
-- products with SNMP agents which supports the wyse MIB
-- ****************************************************************************

    -- group in wbt3Administration

    wbt3UpDnLoad      OBJECT IDENTIFIER ::= {wbt3Administration 1}
    wbt3Action        OBJECT IDENTIFIER ::= {wbt3Administration 2}
	wbt3FTPsetting    OBJECT IDENTIFIER ::= {wbt3Administration 3}

	wbt3SNMPupdate    OBJECT-TYPE
		SYNTAX  INTEGER {
                        No(0),
                        Yes(1) 
						}
        ACCESS  read-write
        STATUS  mandatory
        DESCRIPTION
                "Terminal firmware upgrade using SNMP.
				 Yes = SNMP update enable,
				 No  = SNMP update disable."
		::={wbt3Administration 4}

	wbt3DHCPupdate    OBJECT-TYPE
        SYNTAX  INTEGER {
                        No(0),
                        Yes(1) 
						}
        ACCESS  read-write
        STATUS  mandatory
        DESCRIPTION
                "Terminal firmware upgrade using DHCP.
				 Yes = DHCP automatic update enable,
				 No  = DHCP automatic update disable."
        ::={wbt3Administration 5}

-- ****************************************************************************
-- the wbt3UpDnLoad Group
--
--      The wyse enterprise               (1.3.6.4.1.714)
--        Product Group                   (1.3.6.4.1.714.1)
--          ThinClient Group              (1.3.6.4.1.714.1.2)
--            wbt3 Group                  (1.3.6.4.1.714.1.2.3)
--              wbt3Administration Group  (1.3.6.4.1.714.1.2.3.8)
--                wbt3UpDnLoad Group      (1.3.6.4.1.714.1.2.3.8.1)
--
-- Implementation of the wbt3UpDnLoad Group is mandatory for all ThinClient2
-- products with SNMP agents which supports the wyse MIB
-- ****************************************************************************

wbt3UpDnLoadNum  OBJECT-TYPE
        SYNTAX  INTEGER(1..65535)
        ACCESS  read-write
        STATUS  mandatory
        DESCRIPTION
                "The number of entries in the Up/Download table,
                 Maximum value is 5"
        ::={wbt3UpDnLoad 1}

wbt3UpDnLoadTable OBJECT-TYPE
        SYNTAX  SEQUENCE OF wbt3UpDnLoadEntry
        ACCESS  not-accessible
        STATUS  mandatory
        DESCRIPTION
                "A list of files to be upload or download"
        ::={wbt3UpDnLoad 2}

wbt3AcceptReq    OBJECT-TYPE
        SYNTAX  INTEGER {
                        No(0),
                        Yes(1)                }
        ACCESS  read-write
        STATUS  mandatory
        DESCRIPTION
                "Indicate whether ThinClient is ready to accept SNMP up/down load request"
        ::={wbt3UpDnLoad 3}


wbt3SubmitLoadJob OBJECT-TYPE
        SYNTAX  INTEGER {
                        NotReady(0),
                        Ready(1)                }
        ACCESS  read-write
        STATUS  mandatory
        DESCRIPTION
                "Setting this object to Ready(1) will kick off the up/download process
                 specified in wbt3UpDnLoadTable"
        ::={wbt3UpDnLoad 4}


wbt3UpDnLoadEntry OBJECT-TYPE
        SYNTAX  wbt3UpDnLoadEntry
        ACCESS  not-accessible
        STATUS  mandatory
        DESCRIPTION
                "An upload or download request entry from server"
        INDEX   {wbt3UpDnLoadIndex}
        ::={wbt3UpDnLoadTable 1}
        
wbt3UpDnLoadEntry ::=
        SEQUENCE {
                wbt3UpDnLoadIndex
                INTEGER,
                wbt3UpDnLoadId
                DisplayString,
                wbt3UpDnLoadOp
                INTEGER,
                wbt3UpDnLoadSrcFile
                DisplayString,
                wbt3UpDnLoadDstFile
                DisplayString,
                wbt3UpDnLoadFileType
                DisplayString,
                wbt3UpDnLoadProtocol
                INTEGER,
                wbt3UpDnLoadFServer
                DisplayString,
                wbt3UpDnLoadTimeFlag
                INTEGER
        }

wbt3UpDnLoadIndex OBJECT-TYPE
        SYNTAX  INTEGER
        ACCESS  read-write
        STATUS  mandatory
        DESCRIPTION
                "A unique value for the request entry.  Its value
		     ranges between 1 and the value of wbt3UpDnLoadNum."
        ::={wbt3UpDnLoadEntry 1}

wbt3UpDnLoadId   OBJECT-TYPE
        SYNTAX  DisplayString
        ACCESS  read-write
        STATUS  mandatory
        DESCRIPTION
                "An id number for this up/download request.
 	           This number is used to match with WBT private trap which
		     will be sent to the server upon done with this up/download request."
        ::={wbt3UpDnLoadEntry 2}

wbt3UpDnLoadOp   OBJECT-TYPE
        SYNTAX  INTEGER {
                        Upload(0),
                        Download(1)                }
        ACCESS  read-write
        STATUS  mandatory
        DESCRIPTION
                "0=an upload request;1=a download request"
        ::={wbt3UpDnLoadEntry 3}

wbt3UpDnLoadSrcFile OBJECT-TYPE
        SYNTAX  DisplayString
        ACCESS  read-write
        STATUS  mandatory
        DESCRIPTION
                "The path and file name for source file to be up/downloaded."
        ::={wbt3UpDnLoadEntry 4}

wbt3UpDnLoadDstFile OBJECT-TYPE
        SYNTAX  DisplayString
        ACCESS  read-write
        STATUS  mandatory
        DESCRIPTION
                "The path and file name where the up/downloaded file will be stored."
        ::={wbt3UpDnLoadEntry 5}

wbt3UpDnLoadFileType OBJECT-TYPE
        SYNTAX  INTEGER {
                        Binary(0),
                        ASCII(1)                }
        ACCESS  read-write
        STATUS  mandatory
        DESCRIPTION
                "0=binary;1=ascii"
        ::={wbt3UpDnLoadEntry 6}

wbt3UpDnLoadProtocol OBJECT-TYPE
        SYNTAX  INTEGER {
                        ftp(0),
						tftp(1)
						}
        ACCESS  read-write
        STATUS  mandatory
        DESCRIPTION
                "0=ftp, 1=tftp"
        ::={wbt3UpDnLoadEntry 7}

wbt3UpDnLoadFServer OBJECT-TYPE
        SYNTAX  DisplayString
        ACCESS  read-write
        STATUS  mandatory
        DESCRIPTION
                "The file server IP address (or name) to/from which the file is up/downloaded."
        ::={wbt3UpDnLoadEntry 8}

wbt3UpDnLoadTimeFlag OBJECT-TYPE
        SYNTAX  INTEGER {
                        Immediate(0)                }
        ACCESS  read-write
        STATUS  mandatory
        DESCRIPTION
                "0=execute request immediately"
        ::={wbt3UpDnLoadEntry 9}

-- ****************************************************************************
-- the wbt3Action Group
--
--      The wyse enterprise               (1.3.6.4.1.714)
--        Product Group                   (1.3.6.4.1.714.1)
--          ThinClient Group              (1.3.6.4.1.714.1.2)
--            wbt3 Group                  (1.3.6.4.1.714.1.2.3)
--              wbt3Administration Group  (1.3.6.4.1.714.1.2.3.8)
--                wbt3Action Group        (1.3.6.4.1.714.1.2.3.8.2)
--
-- Implementation of the wbt3Action Group is mandatory for all ThinClient2
-- ****************************************************************************

wbt3RebootRequest  OBJECT-TYPE
        SYNTAX  INTEGER {
                        NoReboot(0),
                        RebootNow(1)                }
        ACCESS  read-write
        STATUS  mandatory
        DESCRIPTION
                "Set this object to RebootNow to kick off a reboot on the thinclient"
        ::={wbt3Action 1}

wbt3ResetToFactoryDefault  OBJECT-TYPE
        SYNTAX  INTEGER {
                        NoReset(0),
                        ResetNow(1)                }
        ACCESS  read-write
        STATUS  mandatory
        DESCRIPTION
                "Reset the terminal to factory-default settings. 
				The terminal will be reboot after ResetNow is set."
        ::={wbt3Action 2}


-- ****************************************************************************
-- the wbt3FTPsetting Group
--
--      The wyse Group						(1.3.6.4.1.714)
--        Product Group						(1.3.6.4.1.714.1)
--          ThinClient Group				(1.3.6.4.1.714.1.2)
--            wbt3 Group					(1.3.6.4.1.714.1.2.3)
--              wbt3Administration Group	(1.3.6.4.1.714.1.2.3.8)
--                wbt3FTPsetting Group		(1.3.6.4.1.714.1.2.3.8.3)
--
-- Implementation of the wbt3FTPsetting Group is mandatory for all ThinClient2
-- ****************************************************************************

wbt3ServerName   OBJECT-TYPE
        SYNTAX  DisplayString
        ACCESS  read-write
        STATUS  mandatory
        DESCRIPTION
				"File server name or IP address where the ROM images are located."
        ::={wbt3FTPsetting 1}

wbt3Directory   OBJECT-TYPE
        SYNTAX  DisplayString
        ACCESS  read-write
        STATUS  mandatory
        DESCRIPTION
				"Directory where the ROM images are located."
        ::={wbt3FTPsetting 2}

wbt3UserID   OBJECT-TYPE
        SYNTAX  DisplayString
        ACCESS  read-write
        STATUS  mandatory
        DESCRIPTION
				"User identification to login to the file server."
        ::={wbt3FTPsetting 3}

wbt3Password2   OBJECT-TYPE
        SYNTAX  DisplayString
        ACCESS  read-write
        STATUS  mandatory
        DESCRIPTION
				"User password to login to the file server."
        ::={wbt3FTPsetting 4}

wbt3SavePassword	OBJECT-TYPE
        SYNTAX  INTEGER {
                        No(0),
                        Yes(1) 
						}
        ACCESS  read-write
        STATUS  mandatory
        DESCRIPTION
                "Yes = to save the password permanently,
				 No = do not save the password."
        ::={wbt3FTPsetting 5}

wbt3InfoLocation	OBJECT-TYPE
        SYNTAX  INTEGER {
                        UseLocalinfo(0),
                        UseDHCPinfo(1)
						}
        ACCESS  read-write
        STATUS  mandatory
        DESCRIPTION
                "UseDHCPinfo  = ServerName and Directory will be provided by DHCP server,
				 UseLocalinfo = ServerName and Directory will be provided using local settings."
        ::={wbt3FTPsetting 6}


	wbt3Security         OBJECT IDENTIFIER ::= {wbt3Administration 7}

-- ****************************************************************************
-- the wbt3Security Group
--
--      The wyse enterprise               (1.3.6.4.1.714)
--        Product Group                   (1.3.6.4.1.714.1)
--          ThinClient Group              (1.3.6.4.1.714.1.2)
--            wbt3 Group                  (1.3.6.4.1.714.1.2.3)
--              wbt3Administration Group  (1.3.6.4.1.714.1.2.3.8)
--                wbt3Security Group		  (1.3.6.4.1.714.1.2.3.8.7)
--
-- Implementation of the wbt3Security Group is mandatory for all wbt3
-- products with SNMP agents which supports the hpWinTerm MIB
-- ****************************************************************************

wbt3SecurityEnable  OBJECT-TYPE
        SYNTAX  INTEGER {
                        No(0),
                        Yes(1)                
						}
        ACCESS  read-write
        STATUS  mandatory
        DESCRIPTION
                "This group box is used to enable terminal security and connection configuration access.
				 selecting enable terminal security, and deactivate the Hide Configure Tab function. 
				 By default this function is disabled"
        ::={wbt3Security 1}

wbt3HideConfigTab  OBJECT-TYPE
        SYNTAX  INTEGER {
                        No(0),
                        Yes(1)                
						}
        ACCESS  read-write
        STATUS  mandatory
        DESCRIPTION
                "This function hides the Configure tab in the Winterm Connections Manager. 
				By default this function is not activated."
        ::={wbt3Security 2}

wbt3FailOverEnable  OBJECT-TYPE
        SYNTAX  INTEGER {
                        No(0),
                        Yes(1)                
						}
        ACCESS  read-write
        STATUS  mandatory
        DESCRIPTION
                "Failover is a connection feature that is enabled using the Security properties sheet.
				Disabling this function activates the PingBeforeConnect function. 
				By default this function is enabled."
        ::={wbt3Security 3}

wbt3MultipleConnect  OBJECT-TYPE
        SYNTAX  INTEGER {
                        No(0),
                        Yes(1)                
						}
        ACCESS  read-write
        STATUS  mandatory
        DESCRIPTION
                "Allow multiple connections.
				Select Yes to enable. By default this function is disabled."
        ::={wbt3Security 4}

wbt3PingBeforeConnect  OBJECT-TYPE
        SYNTAX  INTEGER {
                        No(0),
                        Yes(1)                
						}
        ACCESS  read-write
        STATUS  mandatory
        DESCRIPTION
                "Select Yes to enable. By default this function is deactivated.
				When FailOver is checked, PingBeforeConnect is grayed out, 
				since it is implied that Ping is always performed before 
				a connection is made."
        ::={wbt3Security 5}

wbt3Verbose  OBJECT-TYPE
        SYNTAX  INTEGER {
                        No(0),
                        Yes(1)                
						}
        ACCESS  read-write
        STATUS  mandatory
        DESCRIPTION
                "Select Yes to enable the Verbose connection function. By default the box is disabled.
				During the FailOver operation, user can see the status via a log window 
				by checking the Verbose checkbox.  
				The log window will show everything from first connection onward."
        ::={wbt3Security 6}

wbt3AutoLoginEnable  OBJECT-TYPE
        SYNTAX  INTEGER {
                        No(0),
                        Yes(1)                
						}
        ACCESS  read-write
        STATUS  mandatory
        DESCRIPTION
                "The AutoLogin function is an automatic login function that does not use 
				a dialog box as a prompt to log you back into your terminal. 
				Whether you restart or log off, the AutoLogin dialog box displays, 
				counts five seconds, then returns you to the Winterm Connections Manager. "
        ::={wbt3Security 7}

wbt3AutoLoginUserName  OBJECT-TYPE
        SYNTAX  DisplayString
        ACCESS  read-write
        STATUS  mandatory
        DESCRIPTION
                "This field is activated by enabling AutoLogin Enable. 
				By default the field is blank."
        ::={wbt3Security 8}

wbt3SingleButtonConnect  OBJECT-TYPE
        SYNTAX  INTEGER {
                        No(0),
                        Yes(1)                
						}
        ACCESS  read-write
        STATUS  mandatory
        DESCRIPTION
                "Select Yes to enable the function. By default the function is not activated."
        ::={wbt3Security 9}

wbt3AutoFailRecovery  OBJECT-TYPE
        SYNTAX  INTEGER {
                        No(0),
                        Yes(1)                
						}
        ACCESS  read-write
        STATUS  mandatory
        DESCRIPTION
                "Select Yes to enable the function. By default the function is activated."
        ::={wbt3Security 10}


-- ****************************************************************************
-- the wbt3TrapsInfo Group
--
--      The wyse enterprise         (1.3.6.4.1.714)
--        Product Group             (1.3.6.4.1.714.1)
--          ThinClient Group        (1.3.6.4.1.714.1.2)
--            wbt3 Group            (1.3.6.4.1.714.1.2.3)
--              wbt3TrapsInfo Group (1.3.6.4.1.714.1.2.3.9)
--
-- Implementation of the wbt3TrapsInfo Group is mandatory for all ThinClient2
-- products with SNMP agents which supports the wyse MIB
-- ****************************************************************************

wbt3TrapStatus   OBJECT-TYPE
        SYNTAX  INTEGER {
                        LS_DONE(0),
                        LS_DONE_SAMEVERSION(1),
                        LS_NOTREADY(2),
                        LS_FAIL_SHUTDOWN(3),
                        LS_FAIL_NOUPD(4),
                        LS_FAIL_DNLD_BLOCKED(5),
                        LS_FAIL_FILENOTFOUND(6),
                        LS_FAIL_DIR(7),
                        LS_FAIL_UPLD_BLOCKED(8),
                        LS_FAIL_NOSERV(9),
                        LS_FAIL_PROT(10),
                        LS_FAIL_NOMEM(11),
                        LS_FAIL_NORESOURCE(12),
                        LS_FAIL_RESOLVENAME(13), 
						LS_FAIL_NOTBUNDLE(14),
						LS_FAIL_CHECKSUM(15),
						LS_FAIL_FLASHERROR(16),
						LS_FAIL_DNLD_FLASH(17),
						LS_FAIL_USERCANCEL(18),
                        LS_FAIL_NORFLASH(19),
                        LS_FAIL_PROTNSUPPORT(20),
                        LS_FAIL_PARSEREG(21),
                        LS_FAIL_PARSEREG_VERINCOMP(22),
                        LS_FAIL_PARSEREG_PLATFINCOMP(23),
                        LS_FAIL_PARSEREG_OSINCOMP(24),
                        LS_FAIL_RESET_DEFAULTFACTORY(25),
						LS_FAIL_PARAMINIFILENOTFOUND(26),
						LS_INVALID_BOOTSTRAP(27),
						LS_FAIL_BADKEY(28)
						}

        ACCESS  read-only
        STATUS  mandatory
        DESCRIPTION
                "Current trap status information."
        ::={wbt3TrapsInfo 1}

wbt3TrapReqId    OBJECT-TYPE
        SYNTAX  DisplayString
        ACCESS  read-only
        STATUS  mandatory
        DESCRIPTION
                "The SNMP up/down load request Id associated with current trap"
        ::={wbt3TrapsInfo 2}

wbt3TrapServers	OBJECT IDENTIFIER ::= {wbt3TrapsInfo 3}

-- ****************************************************************************
-- the wbt3TrapServers Group
--
--      The wyse enterprise				(1.3.6.4.1.714)
--        Product Group					(1.3.6.4.1.714.1)
--          ThinClient Group			(1.3.6.4.1.714.1.2)
--            wbt3 Group				(1.3.6.4.1.714.1.2.3)
--              wbt3TrapsInfo Group		(1.3.6.4.1.714.1.2.3.9)
--				 wbt3TrapServers Group	(1.3.6.4.1.714.1.2.3.9.3)
--
-- Implementation of the wbt3TrapServers Group is mandatory for all wbt3
-- ****************************************************************************

wbt3TrapServer1   OBJECT-TYPE
        SYNTAX  DisplayString
        ACCESS  read-write
        STATUS  mandatory
        DESCRIPTION
				"Server name or IP address where the trap messages will be sent."
        ::={wbt3TrapServers 1}

wbt3TrapServer2   OBJECT-TYPE
        SYNTAX  DisplayString
        ACCESS  read-write
        STATUS  mandatory
        DESCRIPTION
				"Server name or IP address where the trap messages will be sent."
        ::={wbt3TrapServers 2}

wbt3TrapServer3   OBJECT-TYPE
        SYNTAX  DisplayString
        ACCESS  read-write
        STATUS  mandatory
        DESCRIPTION
				"Server name or IP address where the trap messages will be sent."
        ::={wbt3TrapServers 3}

wbt3TrapServer4   OBJECT-TYPE
        SYNTAX  DisplayString
        ACCESS  read-write
        STATUS  mandatory
        DESCRIPTION
				"Server name or IP address where the trap messages will be sent."
        ::={wbt3TrapServers 4}

-- ****************************************************************************
-- the MibRev group
--
--      The wyse enterprise      (1.3.6.4.1.714)
--        Product Group             (1.3.6.4.1.714.1)
--          ThinClient Group        (1.3.6.4.1.714.1.2)
--            wbt3 Group             (1.3.6.4.1.714.1.2.3)
--             wbt3MibRev Group  (1.3.6.4.1.714.1.2.3.10)
--
-- Implementation of the wbt3MibRev group is mandatory for all SNMP agents supporting
-- the wyse MIB
-- 
-- An SNMP agent conforming to this document will return 
-- a wbt3MibRevMajor of one(1) and a wbt3MibRevMinor of eight(8)
-- ****************************************************************************

wbt3MibRevMajor   OBJECT-TYPE
        SYNTAX  INTEGER(1..65535)
        ACCESS  read-only
        STATUS  mandatory
        DESCRIPTION
                "The major revision level of the MIB
		 The number for current version."
        ::={wbt3MibRev 1}

wbt3MibRevMinor   OBJECT-TYPE
        SYNTAX  INTEGER(1..65535)
        ACCESS  read-only
        STATUS  mandatory
        DESCRIPTION
                "The minor revision level of the MIB
		 The number for current version is 8."
        ::={wbt3MibRev 2}

-- ****************************************************************************
-- the wbt3Network group
--
--      The wyse enterprise			(1.3.6.4.1.714)
--        Product Group             (1.3.6.4.1.714.1)
--          ThinClient Group        (1.3.6.4.1.714.1.2)
--            wbt3 Group            (1.3.6.4.1.714.1.2.3)
--             wbt3Network Group	(1.3.6.4.1.714.1.2.3.11)
--
-- Implementation of the wbt3Network Group is mandatory for all ThinClient2
-- ****************************************************************************

wbt3NetworkNum   OBJECT-TYPE
        SYNTAX  INTEGER(1..65535)
        ACCESS  read-only
        STATUS  mandatory
        DESCRIPTION
                "The number of entries in the Network table."
        ::={wbt3Network 1}

wbt3NetworkTable OBJECT-TYPE
        SYNTAX  SEQUENCE OF wbt3NetworkEntry
        ACCESS  not-accessible
        STATUS  mandatory
        DESCRIPTION
                "A table of network configuration, number of entries
                 is given by the value of wbt3NetworkNum."
        ::={wbt3Network 2}

wbt3NetworkEntry OBJECT-TYPE
        SYNTAX  wbt3NetworkEntry
        ACCESS  not-accessible
        STATUS  mandatory
        DESCRIPTION
                "A Network configuration presents in this terminal."
        INDEX   {wbt3NetworkIndex}
        ::={wbt3NetworkTable 1}
        
wbt3NetworkEntry ::=
        SEQUENCE {
                wbt3NetworkIndex
                INTEGER,
                wbt3DHCPEnable
                INTEGER,
				wbt3NetworkAddress
                DisplayString,
				wbt3SubnetMask
                DisplayString,
				wbt3Gateway
                DisplayString,
                wbt3dnsEnable
				INTEGER,
				wbt3defaultDomain
				DisplayString,
				wbt3primaryDNSserverIPaddress
				DisplayString,
				wbt3secondaryDNSserverIPaddress
				DisplayString,
				wbt3winsEnable
				INTEGER,
				wbt3primaryWINSserverIPaddress
				DisplayString,
				wbt3secondaryWINSserverIPaddress
				DisplayString,
				wbt3NetworkSpeed
				INTEGER,
				wbt3NetworkProtocol
				INTEGER	
        }

wbt3NetworkIndex OBJECT-TYPE
        SYNTAX  INTEGER
        ACCESS  read-only
        STATUS  mandatory
        DESCRIPTION
                "A unique value for the request entry. Its value
				ranges between 1 and the value of wbt3NetworkIndex."
        ::={wbt3NetworkEntry 1}

wbt3dhcpEnable  OBJECT-TYPE
        SYNTAX  INTEGER {
                        No(0),
                        Yes(1) 
						}
        ACCESS  read-write
        STATUS  mandatory
        DESCRIPTION
                "Indicates whether the terminal acquires its network parameters
				 through DHCP or uses the static parameters provided."
        ::={wbt3NetworkEntry 2}

wbt3NetworkAddress OBJECT-TYPE
        SYNTAX  DisplayString
        ACCESS  read-write
        STATUS  mandatory
        DESCRIPTION
                "IP address persents in this terminal."
        ::={wbt3NetworkEntry 3}

wbt3SubnetMask OBJECT-TYPE
        SYNTAX  DisplayString
        ACCESS  read-write
        STATUS  mandatory
        DESCRIPTION
                "Subnet Mask presents in this terminal."
        ::={wbt3NetworkEntry 4}

wbt3Gateway OBJECT-TYPE
        SYNTAX  DisplayString
        ACCESS  read-write
        STATUS  mandatory
        DESCRIPTION
                "Default gateway IP address."
        ::={wbt3NetworkEntry 5}

wbt3dnsEnable  OBJECT-TYPE
        SYNTAX  INTEGER {
                        No(0),
                        Yes(1) 
						}
        ACCESS  read-write
        STATUS  mandatory
        DESCRIPTION
                "Indicates whether the terminal uses DNS to translate names to IP addresses."
        ::={wbt3NetworkEntry 6}

wbt3defaultDomain OBJECT-TYPE
        SYNTAX  DisplayString
        ACCESS  read-write
        STATUS  mandatory
        DESCRIPTION
                "Indicates the domain in which the terminal belongs."
        ::={wbt3NetworkEntry 7}

wbt3primaryDNSserverIPaddress OBJECT-TYPE
        SYNTAX  DisplayString
        ACCESS  read-write
        STATUS  mandatory
        DESCRIPTION
                "The IP address of the primary name server."
        ::={wbt3NetworkEntry 8}

wbt3secondaryDNSserverIPaddress OBJECT-TYPE
        SYNTAX  DisplayString
        ACCESS  read-write
        STATUS  mandatory
        DESCRIPTION
                "The IP address of the secondary name server."
        ::={wbt3NetworkEntry 9}

wbt3winsEnable  OBJECT-TYPE
        SYNTAX  INTEGER {
                        No(0),
                        Yes(1) 
						}
        ACCESS  read-write
        STATUS  mandatory
        DESCRIPTION
                "Indicates whether the terminal uses WINS to resolve to IP addresses."
        ::={wbt3NetworkEntry 10}

wbt3primaryWINSserverIPaddress OBJECT-TYPE
        SYNTAX  DisplayString
        ACCESS  read-write
        STATUS  mandatory
        DESCRIPTION
                "The IP address of the primary name server."
        ::={wbt3NetworkEntry 11}

wbt3secondaryWINSserverIPaddress OBJECT-TYPE
        SYNTAX  DisplayString
        ACCESS  read-write
        STATUS  mandatory
        DESCRIPTION
                "The IP address of the secondary name server."
        ::={wbt3NetworkEntry 12}

wbt3NetworkSpeed   OBJECT-TYPE
        SYNTAX  INTEGER {
                         Auto-Detect(0),
						 HalfDuplex-10Mbs(9),
						 FullDuplex-10Mbs(8),
						 HalfDuplex-100Mbs(7),
						 FullDuplex-100Mbs(6)
						 }
        ACCESS  read-write
        STATUS  mandatory
        DESCRIPTION
                "Indicates the Network speed connection.(Not available for Mars)"
        ::={wbt3NetworkEntry 17}

wbt3NetworkProtocol OBJECT-TYPE
        SYNTAX  INTEGER {
                        TCP-IP(0),
						Unknown(256)
						}
        ACCESS  read-only
        STATUS  mandatory
        DESCRIPTION
                "Indicates network protocol used."
        ::={wbt3NetworkEntry 20}


-- ****************************************************************************
-- the wbt3Apps group
--
--      The wyse enterprise			(1.3.6.4.1.714)
--        Product Group             (1.3.6.4.1.714.1)
--          ThinClient Group        (1.3.6.4.1.714.1.2)
--            wbt3 Group            (1.3.6.4.1.714.1.2.3)
--             wbt3Apps Group		(1.3.6.4.1.714.1.2.3.12)
--
-- Implementation of the wbt3Apps Group is mandatory for all ThinClient2
-- ****************************************************************************
wbt3RDPencryption   OBJECT-TYPE
        SYNTAX  INTEGER {
                        Enable(0),
                        Disable(1)
						}
        ACCESS  read-write
        STATUS  mandatory
        DESCRIPTION
                "To enable/disable the RPD encryption."
        ::={wbt3Apps 1}

wbt3VirtualPortServerIPaddress   OBJECT-TYPE
        SYNTAX  DisplayString
        ACCESS  read-write
        STATUS  mandatory
        DESCRIPTION
                "Specify the virtual port server address."
        ::={wbt3Apps 2}

wbt3com1Share   OBJECT-TYPE
        SYNTAX  INTEGER {
                        Yes(0),
                        No(1)
						}
        ACCESS  read-write
        STATUS  mandatory
        DESCRIPTION
                "To enable/disable COM1 share."
        ::={wbt3Apps 3}

wbt3com2Share   OBJECT-TYPE
        SYNTAX  INTEGER {
                        Yes(0),
                        No(1)
						}
        ACCESS  read-write
        STATUS  mandatory
        DESCRIPTION
                "To enable/disable COM2 share."
        ::={wbt3Apps 4}

wbt3parallelShare   OBJECT-TYPE
        SYNTAX  INTEGER {
                        Yes(0),
                        No(1)
						}
        ACCESS  read-write
        STATUS  mandatory
        DESCRIPTION
                "To enable/disable parallel share port."
        ::={wbt3Apps 5}

ICADefaultHotkeys   OBJECT-TYPE
        SYNTAX  SEQUENCE OF DefaultHotkeysEntry
        ACCESS  not-accessible
        STATUS  mandatory
        DESCRIPTION
                "ICA Client Default HotKeys settings."
        ::={wbt3Apps 6}

DefaultHotkeysEntry  OBJECT-TYPE
        SYNTAX  DefaultHotkeysEntry
        ACCESS  not-accessible
        STATUS  mandatory
        DESCRIPTION
                "Default HotKeys entry."
        ::={ICADefaultHotkeys 1}
        
DefaultHotkeysEntry ::=
        SEQUENCE {
                ICAStatusDialog
                INTEGER,
                ICAStatusDialog2
                INTEGER,
				ICACloseRemoteApplication
                INTEGER,
				ICACloseRemoteApplication2
                INTEGER,
                ICAtoggleTitleBar
				INTEGER,
				ICAtoggleTitleBar2
				INTEGER,
                ICActrlAltDel
				INTEGER,
				ICActrlAltDel2
				INTEGER,
				ICActrlEsc
				INTEGER,
				ICActrlEsc2
				INTEGER,
				ICAaltEsc
				INTEGER,
				ICAaltEsc2
				INTEGER,
				ICAaltTab
				INTEGER,
				ICAaltTab2
				INTEGER,
				ICAaltBackTab
				INTEGER,
				ICAaltBackTab2
				INTEGER
        }

ICAStatusDialog  OBJECT-TYPE
        SYNTAX  INTEGER {
		                Ctrl(0),
						Shift(1)
						}
        ACCESS  read-write
        STATUS  mandatory
        DESCRIPTION
                "ICAStatusDialog"
        ::={DefaultHotkeysEntry 1}

ICAStatusDialog2  OBJECT-TYPE
        SYNTAX  INTEGER {	Key0(0),
							Key1(1),
							Key2(2),
							Key3(3),
							Key4(4),
							Key5(5),
							Key6(6),
							Key7(7),
							Key8(8),
							Key9(9) }
        ACCESS  read-write
        STATUS  mandatory
        DESCRIPTION
                "ICAStatusDialog"
        ::={DefaultHotkeysEntry 2}

ICACloseRemoteApplication  OBJECT-TYPE
        SYNTAX  INTEGER {
		                Ctrl(0),
						Shift(1)
						}
        ACCESS  read-write
        STATUS  mandatory
        DESCRIPTION
                "ICAStatusDialog"
        ::={DefaultHotkeysEntry 3}

ICACloseRemoteApplication2  OBJECT-TYPE
        SYNTAX  INTEGER {	Key0(0),
							Key1(1),
							Key2(2),
							Key3(3),
							Key4(4),
							Key5(5),
							Key6(6),
							Key7(7),
							Key8(8),
							Key9(9) }
		ACCESS  read-write
        STATUS  mandatory
        DESCRIPTION
                "ICAStatusDialog"
        ::={DefaultHotkeysEntry 4}

ICAtoggleTitleBar  OBJECT-TYPE
        SYNTAX  INTEGER {
		                Ctrl(0),
						Shift(1)
						}
        ACCESS  read-write
        STATUS  mandatory
        DESCRIPTION
                "ICAStatusDialog"
        ::={DefaultHotkeysEntry 5}

ICAtoggleTitleBar2  OBJECT-TYPE
        SYNTAX  INTEGER {	Key0(0),
							Key1(1),
							Key2(2),
							Key3(3),
							Key4(4),
							Key5(5),
							Key6(6),
							Key7(7),
							Key8(8),
							Key9(9) }
        ACCESS  read-write
        STATUS  mandatory
        DESCRIPTION
                "ICAStatusDialog"
        ::={DefaultHotkeysEntry 6}

ICActrlAltDel  OBJECT-TYPE
        SYNTAX  INTEGER {
		                Ctrl(0)
						}
        ACCESS  read-write
        STATUS  mandatory
        DESCRIPTION
                "ICAStatusDialog"
        ::={DefaultHotkeysEntry 7}

ICActrlAltDel2  OBJECT-TYPE
        SYNTAX  INTEGER {	Key0(0),
							Key1(1),
							Key2(2),
							Key3(3),
							Key4(4),
							Key5(5),
							Key6(6),
							Key7(7),
							Key8(8),
							Key9(9) }
        ACCESS  read-write
        STATUS  mandatory
        DESCRIPTION
                "ICAStatusDialog"
        ::={DefaultHotkeysEntry 8}

ICActrlEsc  OBJECT-TYPE
        SYNTAX  INTEGER {
		                Ctrl(0)
						}
        ACCESS  read-write
        STATUS  mandatory
        DESCRIPTION
                "ICAStatusDialog"
        ::={DefaultHotkeysEntry 9}

ICActrlEsc2  OBJECT-TYPE
        SYNTAX  INTEGER {	Key0(0),
							Key1(1),
							Key2(2),
							Key3(3),
							Key4(4),
							Key5(5),
							Key6(6),
							Key7(7),
							Key8(8),
							Key9(9) }
        ACCESS  read-write
        STATUS  mandatory
        DESCRIPTION
                "ICAStatusDialog"
        ::={DefaultHotkeysEntry 10}

ICAaltEsc  OBJECT-TYPE
        SYNTAX  INTEGER {
		                Ctrl(0),
						Shift(1)
						}
        ACCESS  read-write
        STATUS  mandatory
        DESCRIPTION
                "ICAStatusDialog"
        ::={DefaultHotkeysEntry 11}

ICAaltEsc2  OBJECT-TYPE
        SYNTAX  INTEGER {	Key0(0),
							Key1(1),
							Key2(2),
							Key3(3),
							Key4(4),
							Key5(5),
							Key6(6),
							Key7(7),
							Key8(8),
							Key9(9) }
        ACCESS  read-write
        STATUS  mandatory
        DESCRIPTION
                "ICAStatusDialog"
        ::={DefaultHotkeysEntry 12}

ICAaltTab  OBJECT-TYPE
        SYNTAX  INTEGER {
		                Ctrl(0),
						Shift(1)
						}
        ACCESS  read-write
        STATUS  mandatory
        DESCRIPTION
                "ICAStatusDialog"
        ::={DefaultHotkeysEntry 13}

ICAaltTab2  OBJECT-TYPE
        SYNTAX  INTEGER {	Key0(0),
							Key1(1),
							Key2(2),
							Key3(3),
							Key4(4),
							Key5(5),
							Key6(6),
							Key7(7),
							Key8(8),
							Key9(9) }
        ACCESS  read-write
        STATUS  mandatory
        DESCRIPTION
                "ICAStatusDialog"
        ::={DefaultHotkeysEntry 14}

ICAaltBackTab  OBJECT-TYPE
        SYNTAX  INTEGER {
		                Ctrl(0),
						Shift(1)
						}
        ACCESS  read-write
        STATUS  mandatory
        DESCRIPTION
                "ICAStatusDialog"
        ::={DefaultHotkeysEntry 15}

ICAaltBackTab2  OBJECT-TYPE
        SYNTAX  INTEGER {	Key0(0),
							Key1(1),
							Key2(2),
							Key3(3),
							Key4(4),
							Key5(5),
							Key6(6),
							Key7(7),
							Key8(8),
							Key9(9) }
        ACCESS  read-write
        STATUS  mandatory
        DESCRIPTION
                "ICAStatusDialog"
        ::={DefaultHotkeysEntry 16}


-- ****************************************************************************
-- the wbt3Connections group
--
--      The wyse enterprise				(1.3.6.4.1.714)
--        Product Group					(1.3.6.4.1.714.1)
--          ThinClient Group			(1.3.6.4.1.714.1.2)
--            wbt3 Group				(1.3.6.4.1.714.1.2.3)
--             wbt3Connections Group	(1.3.6.4.1.714.1.2.3.13)	
--
-- Implementation of the wbt3Connections Group is mandatory for all ThinClient
-- ****************************************************************************

wbt3ConnectionsTable OBJECT-TYPE
        SYNTAX  SEQUENCE OF wbt3ConnectionEntry
        ACCESS  not-accessible
        STATUS  mandatory
        DESCRIPTION
                "A list of connection entries. The number of entries is the number of existing connections
                plus one. The last entry is a dummy entry reserved for new connection creation.
				wbt3ConnectionName for this dummy entry is 'Not Defined'."
        ::={wbt3Connections 2}

wbt3ConnectionEntry OBJECT-TYPE
        SYNTAX  wbt3ConnectionEntry
        ACCESS  not-accessible
        STATUS  mandatory
        DESCRIPTION
                "A connection entry containing objects describing this connection. 
                wbt3ConnectionName is the instance identifier for wbt3ConnectionEntry"
        INDEX   {wbt3ConnectionName}
        ::={wbt3ConnectionsTable 1}
        
wbt3ConnectionEntry ::=
        SEQUENCE {
                wbt3ConnectionName
                DisplayString,
                wbt3ConnectionType
                INTEGER,
				wbt3ConnectionEntryStatus
				INTEGER
        }

wbt3ConnectionName OBJECT-TYPE
        SYNTAX  DisplayString
        ACCESS  read-write
        STATUS  mandatory
        DESCRIPTION
                "Name of the connection. This object is served as instance identifier for the connection entry.
                Therefore value for this object must be unique among all entries. Maximum length depends on wbt3ConnectionType.
                (37 for RDP wbt3ConnectionType; 32 for ICA wbt3ConnectionType; 
                 42 for TEC wbt3ConnectionType; 20 for DialUp wbt3ConnectionType)"
        ::={wbt3ConnectionEntry 2}

wbt3ConnectionType  OBJECT-TYPE
        SYNTAX  INTEGER {
						RDP(0),
                        ICA(1),
						TEC(2),
                        DialUp(3)
						}
        ACCESS  read-write
        STATUS  mandatory
        DESCRIPTION
                "Type of the connection. 
                This object can be modified when the associated wbt3ConnectionEntryStatus is notInService. "
        ::={wbt3ConnectionEntry 3}


wbt3ConnectionEntryStatus  OBJECT-TYPE
        SYNTAX  INTEGER {
						active(1), 
						notInService(2),
						notReady(3),
						createAndGo(4),
						createAndWait(5),
						destroy(6) 
						}
        ACCESS  read-write
        STATUS  mandatory
        DESCRIPTION
                "Status of this connection entry. This object is used to manage the creation and deletion
				of the wbt3ConnectionEntry.  State machine for this object is compliant to RFC1903, definition
				of textual conventions for RowStatus.  This object may not be set to 'active' unless the 
				wbt3ConnectionName is set.

				active - this is an existing connection saved in permanent storage. Values of fields within this
				table entry are not allowed to modified while it is active.  To modify fields within this table 
				entry, take the entry to 'notInService' state first.

				notInService - this is a connection entry exists in the thinclient's temporary memory, but is
				unavailable for use by the thinclient device. Entry must be put in this state before modification
				to other fields (except wbt3ConnectionName) can be made. Changes to wbt3ConnectionName is NOT 
				allowed.  To modify the name of an existing connection, delete the connection by setting 
				wbt3ConnectionEntryStatus to 'destroy',	then create a new connection with the new name by following 
				the description for status 'notReady', 'createAndGo' or 'createAndWait' as specified below.
				A management device has to set the wbt3ConnectionEntryStatus to 'active' to activate the 
				connection entry.  Entries remaining in notInService state for an excessive period of time will 
				be removed to free up resource in the thinclient device.  Entries in this state will not be retained 
				after reboot.

				notReady - this is a dummy connection defined to facilitate creation of new entry. 
				An administrator can create a new connection by modifying wbt3ConnectionName of this entry to 
				a name which does not currently exist in wbt3ConnectionsTable.  This will put the entry
				in notInService state. An administrator can then put the connection in permanent storage by changing
				wbt3ConnectionEntryStatus to 'active'.
				Note that the assigned connection name CANNOT be an empty or 'Not Defined' string. 

				createAndGo - This status is supplied by a management station wishing to create a new instance
				of a connection entry and to have its status automatically set to active, making it 
				available for use by the thinclient device. wbt3ConnectionName MUST be supplied in the same
				PDU which set wbt3connectionEntryStatus to 'createAndGo'.

				createAndWait - This status is supplied by a management station wishing to create a new instance 
				of a connection entry (but not make it immediately available for use by the thinclient device).

				destroy - an administrator can delete an existing connection by setting this object of
				target entry to 'destroy'."

        ::={wbt3ConnectionEntry 10}


	wbt3RDPConnections         OBJECT IDENTIFIER ::= {wbt3Connections 3}

-- ****************************************************************************
-- the wbt3RDPConnections Group
--
--      The wyse enterprise				(1.3.6.4.1.714)
--        Product Group					(1.3.6.4.1.714.1)
--          ThinClient Group			(1.3.6.4.1.714.1.2)
--            wbt3 Group				(1.3.6.4.1.714.1.2.3)
--             wbt3RDPConnections Group	(1.3.6.4.1.714.1.2.3.13.3)	

-- ****************************************************************************

wbt3RDPConnTable OBJECT-TYPE
        SYNTAX  SEQUENCE OF wbt3RDPConnEntry
        ACCESS  not-accessible
        STATUS  mandatory
        DESCRIPTION
                "A table of connections, number of entries is the number of entries in 
                wbt3ConnectionTable which has wbt3ConnectionEntryStatus=active or notInService, and
                wbt3ConnectionType=RDP."
        ::={wbt3RDPConnections 1}

wbt3RDPConnEntry OBJECT-TYPE
        SYNTAX  wbt3RDPConnEntry
        ACCESS  not-accessible
        STATUS  mandatory
        DESCRIPTION
                "A RDP connection entry containing objects describing this connection. 
                wbt3RDPConnName is the instance identifier for wbt3RDPConnEntry"
        INDEX   {wbt3RDPConnName}
        ::={wbt3RDPConnTable 1}
        
wbt3RDPConnEntry ::=
        SEQUENCE {
                wbt3RDPConnName
                DisplayString,
                wbt3RDPConnServer
                DisplayString,
                wbt3RDPConnLowSpeed
                INTEGER,
				wbt3RDPConnAutoLogon
				INTEGER,
				wbt3RDPConnUsername
                DisplayString,
				wbt3RDPConnDomain
				DisplayString,
				wbt3RDPConnStartApplication
				INTEGER,
				wbt3RDPConnFilename
                DisplayString,
				wbt3RDPConnWorkingDir
                DisplayString,
				wbt3RDPConnModifiable
				INTEGER
        }

wbt3RDPConnName OBJECT-TYPE
        SYNTAX  DisplayString
        ACCESS  read-only
        STATUS  mandatory
        DESCRIPTION
                "Name of the RDP connection. This object is served as instance identifier for the RDPConnEntry.
                Value for this object is unique among all entries."
        ::={wbt3RDPConnEntry 1}

wbt3RDPConnServer OBJECT-TYPE
        SYNTAX  DisplayString
        ACCESS  read-write
        STATUS  mandatory
        DESCRIPTION
                "Host server name or IP address the RDP Client connects to. Maximum length is 32.
                This object is modifiable only when wbt3RDPConnModifiable is 'Yes'."
        ::={wbt3RDPConnEntry 2}

wbt3RDPConnLowSpeed   OBJECT-TYPE
        SYNTAX  INTEGER {
                        No(0),
                        Yes(1)
						}
        ACCESS  read-write
        STATUS  mandatory
        DESCRIPTION
                "Using low speed connection.
                This object is modifiable only when wbt3RDPConnModifiable is 'Yes'."

        ::={wbt3RDPConnEntry 3}

wbt3RDPConnAutoLogon   OBJECT-TYPE
        SYNTAX  INTEGER {
                        No(0),
                        Yes(1)
						}
        ACCESS  read-write
        STATUS  mandatory
        DESCRIPTION
                "Enable RDP automatic logon.
                This object is modifiable only when wbt3RDPConnModifiable is 'Yes'."
        ::={wbt3RDPConnEntry 4}

wbt3RDPConnUsername OBJECT-TYPE
        SYNTAX  DisplayString
        ACCESS  read-write
        STATUS  mandatory
        DESCRIPTION
                "Specify the user name to atomatically logon to host. Maximum length is 32.
                This object is modifiable only when wbt3RDPConnModifiable is 'Yes'."
        ::={wbt3RDPConnEntry 5}

wbt3RDPConnDomain OBJECT-TYPE
        SYNTAX  DisplayString
        ACCESS  read-write
        STATUS  mandatory
        DESCRIPTION
                "Domain name of host server. Maximum length is 80.
                This object is modifiable only when wbt3RDPConnModifiable is 'Yes'."
        ::={wbt3RDPConnEntry 7}

wbt3RDPConnStartApplication OBJECT-TYPE
        SYNTAX  INTEGER {
                        Desktop(0),
                        Filename(2)
						}
        ACCESS  read-write
        STATUS  mandatory
        DESCRIPTION
                "Select application starts up at connection.
				0 = Desktop, 2 = select File name radio button.
                This object is modifiable only when wbt3RDPConnModifiable is 'Yes'."
        ::={wbt3RDPConnEntry 8}

wbt3RDPConnFilename OBJECT-TYPE
        SYNTAX  DisplayString
        ACCESS  read-write
        STATUS  mandatory
        DESCRIPTION
                "Name of the application to start. Maximum length is 80. 
                This object is modifiable only when wbt3RDPConnModifiable is 'Yes'."

        ::={wbt3RDPConnEntry 9}

wbt3RDPConnWorkingDir OBJECT-TYPE
        SYNTAX  DisplayString
        ACCESS  read-write
        STATUS  mandatory
        DESCRIPTION
                "Application working directory. Maximum length is 80. 
                This object is modifiable only when wbt3RDPConnModifiable is 'Yes'."

        ::={wbt3RDPConnEntry 10}

wbt3RDPConnModifiable	OBJECT-TYPE
        SYNTAX  INTEGER {
                        No(0),
                        Yes(1) 
                        }
        ACCESS  read-only
        STATUS  mandatory
        DESCRIPTION
                "Indicate whether objects within this entry is modifiable currently.
                Objects are modifiable if wbt3ConnectionEntryStatus of associated connection entry in 
                wbt3ConnectionsTable is in 'notInService'."
        ::={wbt3RDPConnEntry 30}

	wbt3ICAConnections         OBJECT IDENTIFIER ::= {wbt3Connections 4}

-- ****************************************************************************
-- the wbt3ICAConnections Group
--
--      The wyse enterprise				(1.3.6.4.1.714)
--        Product Group					(1.3.6.4.1.714.1)
--          ThinClient Group			(1.3.6.4.1.714.1.2)
--            wbt3 Group				(1.3.6.4.1.714.1.2.3)
--             wbt3ICAConnections Group	(1.3.6.4.1.714.1.2.3.13.4)	
--
-- ****************************************************************************

wbt3ICAConnTable OBJECT-TYPE
        SYNTAX  SEQUENCE OF wbt3ICAConnEntry
        ACCESS  not-accessible
        STATUS  mandatory
        DESCRIPTION
                "A table of ICA connections, number of entries is the number of entries in 
                wbt3ConnectionTable which has wbt3ConnectionEntryStatus=active or notInService, and
                wbt3ConnectionType=ICA."
        ::={wbt3ICAConnections 1}

wbt3ICAConnEntry OBJECT-TYPE
        SYNTAX  wbt3ICAConnEntry
        ACCESS  not-accessible
        STATUS  mandatory
        DESCRIPTION
                "A ICA connection entry containing objects describing this connection. 
                wbt3ICAConnName is the instance identifier for wbt3ICAConnEntry"
        INDEX   {wbt3ICAConnName}
        ::={wbt3ICAConnTable 1}
        
wbt3ICAConnEntry ::=
        SEQUENCE {
                wbt3ICAConnName
                DisplayString,
                wbt3ICAConnCommType
                INTEGER,
                wbt3ICAConnServer
                DisplayString,
				wbt3ICAConnCommandLine
                DisplayString,
				wbt3ICAConnWorkingDir
				DisplayString,
				wbt3ICAConnUsername
				DisplayString,
				wbt3ICAConnDomain
                DisplayString,
				wbt3ICAConnColors
                INTEGER,
				wbt3ICAConnDataCompress
				INTEGER,
				wbt3ICAConnSoundQuality
				INTEGER,
				wbt3ICAConnModifiable
				INTEGER
        }

wbt3ICAConnName OBJECT-TYPE
        SYNTAX  DisplayString
        ACCESS  read-only
        STATUS  mandatory
        DESCRIPTION
                "Name of the ICA connection. This object is served as instance identifier for the ICAConnEntry.
                Value for this object is unique among all entries."
        ::={wbt3ICAConnEntry 1}

wbt3ICAConnCommType OBJECT-TYPE
        SYNTAX  INTEGER {
                        Network(0) 
						}
        ACCESS  read-write
        STATUS  mandatory
        DESCRIPTION
                "Communication media this connection uses.
                This object is modifiable only when wbt3ICAConnModifiable is 'Yes'."
        ::={wbt3ICAConnEntry 2}

wbt3ICAConnServer OBJECT-TYPE
        SYNTAX  DisplayString
        ACCESS  read-write
        STATUS  mandatory
        DESCRIPTION
                "IP address or name of ICA server connect to. Maximum length is 63.
                This object is modifiable only when wbt3ICAConnModifiable is 'Yes'."
        ::={wbt3ICAConnEntry 3}

wbt3ICAConnCommandLine OBJECT-TYPE
        SYNTAX  DisplayString
        ACCESS  read-write
        STATUS  mandatory
        DESCRIPTION
                "Command line to be launched once this ICA connection is brought up. Maximum length is 80.
                This object is modifiable only when wbt3ICAConnModifiable is 'Yes'."

        ::={wbt3ICAConnEntry 4}

wbt3ICAConnWorkingDir OBJECT-TYPE
        SYNTAX  DisplayString
        ACCESS  read-write
        STATUS  mandatory
        DESCRIPTION
                "Working Directory to be used for this ICA. Maximum length is 80.
                This object is modifiable only when wbt3ICAConnModifiable is 'Yes'."
        ::={wbt3ICAConnEntry 5}

wbt3ICAConnUsername OBJECT-TYPE
        SYNTAX  DisplayString
        ACCESS  read-write
        STATUS  mandatory
        DESCRIPTION
                "User name to be used to log on to ICA server. Maximum length is 19.
                This object is modifiable only when wbt3ICAConnModifiable is 'Yes'."
        ::={wbt3ICAConnEntry 6}

wbt3ICAConnDomain OBJECT-TYPE
        SYNTAX  DisplayString
        ACCESS  read-write
        STATUS  mandatory
        DESCRIPTION
                "Domain name to be used to log on to ICA server. Maximum length is 16.
                This object is modifiable only when wbt3ICAConnModifiable is 'Yes'."
        ::={wbt3ICAConnEntry 8}

wbt3ICAConnColors OBJECT-TYPE
        SYNTAX  INTEGER {
                        Colors-16(0),
                        Colors-256(1)
			}
        ACCESS  read-write
        STATUS  mandatory
        DESCRIPTION
				"Specify 16/256 window colors.
                This object is modifiable only when wbt3ICAConnModifiable is 'Yes'."
        ::={wbt3ICAConnEntry 9}

wbt3ICAConnDataCompress OBJECT-TYPE
        SYNTAX  INTEGER {
                        No(0),
                        Yes(1)
			}
        ACCESS  read-write
        STATUS  mandatory
        DESCRIPTION
                "Enable/Disable Data compression for this ICA session.
                This object is modifiable only when wbt3ICAConnModifiable is 'Yes'."
        ::={wbt3ICAConnEntry 10}

wbt3ICAConnSoundQuality OBJECT-TYPE
        SYNTAX  INTEGER {
                        None(0), 
                        Low(1),
                        Medium(2),
                        High(3)
                        }
        ACCESS  read-write
        STATUS  mandatory
        DESCRIPTION
                "Set sound quality for this ICA session, None to disable sound.
                This object is modifiable only when wbt3ICAConnModifiable is 'Yes'."
        ::={wbt3ICAConnEntry 11}

wbt3ICAConnModifiable	OBJECT-TYPE
        SYNTAX  INTEGER {
                        No(0),
                        Yes(1) 
                        }
        ACCESS  read-only
        STATUS  mandatory
        DESCRIPTION
                "Indicate whether objects within this entry is modifiable currently.
                Objects are modifiable if wbt3ConnectionEntryStatus of associated connection entry in 
                wbt3ConnectionsTable is in 'notInService'."
        ::={wbt3ICAConnEntry 30}


	wbt3TermConnections         OBJECT IDENTIFIER ::= {wbt3Connections 5}

-- ****************************************************************************
-- the wbt3TermConnections Group
--
--      The wyse enterprise					(1.3.6.4.1.714)
--        Product Group						(1.3.6.4.1.714.1)
--          ThinClient Group				(1.3.6.4.1.714.1.2)
--            wbt3 Group					(1.3.6.4.1.714.1.2.3)
--             wbt3TermConnections Group	(1.3.6.4.1.714.1.2.3.13.5)	
--
-- ****************************************************************************

wbt3TermConnTable OBJECT-TYPE
        SYNTAX  SEQUENCE OF wbt3TermConnEntry
        ACCESS  not-accessible
        STATUS  mandatory
        DESCRIPTION
                "A table of Terminal Emulation connections, number of entries is the number of entries in 
                wbt3ConnectionTable which has wbt3ConnectionEntryStatus=active or notInService, and
                wbt3ConnectionType=TEC."
        ::={wbt3TermConnections 1}

wbt3TermConnEntry OBJECT-TYPE
        SYNTAX  wbt3TermConnEntry
        ACCESS  not-accessible
        STATUS  mandatory
        DESCRIPTION
                "A terminal emulation connection entry containing objects describing this connection. 
                wbt3TermConnName is the instance identifier for wbt3TermConnEntry"
        INDEX   {wbt3TermConnName}
        ::={wbt3TermConnTable 1}
        
wbt3TermConnEntry ::=
        SEQUENCE {
                wbt3TermConnName
                DisplayString,
                wbt3TermConnCommType
				INTEGER,
				wbt3TermConnServer
                DisplayString,
				wbt3TermConnEmuType
				INTEGER,
                wbt3TermVTEmuModel
				INTEGER,
                wbt3TermIBM3270EmuModel
				INTEGER,
                wbt3TermIBM5250EmuModel
				INTEGER,
				wbt3TermConnPortNumber
                DisplayString,
				wbt3TermConnTelnetName
				DisplayString,
                wbt3TermConnPrinterPort
				INTEGER,
				wbt3TermConnFormFeed
				INTEGER,
				wbt3TermConnAutoLineFeed
				INTEGER,
				wbt3TermConnModifiable
				INTEGER
				}

wbt3TermConnName OBJECT-TYPE
        SYNTAX  DisplayString
        ACCESS  read-only
        STATUS  mandatory
        DESCRIPTION
                "A unique name for the Terminal Emulation configuration entry. Maximum length is 42"
        ::={wbt3TermConnEntry 1}

wbt3TermConnCommType OBJECT-TYPE
        SYNTAX  INTEGER {
                        Network(0) 
                        }
        ACCESS  read-write
        STATUS  mandatory
        DESCRIPTION
                "Communication media this connection uses.
                This object is modifiable only when wbt3TermConnModifiable is 'Yes'."
        ::={wbt3TermConnEntry 2}

wbt3TermConnServer OBJECT-TYPE
        SYNTAX  DisplayString
        ACCESS  read-write
        STATUS  mandatory
        DESCRIPTION
                "IP address or host name of terminal server connect to. Maximum length is 60.
                This object is modifiable only when wbt3TermConnModifiable is 'Yes'."
        ::={wbt3TermConnEntry 3}

wbt3TermConnEmuType OBJECT-TYPE
        SYNTAX  INTEGER {
                        VT52(0), 
                        VT100(1),
--						VT220(2),
						VT400-7-Bit(3),
						VT400-8-Bit(4),
						Ansi-BBS(5),
						Sco-Console(6),
						IBM3270(7),
						IBM3151(8),
						IBM5250(9),
						WY50(10),
						WY50plus(11),
						TVI910(12),
						TVI920(13),
						TVI925(14),
						ADDS-A2(15),
						HZ1500(16),
						WY60(17)
                        }
        ACCESS  read-write
        STATUS  mandatory
        DESCRIPTION
                "Emulation mode for this connection.
                This object is modifiable only when wbt3TermConnModifiable is 'Yes'."

        ::={wbt3TermConnEntry 4}

wbt3TermConnVTEmuModel  OBJECT-TYPE
        SYNTAX  INTEGER {
						VT100(0),
						VT101(1),
						VT102(2),
						VT125(3),
						VT220(4),
						VT240(5),
						VT320(6),
						VT340(7),
						VT420(8),
						VT131(9),
						VT132(10),
						Not-Applicable(256)
						}
        ACCESS  read-write
        STATUS  mandatory
        DESCRIPTION
                "Terminal model uses for this connection. This field represents the VT Terminal ID.
                This object is modifiable only when wbt3TermConnModifiable is 'Yes'."
        ::={wbt3TermConnEntry 5}

wbt3TermConnIBM3270EmuModel  OBJECT-TYPE
        SYNTAX  INTEGER {
						IBM3278-2(0),
						IBM3278-3(1),
						IBM3278-4(2),
						IBM3278-5(3),
						IBM3278-2-E(4),
						IBM3278-3-E(5),
						IBM3278-4-E(6),
						IBM3278-5-E(7),
						IBM3279-2(8),
						IBM3279-3(9),
						IBM3279-4(10),
						IBM3279-5(11),
						IBM3287-1(12),
						Not-Applicable(256)
						}
        ACCESS  read-write
        STATUS  mandatory
        DESCRIPTION
                "IBM 3270 terminal emulation models. 
                This object is valid only when wbt3TermConnEmuType = IBM3270.
                This object is modifiable only when wbt3TermConnModifiable is 'Yes'."
        ::={wbt3TermConnEntry 6}

wbt3TermConnIBM5250EmuModel  OBJECT-TYPE
        SYNTAX  INTEGER {
						IBM5291-1(0),
						IBM5292-2(1),
						IBM5251-11(2),
						IBM3179-2(3),
						IBM3196-A1(4),
						IBM3180-2(5),
						IBM3477-FC(6),
						IBM3477-FG(7),
						IBM3486-BA(8),
						IBM3487-HA(9),
						IBM3487-HC(10),
						Not-Applicable(256)
						}
        ACCESS  read-write
        STATUS  mandatory
        DESCRIPTION
                "IBM 5250 terminal emulation models.
				This object is valid only when wbt3TermConnEmuType = IBM5250.
                This object is modifiable only when wbt3TermConnModifiable is 'Yes'."
        ::={wbt3TermConnEntry 7}

wbt3TermConnPortNumber OBJECT-TYPE
        SYNTAX  INTEGER(1..65535)
        ACCESS  read-write
        STATUS  mandatory
        DESCRIPTION
                "Telnet port number used for this connection.
                This object is modifiable only when wbt3TermConnModifiable is 'Yes'."
        ::={wbt3TermConnEntry 10}

wbt3TermConnTelnetName OBJECT-TYPE
        SYNTAX  DisplayString
        ACCESS  read-write
        STATUS  mandatory
        DESCRIPTION
                "Name of this telnet session. Maximum length is 39.
                This object is modifiable only when wbt3TermConnModifiable is 'Yes'."
        ::={wbt3TermConnEntry 11}

wbt3TermConnPrinterPort OBJECT-TYPE
        SYNTAX  INTEGER {
                        LPT1(0) 
                        }
        ACCESS  read-write
        STATUS  mandatory
        DESCRIPTION
                "Printer port assigned to this connection.
                This object is modifiable only when wbt3TermConnModifiable is 'Yes'."
        ::={wbt3TermConnEntry 12}

wbt3TermConnFormFeed OBJECT-TYPE
        SYNTAX  INTEGER {
                        No(0),
                        Yes(1)
                        }
        ACCESS  read-write
        STATUS  mandatory
        DESCRIPTION
                "Use Form Feed terminator for printing.
                This object is modifiable only when wbt3TermConnModifiable is 'Yes'."
        ::={wbt3TermConnEntry 13}

wbt3TermConnAutoLineFeed OBJECT-TYPE
        SYNTAX  INTEGER {
                        No(0),
                        Yes(1)
                        }
        ACCESS  read-write
        STATUS  mandatory
        DESCRIPTION
                "Use Auto line Feed for printing.
                This object is modifiable only when wbt3TermConnModifiable is 'Yes'."
        ::={wbt3TermConnEntry 14}

wbt3TermConnScript  OBJECT-TYPE
         SYNTAX  DisplayString
         ACCESS  read-write
         STATUS  mandatory
         DESCRIPTION
             	"Script for this terminal emulation. 
				Script syntax: 
				Use back slash (\) to separate between 2 script commands,
				each script command has 2 entries (Act on and Send),
				Use semi column (;) to separate 2 entries.
				Samples: Login;<CR> or
				         Login;<CR><D>\Username,<U>
				Send entry syntax: C.return = <CR> Delay (2s) = <D> Line Feed = <LF> 
				Password = <PW> Pause (0.255) = <P> UserName = <UN>.
				Maximum length is 256.
                This object is modifiable only when wbt3TermConnModifiable is 'Yes'."
         ::={wbt3TermConnEntry 15}


wbt3TermConnModifiable	OBJECT-TYPE
        SYNTAX  INTEGER {
                        No(0),
                        Yes(1) 
                        }
        ACCESS  read-only
        STATUS  mandatory
        DESCRIPTION
                "Indicate whether objects within this entry is modifiable currently.
                Objects are modifiable if wbt3ConnectionEntryStatus of associated connection entry in 
                wbt3ConnectionsTable is in 'notInService'."
        ::={wbt3TermConnEntry 30}


-- ****************************************************************************
-- the wbt3Users Group
--
--      The wyse enterprise               (1.3.6.4.1.714)
--        Product Group                   (1.3.6.4.1.714.1)
--          ThinClient Group              (1.3.6.4.1.714.1.2)
--            wbt3 Group                  (1.3.6.4.1.714.1.2.3)
--              wbt3Administration Group  (1.3.6.4.1.714.1.2.3.8)
--                wbt3Users Group		  (1.3.6.4.1.714.1.2.3.8.14)
--
-- Implementation of the wbt3UpDnLoad Group is mandatory for all ThinClient2
-- products with SNMP agents which supports the wyse MIB
-- ****************************************************************************

wbt3UsersTable OBJECT-TYPE
        SYNTAX  SEQUENCE OF wbt3UsersEntry
        ACCESS  not-accessible
        STATUS  mandatory
        DESCRIPTION
                "A list of user accounts. The number of entries is the number of existing user accounts
                plus one. The last entry is a dummy entry reserved for new user account creation.
				wbt3userName for this dummy entry is 'Not Defined'."
        ::={wbt3Users 2}

wbt3UsersEntry OBJECT-TYPE
        SYNTAX  wbt3UsersEntry
        ACCESS  not-accessible
        STATUS  mandatory
        DESCRIPTION
                "A user account entry containing objects describing this user. 
                wbt3userName is the instance identifier for wbt3UsersEntry"
        INDEX   {wbt3userName}
        ::={wbt3UsersTable 1}
        
wbt3UsersEntry ::=
        SEQUENCE {
				wbt3UsersStatus
				INTEGER,
                wbt3userName
                DisplayString,
				wbt3privilege
                INTEGER,
				wbt3password1
                DisplayString,
				wbt3Connection1
                DisplayString,
				wbt3Connection2
                DisplayString,
				wbt3Connection3
                DisplayString,
				wbt3Connection4
                DisplayString,
				wbt3Connection5
                DisplayString,
				wbt3Connection6
                DisplayString,
				wbt3Connection7
                DisplayString,
				wbt3Connection8
                DisplayString,
				wbt3UserPasswordChange
				INTEGER
        }

wbt3UsersStatus OBJECT-TYPE
        SYNTAX  INTEGER { 
						active(1),
						notInService(2),
						notReady(3),
						createAndGo(4),
						createAndWait(5),
						destroy(6) 
						}
        ACCESS  read-write
        STATUS  mandatory
        DESCRIPTION
                "Status of this user account entry. This object is used to manage the creation and deletion
				of the wbt3UsersEntry.  State machine for this object is compliant to RFC1903, definition
				of textual conventions for RowStatus.  This object may not be set to 'active' unless the 
				wbt3UserName is set.

				active - this is an existing user account saved in permanent storage. Values of fields within this
				table entry are not allowed to modified while it is active.  To modify fields within this table 
				entry, take the entry to 'notInService' state first.

				notInService - this is a user account entry exists in the thinclient's temporary memory, but is
				unavailable for use by the thinclient device. Entry must be put in this state before modification
				to other fields (except wbt3UserName) can be made. Changes to wbt3UserName is NOT 
				allowed.  To modify the name of an existing user account, delete the user account by setting 
				wbt3UsersStatus to 'destroy',	then create a new user account with the new name by following 
				the description for status 'notReady', 'createAndGo' or 'createAndWait' as specified below.
				A management device has to set the wbt3UsersStatus to 'active' to activate the 
				user account.  Entries remaining in notInService state for an excessive period of time will 
				be removed to free up resource in the thinclient device.  Entries in this state will not be retained 
				after reboot.

				notReady - this is a dummy user account defined to facilitate creation of new entry. 
				An administrator can create a new user account by modifying wbt3UserName of this entry to 
				a name which does not currently exist in wbt3UsersTable.  This will put the entry
				in notInService state. An administrator can then put the user account in permanent storage by changing
				wbt3UsersStatus to 'active'.
				Note that the assigned user account name CANNOT be an empty or 'Not Defined' string. 

				createAndGo - This status is supplied by a management station wishing to create a new instance
				of a user account and to have its status automatically set to active, making it 
				available for use by the thinclient device. wbt3UserName MUST be supplied in the same
				PDU which set wbt3UsersStatus to 'createAndGo'.

				createAndWait - This status is supplied by a management station wishing to create a new instance 
				of a user account. (but not make it immediately available for use by the thinclient device).

				destroy - an administrator can delete an existing user account by setting this object of
				target entry to 'destroy'. Note that the default administrator account with name 'Administrator'
				that is built in to the terminal cannot be deleted."
        ::={wbt3UsersEntry 2}

wbt3userName  OBJECT-TYPE
        SYNTAX  DisplayString
        ACCESS  read-write
        STATUS  mandatory
        DESCRIPTION
                "Name of this user. This object is served as instance identifier for the user account entry.
                Therefore value for this object must be unique among all entries. Maximum length is 20."
        ::={wbt3UsersEntry 3}

wbt3password1   OBJECT-TYPE
        SYNTAX  DisplayString
        ACCESS  read-write
        STATUS  mandatory
        DESCRIPTION
				"The password for this user account. Maximum length is 20.
                This object can be modified only when the associated wbt3UsersStatus is 'notInService'. "
        ::={wbt3UsersEntry 4}

wbt3privilege  OBJECT-TYPE
        SYNTAX  INTEGER {
                        Admin(0),
                        User(1),
                        Guest(2)
						}
        ACCESS  read-write
        STATUS  mandatory
        DESCRIPTION
                "Indicates whether the user has extended, normal, or
				 restricted rights on this terminal.
				Note that the privilege of the default administrator account (with name 'Administrator') cannot
				be modifed.
                For all other accounts, this object can be modified only when the associated wbt3UsersStatus 
                is 'notInService'. "
        ::={wbt3UsersEntry 5}

wbt3Connection1  OBJECT-TYPE
        SYNTAX  DisplayString
        ACCESS  read-write
        STATUS  mandatory
        DESCRIPTION
				"Name of a connection associated with this user. The connection name has to match the value
				in wbt3ConnectionName of one of the entries	in wbt3ConnectionsTable that is in an 'active' state.
				That is, the connection specified has to exist and be currently activated.  
				Set this object to an empty string to dis-associate a connection from the user.
				For a user account that has Administrator privilege, all existing connections are associated with
				the user automatically.  Therefore this object is not modifiable if wbt3privilege is 'Admin'.
                For accounts with User or Guest privilege, this object can be modified only when the associated 
                wbt3UsersStatus is 'notInService'. "
        ::={wbt3UsersEntry 7}

wbt3Connection2  OBJECT-TYPE
        SYNTAX  DisplayString
        ACCESS  read-write
        STATUS  mandatory
        DESCRIPTION
				"Name of a connection associated with this user. The connection name has to match the value
				in wbt3ConnectionName of one of the entries	in wbt3ConnectionsTable that is in an 'active' state.
				That is, the connection specified has to exist and be currently activated.  
				Set this object to an empty string to dis-associate a connection from the user.
				For a user account that has Administrator privilege, all existing connections are associated with
				the user automatically.  Therefore this object is not modifiable if wbt3privilege is 'Admin'.
                For accounts with User or Guest privilege, this object can be modified only when the associated 
                wbt3UsersStatus is 'notInService'. "
        ::={wbt3UsersEntry 8}

wbt3Connection3  OBJECT-TYPE
        SYNTAX  DisplayString
        ACCESS  read-write
        STATUS  mandatory
        DESCRIPTION
				"Name of a connection associated with this user. The connection name has to match the value
				in wbt3ConnectionName of one of the entries	in wbt3ConnectionsTable that is in an 'active' state.
				That is, the connection specified has to exist and be currently activated.  
				Set this object to an empty string to dis-associate a connection from the user.
				For a user account that has Administrator privilege, all existing connections are associated with
				the user automatically.  Therefore this object is not modifiable if wbt3privilege is 'Admin'.
                For accounts with User or Guest privilege, this object can be modified only when the associated 
                wbt3UsersStatus is 'notInService'. "
        ::={wbt3UsersEntry 9}

wbt3Connection4  OBJECT-TYPE
        SYNTAX  DisplayString
        ACCESS  read-write
        STATUS  mandatory
        DESCRIPTION
				"Name of a connection associated with this user. The connection name has to match the value
				in wbt3ConnectionName of one of the entries	in wbt3ConnectionsTable that is in an 'active' state.
				That is, the connection specified has to exist and be currently activated.  
				Set this object to an empty string to dis-associate a connection from the user.
				For a user account that has Administrator privilege, all existing connections are associated with
				the user automatically.  Therefore this object is not modifiable if wbt3privilege is 'Admin'.
                For accounts with User or Guest privilege, this object can be modified only when the associated 
                wbt3UsersStatus is 'notInService'. "
        ::={wbt3UsersEntry 10}

wbt3Connection5  OBJECT-TYPE
        SYNTAX  DisplayString
        ACCESS  read-write
        STATUS  mandatory
        DESCRIPTION
				"Name of a connection associated with this user. The connection name has to match the value
				in wbt3ConnectionName of one of the entries	in wbt3ConnectionsTable that is in an 'active' state.
				That is, the connection specified has to exist and be currently activated.  
				Set this object to an empty string to dis-associate a connection from the user.
				For a user account that has Administrator privilege, all existing connections are associated with
				the user automatically.  Therefore this object is not modifiable if wbt3privilege is 'Admin'.
                For accounts with User or Guest privilege, this object can be modified only when the associated 
                wbt3UsersStatus is 'notInService'. "
        ::={wbt3UsersEntry 11}

wbt3Connection6  OBJECT-TYPE
        SYNTAX  DisplayString
        ACCESS  read-write
        STATUS  mandatory
        DESCRIPTION
				"Name of a connection associated with this user. The connection name has to match the value
				in wbt3ConnectionName of one of the entries	in wbt3ConnectionsTable that is in an 'active' state.
				That is, the connection specified has to exist and be currently activated.  
				Set this object to an empty string to dis-associate a connection from the user.
				For a user account that has Administrator privilege, all existing connections are associated with
				the user automatically.  Therefore this object is not modifiable if wbt3privilege is 'Admin'.
                For accounts with User or Guest privilege, this object can be modified only when the associated 
                wbt3UsersStatus is 'notInService'. "
        ::={wbt3UsersEntry 12}

wbt3Connection7  OBJECT-TYPE
        SYNTAX  DisplayString
        ACCESS  read-write
        STATUS  mandatory
        DESCRIPTION
				"Name of a connection associated with this user. The connection name has to match the value
				in wbt3ConnectionName of one of the entries	in wbt3ConnectionsTable that is in an 'active' state.
				That is, the connection specified has to exist and be currently activated.  
				Set this object to an empty string to dis-associate a connection from the user.
				For a user account that has Administrator privilege, all existing connections are associated with
				the user automatically.  Therefore this object is not modifiable if wbt3privilege is 'Admin'.
                For accounts with User or Guest privilege, this object can be modified only when the associated 
                wbt3UsersStatus is 'notInService'. "
        ::={wbt3UsersEntry 13}

wbt3Connection8  OBJECT-TYPE
        SYNTAX  DisplayString
        ACCESS  read-write
        STATUS  mandatory
        DESCRIPTION
				"Name of a connection associated with this user. The connection name has to match the value
				in wbt3ConnectionName of one of the entries	in wbt3ConnectionsTable that is in an 'active' state.
				That is, the connection specified has to exist and be currently activated.  
				Set this object to an empty string to dis-associate a connection from the user.
				For a user account that has Administrator privilege, all existing connections are associated with
				the user automatically.  Therefore this object is not modifiable if wbt3privilege is 'Admin'.
                For accounts with User or Guest privilege, this object can be modified only when the associated 
                wbt3UsersStatus is 'notInService'. "
        ::={wbt3UsersEntry 14}

wbt3AutoStart1  OBJECT-TYPE
        SYNTAX  INTEGER {
                        No(0),
                        Yes(1)
                        }
        ACCESS  read-write
        STATUS  mandatory
        DESCRIPTION
                "Setting this object to 'Yes' enable automatic launch of connection specified in wbt3Connection1
                object when the user logs on.  This object cannot be modified if wbt3Connection1 is empty string.
                Also, this object can be modified only when the associated wbt3UsersStatus is 'notInService'. "
        ::={wbt3UsersEntry 15}

wbt3AutoStart2  OBJECT-TYPE
        SYNTAX  INTEGER {
                        No(0),
                        Yes(1)
                        }
        ACCESS  read-write
        STATUS  mandatory
        DESCRIPTION
                "Setting this object to 'Yes' enable automatic launch of connection specified in wbt3Connection2
                object when the user logs on.  This object cannot be modified if wbt3Connection2 is empty string.
                Also, this object can be modified only when the associated wbt3UsersStatus is 'notInService'. "
        ::={wbt3UsersEntry 16}

wbt3AutoStart3  OBJECT-TYPE
        SYNTAX  INTEGER {
                        No(0),
                        Yes(1)
                        }
        ACCESS  read-write
        STATUS  mandatory
        DESCRIPTION
                "Setting this object to 'Yes' enable automatic launch of connection specified in wbt3Connection3
                object when the user logs on.  This object cannot be modified if wbt3Connection3 is empty string.
                Also, this object can be modified only when the associated wbt3UsersStatus is 'notInService'. "
        ::={wbt3UsersEntry 17}

wbt3AutoStart4  OBJECT-TYPE
        SYNTAX  INTEGER {
                        No(0),
                        Yes(1)
                        }
        ACCESS  read-write
        STATUS  mandatory
        DESCRIPTION
                "Setting this object to 'Yes' enable automatic launch of connection specified in wbt3Connection4
                object when the user logs on.  This object cannot be modified if wbt3Connection4 is empty string.
                Also, this object can be modified only when the associated wbt3UsersStatus is 'notInService'. "
        ::={wbt3UsersEntry 18}

wbt3AutoStart5  OBJECT-TYPE
        SYNTAX  INTEGER {
                        No(0),
                        Yes(1)
                        }
        ACCESS  read-write
        STATUS  mandatory
        DESCRIPTION
                "Setting this object to 'Yes' enable automatic launch of connection specified in wbt3Connection5
                object when the user logs on.  This object cannot be modified if wbt3Connection5 is empty string.
                Also, this object can be modified only when the associated wbt3UsersStatus is 'notInService'. "
        ::={wbt3UsersEntry 19}

wbt3AutoStart6  OBJECT-TYPE
        SYNTAX  INTEGER {
                        No(0),
                        Yes(1)
                        }
        ACCESS  read-write
        STATUS  mandatory
        DESCRIPTION
                "Setting this object to 'Yes' enable automatic launch of connection specified in wbt3Connection6
                object when the user logs on.  This object cannot be modified if wbt3Connection6 is empty string.
                Also, this object can be modified only when the associated wbt3UsersStatus is 'notInService'. "
        ::={wbt3UsersEntry 20}

wbt3AutoStart7  OBJECT-TYPE
        SYNTAX  INTEGER {
                        No(0),
                        Yes(1)
                        }
        ACCESS  read-write
        STATUS  mandatory
        DESCRIPTION
                "Setting this object to 'Yes' enable automatic launch of connection specified in wbt3Connection7
                object when the user logs on.  This object cannot be modified if wbt3Connection7 is empty string.
                Also, this object can be modified only when the associated wbt3UsersStatus is 'notInService'. "
        ::={wbt3UsersEntry 21}

wbt3AutoStart8  OBJECT-TYPE
        SYNTAX  INTEGER {
                        No(0),
                        Yes(1)
                        }
        ACCESS  read-write
        STATUS  mandatory
        DESCRIPTION
                "Setting this object to 'Yes' enable automatic launch of connection specified in wbt3Connection8
                object when the user logs on.  This object cannot be modified if wbt3Connection8 is empty string.
                Also, this object can be modified only when the associated wbt3UsersStatus is 'notInService'. "
        ::={wbt3UsersEntry 22}

wbt3UserPasswordChange  OBJECT-TYPE
        SYNTAX  INTEGER {
                        No(0),
                        Yes(1)
                        }
        ACCESS  read-write
        STATUS  mandatory
        DESCRIPTION
                "Indicates this user has privilege to change the password.
				For administrator, the password change is always on and cannot be set.
				For guest account, the password change is always off and cannot be set.
				For user account,  the password change can be set on/off.
                Also, this object can be modified only when the associated wbt3UsersStatus is 'notInService'. "
        ::={wbt3UsersEntry 23}

-- ****************************************************************************
--
--                               *** TRAPS ***
--
-- ****************************************************************************

wbt3TrapDHCPBuildMismatch TRAP-TYPE
   ENTERPRISE wbt3
   VARIABLES   { wbt3CurBuildNum, wbt3CurOEMBuildNum, wbt3CurModBuildDate,
                 wbt3DUpBuildNum, wbt3DUpOEMBuildNum, wbt3DUpOEMBuildDate}
   DESCRIPTION
      "Firmware build number mismatch according to information
       supplied by DHCP server."
   ::= 1

wbt3TrapDHCPUpdDone TRAP-TYPE
   ENTERPRISE wbt3
   VARIABLES   { wbt3CurBuildNum, wbt3CurOEMBuildNum, wbt3CurModBuildDate,
                 wbt3DUpBuildNum, wbt3DUpOEMBuildNum, wbt3DUpOEMBuildDate}
   DESCRIPTION
      "Firmware upgrade initiated due to build number mismatch according
       to DHCP information is done."
   ::= 2

wbt3TrapDHCPUpdNotComplete TRAP-TYPE
   ENTERPRISE wbt3
   VARIABLES   { wbt3CurBuildNum, wbt3CurOEMBuildNum, wbt3CurModBuildDate,
                 wbt3DUpBuildNum, wbt3DUpOEMBuildNum, wbt3DUpOEMBuildDate,
                 wbt3TrapStatus}
   DESCRIPTION
      "Firmware upgrade initiated due to build number mismatch
       according to DHCP information is not completed for some reason."
   ::= 3

wbt3TrapSNMPAccptLd TRAP-TYPE
   ENTERPRISE wbt3
   VARIABLES   { wbt3SubmitLoadJob }
   DESCRIPTION
      "Ready to accept up/download request initiated by SNMP manager."
   ::= 4

wbt3TrapSNMPLdDone TRAP-TYPE
   ENTERPRISE wbt3
   VARIABLES   { wbt3TrapReqId }
   DESCRIPTION
      "SNMP initiated up/download request is done."
   ::= 5

wbt3TrapSNMPLdNotComplete TRAP-TYPE
   ENTERPRISE wbt3
   VARIABLES   { wbt3TrapReqId, wbt3TrapStatus }
   DESCRIPTION
      "SNMP initiated up/download request is not completed for some reason."
   ::= 6

wbt3TrapRebootNotComplete TRAP-TYPE
   ENTERPRISE wbt3
   VARIABLES   { wbt3TrapStatus }
   DESCRIPTION
      "SNMP initiated reboot request is not completed for some reason."
   ::= 7


END
