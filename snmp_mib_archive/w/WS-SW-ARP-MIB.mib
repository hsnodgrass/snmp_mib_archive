--
-- WS-SW-ARP-MIB.my
-- MIB generated by MG-SOFT Visual MIB Builder Version 6.0  Build 88
-- Wednesday, May 24, 2006 at 16:43:04
--

	WS-SW-ARP-MIB DEFINITIONS ::= BEGIN
 
		IMPORTS
			OBJECT-GROUP, MODULE-COMPLIANCE			
				FROM SNMPv2-CONF			
			OBJECT-TYPE, MODULE-IDENTITY			
				FROM SNMPv2-SMI			
			wsSwArp			
				FROM WS-SW-SMI;
	
	
		-- 1.3.6.1.4.1.388.14.2.7.1
		wsSwArpMIB MODULE-IDENTITY 
			LAST-UPDATED "200509201549Z"		-- September 20, 2005 at 15:49 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Description."
			REVISION "200605241628Z"		-- May 24, 2006 at 16:28 GMT
			DESCRIPTION 
				"01a02"
			REVISION "200509201549Z"		-- September 20, 2005 at 15:49 GMT
			DESCRIPTION 
				"01a01"
			::= { wsSwArp 1 }

		
	
--
-- Node definitions
--
	
		-- 1.3.6.1.4.1.388.14.2.7.1.1
		wsSwArpCachClear OBJECT-TYPE
			SYNTAX INTEGER
				{
				idle(1),
				clearCach(2)
				}
			MAX-ACCESS read-write
			STATUS current
			DESCRIPTION
				"Description."
			::= { wsSwArpMIB 1 }

		
		-- 1.3.6.1.4.1.388.14.2.7.1.100
		wsSwArpMIBConformance OBJECT IDENTIFIER ::= { wsSwArpMIB 100 }

		
		-- 1.3.6.1.4.1.388.14.2.7.1.100.1
		wsSwArpCompliances OBJECT IDENTIFIER ::= { wsSwArpMIBConformance 1 }

		
		-- 1.3.6.1.4.1.388.14.2.7.1.100.1.1
		wsSwArpCompliance MODULE-COMPLIANCE
			STATUS current
			DESCRIPTION 
				"Description."
			MODULE -- this module
				MANDATORY-GROUPS { wsSwArpGroup }
			::= { wsSwArpCompliances 1 }

		
		-- 1.3.6.1.4.1.388.14.2.7.1.100.2
		wsSwArpGroups OBJECT IDENTIFIER ::= { wsSwArpMIBConformance 2 }

		
		-- 1.3.6.1.4.1.388.14.2.7.1.100.2.1
		wsSwArpGroup OBJECT-GROUP
			OBJECTS { wsSwArpCachClear }
			STATUS current
			DESCRIPTION 
				"Description."
			::= { wsSwArpGroups 1 }

		
	
	END

--
-- WS-SW-ARP-MIB.my
--
