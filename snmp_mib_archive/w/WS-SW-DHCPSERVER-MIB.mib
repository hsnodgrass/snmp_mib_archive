--
-- WS-SW-DHCPSERVER-MIB.my
-- MIB generated by MG-SOFT Visual MIB Builder Version 6.0  Build 88
-- Sunday, March 02, 2008 at 21:13:34
--

	WS-SW-DHCPSERVER-MIB DEFINITIONS ::= BEGIN
 
		IMPORTS
			OBJECT-GROUP, MODULE-COMPLIANCE			
				FROM SNMPv2-CONF			
			IpAddress, Unsigned32, OBJECT-TYPE, MODULE-IDENTITY			
				FROM SNMPv2-SMI			
			RowStatus, TruthValue, DisplayString, PhysAddress, DateAndTime			
				FROM SNMPv2-TC			
			wsSwDHCP			
				FROM WS-SW-SMI			
			AbbrevRowStatus			
				FROM WS-TYPE-MIB;
	
	
		-- 1.3.6.1.4.1.388.14.2.3.5
		wsSwDhcpServerModule MODULE-IDENTITY 
			LAST-UPDATED "200803022115Z"		-- March 02, 2008 at 21:15 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"This module contains DHCP server MIB definition"
			REVISION "200803022100Z"		-- March 02, 2008 at 21:00 GMT
			DESCRIPTION 
				"02a23
				1. Removed wsSwDhcpSvrPoolOptionValue from the INDEX of
				   wsSwDhcpSvrPoolOptionTable
				2. Changed maximum SIZE of wsSwDhcpSvrPoolOptionValue
				   from 32 to 75."
			REVISION "200710251206Z"		-- October 25, 2007 at 12:06 GMT
			DESCRIPTION 
				"02a22
				Deprecated wsSwDhcpSvrRestart.
				Renamed wsSwDhcpSvrObsoleteGroup to 
				wsSwDhcpSvrDeprecatedGroup.
				Fixed the size range of some 
				DisplayString objects."
			REVISION "200701100730Z"		-- January 10, 2007 at 07:30 GMT
			DESCRIPTION 
				"02a21"
			REVISION "200611291042Z"		-- November 29, 2006 at 10:42 GMT
			DESCRIPTION 
				"02a20"
			REVISION "200607120031Z"		-- July 12, 2006 at 00:31 GMT
			DESCRIPTION 
				"02a19"
			REVISION "200607110532Z"		-- July 11, 2006 at 05:32 GMT
			DESCRIPTION 
				"02a18"
			REVISION "200607080450Z"		-- July 08, 2006 at 04:50 GMT
			DESCRIPTION 
				"02a17"
			REVISION "200606051329Z"		-- June 05, 2006 at 13:29 GMT
			DESCRIPTION 
				"02a16"
			REVISION "200605241649Z"		-- May 24, 2006 at 16:49 GMT
			DESCRIPTION 
				"02a15"
			REVISION "200605161109Z"		-- May 16, 2006 at 11:09 GMT
			DESCRIPTION 
				"02a14"
			REVISION "200605121636Z"		-- May 12, 2006 at 16:36 GMT
			DESCRIPTION 
				"02a13"
			REVISION "200605121201Z"		-- May 12, 2006 at 12:01 GMT
			DESCRIPTION 
				"02a12"
			REVISION "200605121126Z"		-- May 12, 2006 at 11:26 GMT
			DESCRIPTION 
				"02a11"
			REVISION "200605121056Z"		-- May 12, 2006 at 10:56 GMT
			DESCRIPTION 
				"02a10"
			REVISION "200605111743Z"		-- May 11, 2006 at 17:43 GMT
			DESCRIPTION 
				"02a09"
			REVISION "200605101652Z"		-- May 10, 2006 at 16:52 GMT
			DESCRIPTION 
				"02a08"
			REVISION "200605031047Z"		-- May 03, 2006 at 10:47 GMT
			DESCRIPTION 
				"02a07"
			REVISION "200605011334Z"		-- May 01, 2006 at 13:34 GMT
			DESCRIPTION 
				"02a06"
			REVISION "200604271333Z"		-- April 27, 2006 at 13:33 GMT
			DESCRIPTION 
				"02a05"
			REVISION "200604251354Z"		-- April 25, 2006 at 13:54 GMT
			DESCRIPTION 
				"02a04"
			REVISION "200604201016Z"		-- April 20, 2006 at 10:16 GMT
			DESCRIPTION 
				"02a03"
			REVISION "200604191409Z"		-- April 19, 2006 at 14:09 GMT
			DESCRIPTION 
				"02a02"
			REVISION "200604141145Z"		-- April 14, 2006 at 11:45 GMT
			DESCRIPTION 
				"02a01"
			::= { wsSwDHCP 5 }

		
	
	
	
--
-- Node definitions
--
	
		-- 1.3.6.1.4.1.388.14.2.3.5.1
		wsSwDhcpSvrGlobal OBJECT IDENTIFIER ::= { wsSwDhcpServerModule 1 }

		
		-- 1.3.6.1.4.1.388.14.2.3.5.1.1
		wsSwDhcpSvrBootp OBJECT-TYPE
			SYNTAX TruthValue
			MAX-ACCESS read-write
			STATUS current
			DESCRIPTION
				"Allow /Ignore Bootp requests "
			::= { wsSwDhcpSvrGlobal 1 }

		
		-- 1.3.6.1.4.1.388.14.2.3.5.1.2
		wsSwDhcpSvrPingInterval OBJECT-TYPE
			SYNTAX INTEGER (1..10)
			MAX-ACCESS read-write
			STATUS current
			DESCRIPTION
				"Ping time interval"
			::= { wsSwDhcpSvrGlobal 2 }

		
		-- 1.3.6.1.4.1.388.14.2.3.5.1.3
		wsSwDhcpSvrEnable OBJECT-TYPE
			SYNTAX TruthValue
			MAX-ACCESS read-write
			STATUS current
			DESCRIPTION
				"Description."
			::= { wsSwDhcpSvrGlobal 3 }

		
		-- 1.3.6.1.4.1.388.14.2.3.5.1.4
		wsSwDhcpSvrRestart OBJECT-TYPE
			SYNTAX INTEGER
				{
				restart(1),
				idle(2)
				}
			MAX-ACCESS read-write
			STATUS deprecated
			DESCRIPTION
				"dhcp svr restart"
			::= { wsSwDhcpSvrGlobal 4 }

		
		-- 1.3.6.1.4.1.388.14.2.3.5.1.5
		wsSwDhcpSvrStatus OBJECT-TYPE
			SYNTAX INTEGER
				{
				running(1),
				stopped(2)
				}
			MAX-ACCESS read-only
			STATUS current
			DESCRIPTION
				"Description."
			::= { wsSwDhcpSvrGlobal 5 }

		
		-- 1.3.6.1.4.1.388.14.2.3.5.1.6
		wsSwDhcpSvrLastErrorMsg OBJECT-TYPE
			SYNTAX DisplayString
			MAX-ACCESS read-only
			STATUS current
			DESCRIPTION
				"Description."
			::= { wsSwDhcpSvrGlobal 6 }

		
		-- 1.3.6.1.4.1.388.14.2.3.5.1.7
		wsSwDhcpDeleteAllLease OBJECT-TYPE
			SYNTAX TruthValue
			MAX-ACCESS read-write
			STATUS current
			DESCRIPTION
				"This is set only OID. Get on this OID will always return false. This is used to delete all the DHCP bindings."
			::= { wsSwDhcpSvrGlobal 7 }

		
		-- 1.3.6.1.4.1.388.14.2.3.5.2
		wsSwDhcpSvrExcludeTable OBJECT-TYPE
			SYNTAX SEQUENCE OF WsSwDhcpSvrExcludeEntry
			MAX-ACCESS not-accessible
			STATUS current
			DESCRIPTION
				"Description."
			::= { wsSwDhcpServerModule 2 }

		
		-- 1.3.6.1.4.1.388.14.2.3.5.2.1
		wsSwDhcpSvrExcludeEntry OBJECT-TYPE
			SYNTAX WsSwDhcpSvrExcludeEntry
			MAX-ACCESS not-accessible
			STATUS current
			DESCRIPTION
				"Description."
			INDEX { wsSwDhcpSvrExcludeLowIpAddr, wsSwDhcpSvrExcludeHighIpAddr }
			::= { wsSwDhcpSvrExcludeTable 1 }

		
		WsSwDhcpSvrExcludeEntry ::=
			SEQUENCE { 
				wsSwDhcpSvrExcludeLowIpAddr
					IpAddress,
				wsSwDhcpSvrExcludeHighIpAddr
					DisplayString,
				wsSwDhcpSvrExcludeRowStatus
					RowStatus
			 }

		-- 1.3.6.1.4.1.388.14.2.3.5.2.1.1
		wsSwDhcpSvrExcludeLowIpAddr OBJECT-TYPE
			SYNTAX IpAddress
			MAX-ACCESS read-only
			STATUS current
			DESCRIPTION
				"Excluded low address"
			::= { wsSwDhcpSvrExcludeEntry 1 }

		
		-- 1.3.6.1.4.1.388.14.2.3.5.2.1.2
		wsSwDhcpSvrExcludeHighIpAddr OBJECT-TYPE
			SYNTAX DisplayString
			MAX-ACCESS read-only
			STATUS current
			DESCRIPTION
				"Excluded high address"
			::= { wsSwDhcpSvrExcludeEntry 2 }

		
		-- 1.3.6.1.4.1.388.14.2.3.5.2.1.3
		wsSwDhcpSvrExcludeRowStatus OBJECT-TYPE
			SYNTAX RowStatus
			MAX-ACCESS read-create
			STATUS current
			DESCRIPTION
				"row status of wsSwDhcpSvrExcludeEntry"
			::= { wsSwDhcpSvrExcludeEntry 3 }

		
		-- 1.3.6.1.4.1.388.14.2.3.5.3
		wsSwDhcpSvrPoolTable OBJECT-TYPE
			SYNTAX SEQUENCE OF WsSwDhcpSvrPoolEntry
			MAX-ACCESS not-accessible
			STATUS current
			DESCRIPTION
				"Description."
			::= { wsSwDhcpServerModule 3 }

		
		-- 1.3.6.1.4.1.388.14.2.3.5.3.1
		wsSwDhcpSvrPoolEntry OBJECT-TYPE
			SYNTAX WsSwDhcpSvrPoolEntry
			MAX-ACCESS not-accessible
			STATUS current
			DESCRIPTION
				"Description."
			INDEX { wsSwDhcpSvrPoolNameIndex }
			::= { wsSwDhcpSvrPoolTable 1 }

		
		WsSwDhcpSvrPoolEntry ::=
			SEQUENCE { 
				wsSwDhcpSvrPoolNameIndex
					DisplayString,
				wsSwDhcpSvrPoolType
					INTEGER,
				wsSwDhcpSvrPoolHostIp
					IpAddress,
				wsSwDhcpSvrPoolSubnetIpAndMask
					DisplayString,
				wsSwDhcpSvrPoolClientId
					OCTET STRING,
				wsSwDhcpSvrPoolClientName
					DisplayString,
				wsSwDhcpSvrPoolHardWareAddrAndType
					DisplayString,
				wsSwDhcpSvrPoolDomainName
					DisplayString,
				wsSwDhcpSvrPoolNetBiosNodeType
					INTEGER,
				wsSwDhcpSvrPoolBootfile
					DisplayString,
				wsSwDhcpSvrPoolDdnsUpdate
					INTEGER,
				wsSwDhcpSvrPoolDdnsUpdateAll
					INTEGER,
				wsSwDhcpSvrPoolDdnsIp
					DisplayString,
				wsSwDhcpSvrPoolDdnsDomainName
					DisplayString,
				wsSwDhcpSvrPoolDdnsTtl
					INTEGER,
				wsSwDhcpSvrPoolDdnsMultiUserClass
					TruthValue,
				wsSwDhcpSvrPoolDefaultRouter
					DisplayString,
				wsSwDhcpSvrPoolBootpNextSvrIP
					IpAddress,
				wsSwDhcpSvrPoolDnsSvrIP
					DisplayString,
				wsSwDhcpSvrPoolNetbiosSvrIP
					DisplayString,
				wsSwDhcpSvrPoolNoDefault
					INTEGER,
				wsSwDhcpSvrPoolLeaseTime
					DisplayString,
				wsSwDhcpSvrPoolRowStatus
					RowStatus
			 }

		-- 1.3.6.1.4.1.388.14.2.3.5.3.1.1
		wsSwDhcpSvrPoolNameIndex OBJECT-TYPE
			SYNTAX DisplayString (SIZE (1..32))
			MAX-ACCESS read-only
			STATUS current
			DESCRIPTION
				"index of wsSwDhcpSvrPoolTable"
			::= { wsSwDhcpSvrPoolEntry 1 }

		
		-- 1.3.6.1.4.1.388.14.2.3.5.3.1.2
		wsSwDhcpSvrPoolType OBJECT-TYPE
			SYNTAX INTEGER
				{
				unDefined(0),
				network(1),
				host(2)
				}
			MAX-ACCESS read-only
			STATUS current
			DESCRIPTION
				"Description."
			::= { wsSwDhcpSvrPoolEntry 2 }

		
		-- 1.3.6.1.4.1.388.14.2.3.5.3.1.3
		wsSwDhcpSvrPoolHostIp OBJECT-TYPE
			SYNTAX IpAddress
			MAX-ACCESS read-create
			STATUS current
			DESCRIPTION
				"Description."
			::= { wsSwDhcpSvrPoolEntry 3 }

		
		-- 1.3.6.1.4.1.388.14.2.3.5.3.1.4
		wsSwDhcpSvrPoolSubnetIpAndMask OBJECT-TYPE
			SYNTAX DisplayString
			MAX-ACCESS read-create
			STATUS current
			DESCRIPTION
				"subnet IP and mask"
			::= { wsSwDhcpSvrPoolEntry 4 }

		
		-- 1.3.6.1.4.1.388.14.2.3.5.3.1.5
		wsSwDhcpSvrPoolClientId OBJECT-TYPE
			SYNTAX OCTET STRING
			MAX-ACCESS read-create
			STATUS current
			DESCRIPTION
				"client identifier
				
				To prepend Null character use \0 at the beginning."
			::= { wsSwDhcpSvrPoolEntry 5 }

		
		-- 1.3.6.1.4.1.388.14.2.3.5.3.1.6
		wsSwDhcpSvrPoolClientName OBJECT-TYPE
			SYNTAX DisplayString
			MAX-ACCESS read-create
			STATUS current
			DESCRIPTION
				"Description."
			::= { wsSwDhcpSvrPoolEntry 6 }

		
		-- 1.3.6.1.4.1.388.14.2.3.5.3.1.7
		wsSwDhcpSvrPoolHardWareAddrAndType OBJECT-TYPE
			SYNTAX DisplayString
			MAX-ACCESS read-create
			STATUS current
			DESCRIPTION
				"Hardware address and hardware type for the pool. Hardware type is optional. Default hardware type is ethernet
				Input formats are 
				XX:XX:XX:XX:XX:XX
				or
				XX:XX:XX:XX:XX:XX,ethernet 
				or
				XX:XX:XX:XX:XX:XX,token-ring"
			::= { wsSwDhcpSvrPoolEntry 7 }

		
		-- 1.3.6.1.4.1.388.14.2.3.5.3.1.8
		wsSwDhcpSvrPoolDomainName OBJECT-TYPE
			SYNTAX DisplayString
			MAX-ACCESS read-create
			STATUS current
			DESCRIPTION
				"Domain name"
			::= { wsSwDhcpSvrPoolEntry 8 }

		
		-- 1.3.6.1.4.1.388.14.2.3.5.3.1.9
		wsSwDhcpSvrPoolNetBiosNodeType OBJECT-TYPE
			SYNTAX INTEGER
				{
				undefined(0),
				nodeB(1),
				nodeP(2),
				nodeM(4),
				nodeH(8)
				}
			MAX-ACCESS read-create
			STATUS current
			DESCRIPTION
				"etbios-node-type"
			::= { wsSwDhcpSvrPoolEntry 9 }

		
		-- 1.3.6.1.4.1.388.14.2.3.5.3.1.10
		wsSwDhcpSvrPoolBootfile OBJECT-TYPE
			SYNTAX DisplayString
			MAX-ACCESS read-create
			STATUS current
			DESCRIPTION
				"boot file name"
			::= { wsSwDhcpSvrPoolEntry 10 }

		
		-- 1.3.6.1.4.1.388.14.2.3.5.3.1.11
		wsSwDhcpSvrPoolDdnsUpdate OBJECT-TYPE
			SYNTAX INTEGER
				{
				noUpdate(0),
				serverUpdate(1),
				clientUpdate(2)
				}
			MAX-ACCESS read-create
			STATUS current
			DESCRIPTION
				"DDNS updates"
			::= { wsSwDhcpSvrPoolEntry 11 }

		
		-- 1.3.6.1.4.1.388.14.2.3.5.3.1.12
		wsSwDhcpSvrPoolDdnsUpdateAll OBJECT-TYPE
			SYNTAX INTEGER
				{
				updateAll(1),
				idle(2)
				}
			MAX-ACCESS read-create
			STATUS deprecated
			DESCRIPTION
				"DDNS Update All functionality will not be supported anymore."
			::= { wsSwDhcpSvrPoolEntry 12 }

		
		-- 1.3.6.1.4.1.388.14.2.3.5.3.1.13
		wsSwDhcpSvrPoolDdnsIp OBJECT-TYPE
			SYNTAX DisplayString
			MAX-ACCESS read-create
			STATUS current
			DESCRIPTION
				"This can take a max of 2 IP addresses in the format IP1, IP2. 
				To remove just IP1 use any of the following formats
				,IP2   or
				0.0.0.0,IP2
				To remove just IP2 use any of the following formats
				IP1,   or
				IP1,0.0.0.0
				To remove both IP addresses use any of the following formats
				(blank string or zero length string) or
				,
				"
			::= { wsSwDhcpSvrPoolEntry 13 }

		
		-- 1.3.6.1.4.1.388.14.2.3.5.3.1.14
		wsSwDhcpSvrPoolDdnsDomainName OBJECT-TYPE
			SYNTAX DisplayString
			MAX-ACCESS read-create
			STATUS current
			DESCRIPTION
				"DDNS domain name"
			::= { wsSwDhcpSvrPoolEntry 14 }

		
		-- 1.3.6.1.4.1.388.14.2.3.5.3.1.15
		wsSwDhcpSvrPoolDdnsTtl OBJECT-TYPE
			SYNTAX INTEGER (-1 | 1..864000)
			MAX-ACCESS read-create
			STATUS current
			DESCRIPTION
				"DDNS TTL value. This OID can take values in range 1 to 864000. The value -1 is used to remove the configured value."
			::= { wsSwDhcpSvrPoolEntry 15 }

		
		-- 1.3.6.1.4.1.388.14.2.3.5.3.1.16
		wsSwDhcpSvrPoolDdnsMultiUserClass OBJECT-TYPE
			SYNTAX TruthValue
			MAX-ACCESS read-create
			STATUS current
			DESCRIPTION
				"enable/disable DDNS multi user class"
			::= { wsSwDhcpSvrPoolEntry 16 }

		
		-- 1.3.6.1.4.1.388.14.2.3.5.3.1.17
		wsSwDhcpSvrPoolDefaultRouter OBJECT-TYPE
			SYNTAX DisplayString
			MAX-ACCESS read-create
			STATUS current
			DESCRIPTION
				"Default Router, the format is xxx.xxx.xxx.xxx, yyy.yyy.yyy.yy,..., the maximum number of the router entry is 8"
			::= { wsSwDhcpSvrPoolEntry 17 }

		
		-- 1.3.6.1.4.1.388.14.2.3.5.3.1.18
		wsSwDhcpSvrPoolBootpNextSvrIP OBJECT-TYPE
			SYNTAX IpAddress
			MAX-ACCESS read-create
			STATUS current
			DESCRIPTION
				"bootp next server address, set it to 0.0.0.0 means there is no bootp next server address"
			::= { wsSwDhcpSvrPoolEntry 18 }

		
		-- 1.3.6.1.4.1.388.14.2.3.5.3.1.19
		wsSwDhcpSvrPoolDnsSvrIP OBJECT-TYPE
			SYNTAX DisplayString
			MAX-ACCESS read-create
			STATUS current
			DESCRIPTION
				"dns server address, the format is xxx.xxx.xxx.xxx, yyy.yyy.yyy.yy,..., the maximum number of the server entry is 8"
			::= { wsSwDhcpSvrPoolEntry 19 }

		
		-- 1.3.6.1.4.1.388.14.2.3.5.3.1.20
		wsSwDhcpSvrPoolNetbiosSvrIP OBJECT-TYPE
			SYNTAX DisplayString
			MAX-ACCESS read-create
			STATUS current
			DESCRIPTION
				"net bios server address, the format is xxx.xxx.xxx.xxx, yyy.yyy.yyy.yy,..., the maximum number of the server entry is 8"
			::= { wsSwDhcpSvrPoolEntry 20 }

		
		-- 1.3.6.1.4.1.388.14.2.3.5.3.1.21
		wsSwDhcpSvrPoolNoDefault OBJECT-TYPE
			SYNTAX INTEGER
				{
				noDefaultRouter(1),
				noDnsSvrIP(2),
				noNetbiosSvrIP(3),
				idle(4)
				}
			MAX-ACCESS read-create
			STATUS current
			DESCRIPTION
				"No default"
			::= { wsSwDhcpSvrPoolEntry 21 }

		
		-- 1.3.6.1.4.1.388.14.2.3.5.3.1.22
		wsSwDhcpSvrPoolLeaseTime OBJECT-TYPE
			SYNTAX DisplayString
			MAX-ACCESS read-create
			STATUS current
			DESCRIPTION
				"Lease time, the format is XX:YY:ZZ, which represents days:hours:mins. 00:00:00 means infinite lease"
			::= { wsSwDhcpSvrPoolEntry 22 }

		
		-- 1.3.6.1.4.1.388.14.2.3.5.3.1.23
		wsSwDhcpSvrPoolRowStatus OBJECT-TYPE
			SYNTAX RowStatus
			MAX-ACCESS read-create
			STATUS current
			DESCRIPTION
				"row status of wsSwDhcpSvrPoolTable"
			::= { wsSwDhcpSvrPoolEntry 23 }

		
		-- 1.3.6.1.4.1.388.14.2.3.5.4
		wsSwDhcpSvrIncludeTable OBJECT-TYPE
			SYNTAX SEQUENCE OF WsSwDhcpSvrIncludeEntry
			MAX-ACCESS not-accessible
			STATUS current
			DESCRIPTION
				"Description."
			::= { wsSwDhcpServerModule 4 }

		
		-- 1.3.6.1.4.1.388.14.2.3.5.4.1
		wsSwDhcpSvrIncludeEntry OBJECT-TYPE
			SYNTAX WsSwDhcpSvrIncludeEntry
			MAX-ACCESS not-accessible
			STATUS current
			DESCRIPTION
				"Description."
			INDEX { wsSwDhcpSvrPoolNameIndex, wsSwDhcpSvrIncludeLowIP, wsSwDhcpSvrIncludeHighIP }
			::= { wsSwDhcpSvrIncludeTable 1 }

		
		WsSwDhcpSvrIncludeEntry ::=
			SEQUENCE { 
				wsSwDhcpSvrIncludeLowIP
					IpAddress,
				wsSwDhcpSvrIncludeHighIP
					DisplayString,
				wsSwDhcpSvrIncludeRowStatus
					RowStatus
			 }

		-- 1.3.6.1.4.1.388.14.2.3.5.4.1.1
		wsSwDhcpSvrIncludeLowIP OBJECT-TYPE
			SYNTAX IpAddress
			MAX-ACCESS read-only
			STATUS current
			DESCRIPTION
				"Included low address"
			::= { wsSwDhcpSvrIncludeEntry 1 }

		
		-- 1.3.6.1.4.1.388.14.2.3.5.4.1.2
		wsSwDhcpSvrIncludeHighIP OBJECT-TYPE
			SYNTAX DisplayString
			MAX-ACCESS read-only
			STATUS current
			DESCRIPTION
				"Included high address"
			::= { wsSwDhcpSvrIncludeEntry 2 }

		
		-- 1.3.6.1.4.1.388.14.2.3.5.4.1.3
		wsSwDhcpSvrIncludeRowStatus OBJECT-TYPE
			SYNTAX RowStatus
			MAX-ACCESS read-create
			STATUS current
			DESCRIPTION
				"row status of wsSwDhcpSvrIncludeTable"
			::= { wsSwDhcpSvrIncludeEntry 3 }

		
		-- 1.3.6.1.4.1.388.14.2.3.5.5
		wsSwDhcpSvrPoolOptionTable OBJECT-TYPE
			SYNTAX SEQUENCE OF WsSwDhcpSvrPoolOptionEntry
			MAX-ACCESS not-accessible
			STATUS current
			DESCRIPTION
				"Description."
			::= { wsSwDhcpServerModule 5 }

		
		-- 1.3.6.1.4.1.388.14.2.3.5.5.1
		wsSwDhcpSvrPoolOptionEntry OBJECT-TYPE
			SYNTAX WsSwDhcpSvrPoolOptionEntry
			MAX-ACCESS not-accessible
			STATUS current
			DESCRIPTION
				"Description."
			INDEX { wsSwDhcpSvrPoolNameIndex, wsSwDhcpSvrPoolOptionName }
			::= { wsSwDhcpSvrPoolOptionTable 1 }

		
		WsSwDhcpSvrPoolOptionEntry ::=
			SEQUENCE { 
				wsSwDhcpSvrPoolOptionName
					DisplayString,
				wsSwDhcpSvrPoolOptionValue
					DisplayString,
				wsSwDhcpSvrPoolOptionRowStatus
					RowStatus
			 }

		-- 1.3.6.1.4.1.388.14.2.3.5.5.1.1
		wsSwDhcpSvrPoolOptionName OBJECT-TYPE
			SYNTAX DisplayString (SIZE (1..32))
			MAX-ACCESS read-only
			STATUS current
			DESCRIPTION
				"option name"
			::= { wsSwDhcpSvrPoolOptionEntry 1 }

		
		-- 1.3.6.1.4.1.388.14.2.3.5.5.1.2
		wsSwDhcpSvrPoolOptionValue OBJECT-TYPE
			SYNTAX DisplayString (SIZE (1..75))
			MAX-ACCESS read-create
			STATUS current
			DESCRIPTION
				"option tpe"
			::= { wsSwDhcpSvrPoolOptionEntry 2 }

		
		-- 1.3.6.1.4.1.388.14.2.3.5.5.1.3
		wsSwDhcpSvrPoolOptionRowStatus OBJECT-TYPE
			SYNTAX RowStatus
			MAX-ACCESS read-create
			STATUS current
			DESCRIPTION
				"row status of the table"
			::= { wsSwDhcpSvrPoolOptionEntry 3 }

		
		-- 1.3.6.1.4.1.388.14.2.3.5.6
		wsSwDhcpBindingStatusTable OBJECT-TYPE
			SYNTAX SEQUENCE OF WsSwDhcpBindingStatusEntry
			MAX-ACCESS not-accessible
			STATUS current
			DESCRIPTION
				"Description."
			::= { wsSwDhcpServerModule 6 }

		
		-- 1.3.6.1.4.1.388.14.2.3.5.6.1
		wsSwDhcpBindingStatusEntry OBJECT-TYPE
			SYNTAX WsSwDhcpBindingStatusEntry
			MAX-ACCESS not-accessible
			STATUS current
			DESCRIPTION
				"Description."
			INDEX { wsSwDhcpBindingStatusIp }
			::= { wsSwDhcpBindingStatusTable 1 }

		
		WsSwDhcpBindingStatusEntry ::=
			SEQUENCE { 
				wsSwDhcpBindingStatusIp
					IpAddress,
				wsSwDhcpBindingStatusHardwareAddr
					DisplayString,
				wsSwDhcpBindingStatusClientID
					DisplayString,
				wsSwDhcpBindingStatusLeaseExpired
					DisplayString,
				wsSwDhcpBindingStatusLeaseType
					INTEGER,
				wsSwDhcpBindingStatusRowStatus
					RowStatus
			 }

		-- 1.3.6.1.4.1.388.14.2.3.5.6.1.1
		wsSwDhcpBindingStatusIp OBJECT-TYPE
			SYNTAX IpAddress
			MAX-ACCESS read-only
			STATUS current
			DESCRIPTION
				"IP address of binding"
			::= { wsSwDhcpBindingStatusEntry 1 }

		
		-- 1.3.6.1.4.1.388.14.2.3.5.6.1.2
		wsSwDhcpBindingStatusHardwareAddr OBJECT-TYPE
			SYNTAX DisplayString
			MAX-ACCESS read-only
			STATUS current
			DESCRIPTION
				"Hardware address"
			::= { wsSwDhcpBindingStatusEntry 2 }

		
		-- 1.3.6.1.4.1.388.14.2.3.5.6.1.3
		wsSwDhcpBindingStatusClientID OBJECT-TYPE
			SYNTAX DisplayString
			MAX-ACCESS read-only
			STATUS current
			DESCRIPTION
				"Description."
			::= { wsSwDhcpBindingStatusEntry 3 }

		
		-- 1.3.6.1.4.1.388.14.2.3.5.6.1.4
		wsSwDhcpBindingStatusLeaseExpired OBJECT-TYPE
			SYNTAX DisplayString
			MAX-ACCESS read-only
			STATUS current
			DESCRIPTION
				"Lease expiration"
			::= { wsSwDhcpBindingStatusEntry 4 }

		
		-- 1.3.6.1.4.1.388.14.2.3.5.6.1.5
		wsSwDhcpBindingStatusLeaseType OBJECT-TYPE
			SYNTAX INTEGER
				{
				automatic(0),
				manual(1)
				}
			MAX-ACCESS read-only
			STATUS deprecated
			DESCRIPTION
				"Description."
			::= { wsSwDhcpBindingStatusEntry 5 }

		
		-- 1.3.6.1.4.1.388.14.2.3.5.6.1.6
		wsSwDhcpBindingStatusRowStatus OBJECT-TYPE
			SYNTAX RowStatus
			MAX-ACCESS read-create
			STATUS current
			DESCRIPTION
				"only delete is supported in this row-status."
			::= { wsSwDhcpBindingStatusEntry 6 }

		
		-- 1.3.6.1.4.1.388.14.2.3.5.7
		wsSwDhcpSvrGlobalOptionTable OBJECT-TYPE
			SYNTAX SEQUENCE OF WsSwDhcpSvrGlobalOptionEntry
			MAX-ACCESS not-accessible
			STATUS current
			DESCRIPTION
				"Description."
			::= { wsSwDhcpServerModule 7 }

		
		-- 1.3.6.1.4.1.388.14.2.3.5.7.1
		wsSwDhcpSvrGlobalOptionEntry OBJECT-TYPE
			SYNTAX WsSwDhcpSvrGlobalOptionEntry
			MAX-ACCESS not-accessible
			STATUS current
			DESCRIPTION
				"Description."
			INDEX { wsSwDhcpSvrGlobalOptionName, wsSwDhcpSvrGlobalOptionCode, wsSwDhcpSvrGlobalOptionType }
			::= { wsSwDhcpSvrGlobalOptionTable 1 }

		
		WsSwDhcpSvrGlobalOptionEntry ::=
			SEQUENCE { 
				wsSwDhcpSvrGlobalOptionName
					DisplayString,
				wsSwDhcpSvrGlobalOptionCode
					Unsigned32,
				wsSwDhcpSvrGlobalOptionType
					INTEGER,
				wsSwDhcpSvrGlobalOptionRowStatus
					RowStatus
			 }

		-- 1.3.6.1.4.1.388.14.2.3.5.7.1.1
		wsSwDhcpSvrGlobalOptionName OBJECT-TYPE
			SYNTAX DisplayString (SIZE (1..32))
			MAX-ACCESS read-only
			STATUS current
			DESCRIPTION
				"Description."
			::= { wsSwDhcpSvrGlobalOptionEntry 1 }

		
		-- 1.3.6.1.4.1.388.14.2.3.5.7.1.2
		wsSwDhcpSvrGlobalOptionCode OBJECT-TYPE
			SYNTAX Unsigned32 (0..254)
			MAX-ACCESS read-create
			STATUS current
			DESCRIPTION
				"Description."
			::= { wsSwDhcpSvrGlobalOptionEntry 2 }

		
		-- 1.3.6.1.4.1.388.14.2.3.5.7.1.3
		wsSwDhcpSvrGlobalOptionType OBJECT-TYPE
			SYNTAX INTEGER
				{
				ipAddress(0),
				text(1)
				}
			MAX-ACCESS read-create
			STATUS current
			DESCRIPTION
				"Description."
			::= { wsSwDhcpSvrGlobalOptionEntry 3 }

		
		-- 1.3.6.1.4.1.388.14.2.3.5.7.1.4
		wsSwDhcpSvrGlobalOptionRowStatus OBJECT-TYPE
			SYNTAX RowStatus
			MAX-ACCESS read-create
			STATUS current
			DESCRIPTION
				"Description."
			::= { wsSwDhcpSvrGlobalOptionEntry 4 }

		
		-- 1.3.6.1.4.1.388.14.2.3.5.8
		wsSwDhcpRelayTable OBJECT-TYPE
			SYNTAX SEQUENCE OF WsSwDhcpRelayEntry
			MAX-ACCESS not-accessible
			STATUS current
			DESCRIPTION
				"Description."
			::= { wsSwDhcpServerModule 8 }

		
		-- 1.3.6.1.4.1.388.14.2.3.5.8.1
		wsSwDhcpRelayEntry OBJECT-TYPE
			SYNTAX WsSwDhcpRelayEntry
			MAX-ACCESS not-accessible
			STATUS current
			DESCRIPTION
				"Description."
			INDEX { wsSwDhcpRelayInterface }
			::= { wsSwDhcpRelayTable 1 }

		
		WsSwDhcpRelayEntry ::=
			SEQUENCE { 
				wsSwDhcpRelayInterface
					DisplayString,
				wsSwDhcpRelayTarget
					DisplayString,
				wsSwDhcpRelayTargetSet
					DisplayString,
				wsSwDhcpRelayRowStatus
					RowStatus
			 }

		-- 1.3.6.1.4.1.388.14.2.3.5.8.1.1
		wsSwDhcpRelayInterface OBJECT-TYPE
			SYNTAX DisplayString
			MAX-ACCESS read-only
			STATUS current
			DESCRIPTION
				"Interface Name"
			::= { wsSwDhcpRelayEntry 1 }

		
		-- 1.3.6.1.4.1.388.14.2.3.5.8.1.2
		wsSwDhcpRelayTarget OBJECT-TYPE
			SYNTAX DisplayString
			MAX-ACCESS read-only
			STATUS current
			DESCRIPTION
				"This is a read-only attribute which shows the currently configured relay targets in the format Ip,interface;Ip,interface... There can be a maximum of 4 such relay targets."
			::= { wsSwDhcpRelayEntry 2 }

		
		-- 1.3.6.1.4.1.388.14.2.3.5.8.1.3
		wsSwDhcpRelayTargetSet OBJECT-TYPE
			SYNTAX DisplayString
			MAX-ACCESS read-create
			STATUS current
			DESCRIPTION
				"Relay target in the format IP,Iface, where IP is the IP address to which DHCP packets have to be relayed and Iface is the interface name on which response from the relayed DHCP Server is received.
				A maximum of 4 relay targets can be added one at a time. To remove individual relay targets, use the following format
				0:IP, Iface. If there is only one relay target then it cannot be removed. In such a case the entire row has to be deleted."
			::= { wsSwDhcpRelayEntry 3 }

		
		-- 1.3.6.1.4.1.388.14.2.3.5.8.1.4
		wsSwDhcpRelayRowStatus OBJECT-TYPE
			SYNTAX RowStatus
			MAX-ACCESS read-create
			STATUS current
			DESCRIPTION
				"Row status of DHCP Relay Table"
			::= { wsSwDhcpRelayEntry 4 }

		
		-- 1.3.6.1.4.1.388.14.2.3.5.9
		wsSwDhcpSvrClassTable OBJECT-TYPE
			SYNTAX SEQUENCE OF WsSwDhcpSvrClassEntry
			MAX-ACCESS not-accessible
			STATUS current
			DESCRIPTION
				"DHCP Server Class Table. 
				
				Class Table defines a class and associated user class option values."
			::= { wsSwDhcpServerModule 9 }

		
		-- 1.3.6.1.4.1.388.14.2.3.5.9.1
		wsSwDhcpSvrClassEntry OBJECT-TYPE
			SYNTAX WsSwDhcpSvrClassEntry
			MAX-ACCESS not-accessible
			STATUS current
			DESCRIPTION
				"Description."
			INDEX { wsSwDhcpSvrClassName }
			::= { wsSwDhcpSvrClassTable 1 }

		
		WsSwDhcpSvrClassEntry ::=
			SEQUENCE { 
				wsSwDhcpSvrClassName
					DisplayString,
				wsSwDhcpSvrClassUsrClassOptValue1
					DisplayString,
				wsSwDhcpSvrClassUsrClassOptValue2
					DisplayString,
				wsSwDhcpSvrClassUsrClassOptValue3
					DisplayString,
				wsSwDhcpSvrClassUsrClassOptValue4
					DisplayString,
				wsSwDhcpSvrClassUsrClassOptValue5
					DisplayString,
				wsSwDhcpSvrClassUsrClassOptValue6
					DisplayString,
				wsSwDhcpSvrClassUsrClassOptValue7
					DisplayString,
				wsSwDhcpSvrClassUsrClassOptValue8
					DisplayString,
				wsSwDhcpSvrClassMutipleUserClass
					TruthValue,
				wsSwDhcpSvrClassRowStatus
					AbbrevRowStatus
			 }

		-- 1.3.6.1.4.1.388.14.2.3.5.9.1.1
		wsSwDhcpSvrClassName OBJECT-TYPE
			SYNTAX DisplayString (SIZE (1..32))
			MAX-ACCESS read-only
			STATUS current
			DESCRIPTION
				"DHCP Server class name. 
				
				class name indexes into class Table."
			::= { wsSwDhcpSvrClassEntry 1 }

		
		-- 1.3.6.1.4.1.388.14.2.3.5.9.1.2
		wsSwDhcpSvrClassUsrClassOptValue1 OBJECT-TYPE
			SYNTAX DisplayString (SIZE (0..32))
			MAX-ACCESS read-create
			STATUS current
			DESCRIPTION
				"User Class Option Value associated with the class"
			::= { wsSwDhcpSvrClassEntry 2 }

		
		-- 1.3.6.1.4.1.388.14.2.3.5.9.1.3
		wsSwDhcpSvrClassUsrClassOptValue2 OBJECT-TYPE
			SYNTAX DisplayString (SIZE (0..32))
			MAX-ACCESS read-create
			STATUS current
			DESCRIPTION
				"User Class Option Value associated with the class"
			::= { wsSwDhcpSvrClassEntry 3 }

		
		-- 1.3.6.1.4.1.388.14.2.3.5.9.1.4
		wsSwDhcpSvrClassUsrClassOptValue3 OBJECT-TYPE
			SYNTAX DisplayString (SIZE (0..32))
			MAX-ACCESS read-create
			STATUS current
			DESCRIPTION
				"User Class Option Value associated with the class"
			::= { wsSwDhcpSvrClassEntry 4 }

		
		-- 1.3.6.1.4.1.388.14.2.3.5.9.1.5
		wsSwDhcpSvrClassUsrClassOptValue4 OBJECT-TYPE
			SYNTAX DisplayString (SIZE (0..32))
			MAX-ACCESS read-create
			STATUS current
			DESCRIPTION
				"User Class Option Value associated with the class"
			::= { wsSwDhcpSvrClassEntry 5 }

		
		-- 1.3.6.1.4.1.388.14.2.3.5.9.1.6
		wsSwDhcpSvrClassUsrClassOptValue5 OBJECT-TYPE
			SYNTAX DisplayString (SIZE (0..32))
			MAX-ACCESS read-create
			STATUS current
			DESCRIPTION
				"User Class Option Value associated with the class"
			::= { wsSwDhcpSvrClassEntry 6 }

		
		-- 1.3.6.1.4.1.388.14.2.3.5.9.1.7
		wsSwDhcpSvrClassUsrClassOptValue6 OBJECT-TYPE
			SYNTAX DisplayString (SIZE (0..32))
			MAX-ACCESS read-create
			STATUS current
			DESCRIPTION
				"User Class Option Value associated with the class"
			::= { wsSwDhcpSvrClassEntry 7 }

		
		-- 1.3.6.1.4.1.388.14.2.3.5.9.1.8
		wsSwDhcpSvrClassUsrClassOptValue7 OBJECT-TYPE
			SYNTAX DisplayString (SIZE (0..32))
			MAX-ACCESS read-create
			STATUS current
			DESCRIPTION
				"User Class Option Value associated with the class"
			::= { wsSwDhcpSvrClassEntry 8 }

		
		-- 1.3.6.1.4.1.388.14.2.3.5.9.1.9
		wsSwDhcpSvrClassUsrClassOptValue8 OBJECT-TYPE
			SYNTAX DisplayString (SIZE (0..32))
			MAX-ACCESS read-create
			STATUS current
			DESCRIPTION
				"User Class Option Value associated with the class"
			::= { wsSwDhcpSvrClassEntry 9 }

		
		-- 1.3.6.1.4.1.388.14.2.3.5.9.1.10
		wsSwDhcpSvrClassMutipleUserClass OBJECT-TYPE
			SYNTAX TruthValue
			MAX-ACCESS read-create
			STATUS current
			DESCRIPTION
				"It defines weather DHCP clients are configured multiple user class options."
			::= { wsSwDhcpSvrClassEntry 10 }

		
		-- 1.3.6.1.4.1.388.14.2.3.5.9.1.11
		wsSwDhcpSvrClassRowStatus OBJECT-TYPE
			SYNTAX AbbrevRowStatus
			MAX-ACCESS read-create
			STATUS current
			DESCRIPTION
				"Row Status of DHCP Server Class Table "
			::= { wsSwDhcpSvrClassEntry 11 }

		
		-- 1.3.6.1.4.1.388.14.2.3.5.10
		wsSwDhcpSvrPoolClassTable OBJECT-TYPE
			SYNTAX SEQUENCE OF WsSwDhcpSvrPoolClassEntry
			MAX-ACCESS not-accessible
			STATUS current
			DESCRIPTION
				"DHCP Server Pool Class Table. 
				
				Pool Class Table defines association of class to the pool and address ranges associated with the pool class."
			::= { wsSwDhcpServerModule 10 }

		
		-- 1.3.6.1.4.1.388.14.2.3.5.10.1
		wsSwDhcpSvrPoolClassEntry OBJECT-TYPE
			SYNTAX WsSwDhcpSvrPoolClassEntry
			MAX-ACCESS not-accessible
			STATUS current
			DESCRIPTION
				"Description."
			INDEX { wsSwDhcpSvrPoolClassPoolName, wsSwDhcpSvrPoolClassName }
			::= { wsSwDhcpSvrPoolClassTable 1 }

		
		WsSwDhcpSvrPoolClassEntry ::=
			SEQUENCE { 
				wsSwDhcpSvrPoolClassPoolName
					DisplayString,
				wsSwDhcpSvrPoolClassName
					DisplayString,
				wsSwDhcpSvrPoolClassFirstLowIP
					IpAddress,
				wsSwDhcpSvrPoolClassFirstHighIP
					IpAddress,
				wsSwDhcpSvrPoolClassSecLowIP
					IpAddress,
				wsSwDhcpSvrPoolClassSecHighIP
					IpAddress,
				wsSwDhcpSvrPoolClassThirdLowIP
					IpAddress,
				wsSwDhcpSvrPoolClassThirdHighIP
					IpAddress,
				wsSwDhcpSvrPoolClassFourthLowIP
					IpAddress,
				wsSwDhcpSvrPoolClassFourthHighIP
					IpAddress,
				wsSwDhcpSvrPoolClassRowStatus
					AbbrevRowStatus
			 }

		-- 1.3.6.1.4.1.388.14.2.3.5.10.1.1
		wsSwDhcpSvrPoolClassPoolName OBJECT-TYPE
			SYNTAX DisplayString (SIZE (1..32))
			MAX-ACCESS read-only
			STATUS current
			DESCRIPTION
				"DHCP Server pool name
				
				pool name along with class name indexes into pool class table"
			::= { wsSwDhcpSvrPoolClassEntry 1 }

		
		-- 1.3.6.1.4.1.388.14.2.3.5.10.1.2
		wsSwDhcpSvrPoolClassName OBJECT-TYPE
			SYNTAX DisplayString (SIZE (1..32))
			MAX-ACCESS read-only
			STATUS current
			DESCRIPTION
				"Dhcp Server class name
				
				pool name along with class name indexes into pool class table"
			::= { wsSwDhcpSvrPoolClassEntry 2 }

		
		-- 1.3.6.1.4.1.388.14.2.3.5.10.1.3
		wsSwDhcpSvrPoolClassFirstLowIP OBJECT-TYPE
			SYNTAX IpAddress
			MAX-ACCESS read-create
			STATUS current
			DESCRIPTION
				"Pool Class First Address Range: Low Address"
			::= { wsSwDhcpSvrPoolClassEntry 3 }

		
		-- 1.3.6.1.4.1.388.14.2.3.5.10.1.4
		wsSwDhcpSvrPoolClassFirstHighIP OBJECT-TYPE
			SYNTAX IpAddress
			MAX-ACCESS read-create
			STATUS current
			DESCRIPTION
				"Pool Class First Address Range: High Address"
			::= { wsSwDhcpSvrPoolClassEntry 4 }

		
		-- 1.3.6.1.4.1.388.14.2.3.5.10.1.5
		wsSwDhcpSvrPoolClassSecLowIP OBJECT-TYPE
			SYNTAX IpAddress
			MAX-ACCESS read-create
			STATUS current
			DESCRIPTION
				"Pool Class Second Address Range: Low Address"
			::= { wsSwDhcpSvrPoolClassEntry 5 }

		
		-- 1.3.6.1.4.1.388.14.2.3.5.10.1.6
		wsSwDhcpSvrPoolClassSecHighIP OBJECT-TYPE
			SYNTAX IpAddress
			MAX-ACCESS read-create
			STATUS current
			DESCRIPTION
				"Pool Class Second Address Range: High Address"
			::= { wsSwDhcpSvrPoolClassEntry 6 }

		
		-- 1.3.6.1.4.1.388.14.2.3.5.10.1.7
		wsSwDhcpSvrPoolClassThirdLowIP OBJECT-TYPE
			SYNTAX IpAddress
			MAX-ACCESS read-create
			STATUS current
			DESCRIPTION
				"Pool Class Third Address Range: Low Address"
			::= { wsSwDhcpSvrPoolClassEntry 7 }

		
		-- 1.3.6.1.4.1.388.14.2.3.5.10.1.8
		wsSwDhcpSvrPoolClassThirdHighIP OBJECT-TYPE
			SYNTAX IpAddress
			MAX-ACCESS read-create
			STATUS current
			DESCRIPTION
				"Pool Class Third Address Range: High Address"
			::= { wsSwDhcpSvrPoolClassEntry 8 }

		
		-- 1.3.6.1.4.1.388.14.2.3.5.10.1.9
		wsSwDhcpSvrPoolClassFourthLowIP OBJECT-TYPE
			SYNTAX IpAddress
			MAX-ACCESS read-create
			STATUS current
			DESCRIPTION
				"Pool Class Fourth Address Range: Low Address"
			::= { wsSwDhcpSvrPoolClassEntry 9 }

		
		-- 1.3.6.1.4.1.388.14.2.3.5.10.1.10
		wsSwDhcpSvrPoolClassFourthHighIP OBJECT-TYPE
			SYNTAX IpAddress
			MAX-ACCESS read-create
			STATUS current
			DESCRIPTION
				"Pool Class Fourth Address Range: High Address"
			::= { wsSwDhcpSvrPoolClassEntry 10 }

		
		-- 1.3.6.1.4.1.388.14.2.3.5.10.1.11
		wsSwDhcpSvrPoolClassRowStatus OBJECT-TYPE
			SYNTAX AbbrevRowStatus
			MAX-ACCESS read-create
			STATUS current
			DESCRIPTION
				"Row Status of DHCP Server Pool Class Table"
			::= { wsSwDhcpSvrPoolClassEntry 11 }

		
		-- 1.3.6.1.4.1.388.14.2.3.5.11
		wsSwDhcpDynamicBindingStatusTable OBJECT-TYPE
			SYNTAX SEQUENCE OF WsSwDhcpDynamicBindingStatusEntry
			MAX-ACCESS not-accessible
			STATUS current
			DESCRIPTION
				"Dynamic bindings tables.
				
				This gives list of Active DHCP clients who obtained IP Address from onboard DHCP Server's dynamic pool."
			::= { wsSwDhcpServerModule 11 }

		
		-- 1.3.6.1.4.1.388.14.2.3.5.11.1
		wsSwDhcpDynamicBindingStatusEntry OBJECT-TYPE
			SYNTAX WsSwDhcpDynamicBindingStatusEntry
			MAX-ACCESS not-accessible
			STATUS current
			DESCRIPTION
				"Description."
			INDEX { wsSwDhcpDynamicBindingStatusIp }
			::= { wsSwDhcpDynamicBindingStatusTable 1 }

		
		WsSwDhcpDynamicBindingStatusEntry ::=
			SEQUENCE { 
				wsSwDhcpDynamicBindingStatusIp
					IpAddress,
				wsSwDhcpDynamicBindingStatusHardwareAddr
					PhysAddress,
				wsSwDhcpDynamicBindingStatusLeaseExpiry
					DateAndTime,
				wsSwDhcpDynamicBindingStatusRowStatus
					AbbrevRowStatus
			 }

		-- 1.3.6.1.4.1.388.14.2.3.5.11.1.1
		wsSwDhcpDynamicBindingStatusIp OBJECT-TYPE
			SYNTAX IpAddress
			MAX-ACCESS read-only
			STATUS current
			DESCRIPTION
				"IP Address of DHCP client."
			::= { wsSwDhcpDynamicBindingStatusEntry 1 }

		
		-- 1.3.6.1.4.1.388.14.2.3.5.11.1.2
		wsSwDhcpDynamicBindingStatusHardwareAddr OBJECT-TYPE
			SYNTAX PhysAddress
			MAX-ACCESS read-only
			STATUS current
			DESCRIPTION
				"Hardware Address of DHCP client."
			::= { wsSwDhcpDynamicBindingStatusEntry 2 }

		
		-- 1.3.6.1.4.1.388.14.2.3.5.11.1.3
		wsSwDhcpDynamicBindingStatusLeaseExpiry OBJECT-TYPE
			SYNTAX DateAndTime
			MAX-ACCESS read-only
			STATUS current
			DESCRIPTION
				"Lease Expiry time of DHCP client. "
			::= { wsSwDhcpDynamicBindingStatusEntry 3 }

		
		-- 1.3.6.1.4.1.388.14.2.3.5.11.1.4
		wsSwDhcpDynamicBindingStatusRowStatus OBJECT-TYPE
			SYNTAX AbbrevRowStatus
			MAX-ACCESS read-create
			STATUS current
			DESCRIPTION
				"Only deletion of rows are permitted."
			::= { wsSwDhcpDynamicBindingStatusEntry 4 }

		
		-- 1.3.6.1.4.1.388.14.2.3.5.12
		wsSwDhcpSvrDDNSTable OBJECT-TYPE
			SYNTAX SEQUENCE OF WsSwDhcpSvrDDNSEntry
			MAX-ACCESS not-accessible
			STATUS current
			DESCRIPTION
				"DDNS bindings Table.
				
				This gives list of IP - Name bindings which onboard DHCP Server has updated with external DDNS Server. "
			::= { wsSwDhcpServerModule 12 }

		
		-- 1.3.6.1.4.1.388.14.2.3.5.12.1
		wsSwDhcpSvrDDNSEntry OBJECT-TYPE
			SYNTAX WsSwDhcpSvrDDNSEntry
			MAX-ACCESS not-accessible
			STATUS current
			DESCRIPTION
				"Description."
			INDEX { wsSwDhcpSvrDDNSAddress }
			::= { wsSwDhcpSvrDDNSTable 1 }

		
		WsSwDhcpSvrDDNSEntry ::=
			SEQUENCE { 
				wsSwDhcpSvrDDNSAddress
					IpAddress,
				wsSwDhcpSvrDDNSName
					DisplayString
			 }

		-- 1.3.6.1.4.1.388.14.2.3.5.12.1.1
		wsSwDhcpSvrDDNSAddress OBJECT-TYPE
			SYNTAX IpAddress
			MAX-ACCESS read-only
			STATUS current
			DESCRIPTION
				"The IP address of the DHCP client for which the switch has sent DDNS update."
			::= { wsSwDhcpSvrDDNSEntry 1 }

		
		-- 1.3.6.1.4.1.388.14.2.3.5.12.1.2
		wsSwDhcpSvrDDNSName OBJECT-TYPE
			SYNTAX DisplayString
			MAX-ACCESS read-only
			STATUS current
			DESCRIPTION
				"The Fully qualified domain name of the DHCP client with which the switch has sent DDNS update."
			::= { wsSwDhcpSvrDDNSEntry 2 }

		
		-- 1.3.6.1.4.1.388.14.2.3.5.100
		wsSwDhcpServerMIBConformance OBJECT IDENTIFIER ::= { wsSwDhcpServerModule 100 }

		
		-- 1.3.6.1.4.1.388.14.2.3.5.100.2
		wsSwDhcpServerCompliances OBJECT IDENTIFIER ::= { wsSwDhcpServerMIBConformance 2 }

		
		-- 1.3.6.1.4.1.388.14.2.3.5.100.2.1
		wsSwDhcpServerCompliance MODULE-COMPLIANCE
			STATUS current
			DESCRIPTION 
				"Description."
			MODULE -- this module
				MANDATORY-GROUPS { wsSwDhcpServerGroup }
			::= { wsSwDhcpServerCompliances 1 }

		
		-- 1.3.6.1.4.1.388.14.2.3.5.100.3
		wsSwDhcpServerGroups OBJECT IDENTIFIER ::= { wsSwDhcpServerMIBConformance 3 }

		
		-- 1.3.6.1.4.1.388.14.2.3.5.100.3.1
		wsSwDhcpServerGroup OBJECT-GROUP
			OBJECTS { wsSwDhcpSvrBootp, wsSwDhcpSvrPingInterval, wsSwDhcpSvrExcludeRowStatus, wsSwDhcpSvrPoolDomainName, wsSwDhcpSvrPoolNetBiosNodeType, 
				wsSwDhcpSvrPoolBootfile, wsSwDhcpSvrPoolDdnsUpdate, wsSwDhcpSvrPoolDdnsDomainName, wsSwDhcpSvrPoolDdnsTtl, wsSwDhcpSvrPoolDdnsMultiUserClass, 
				wsSwDhcpSvrPoolDefaultRouter, wsSwDhcpSvrPoolBootpNextSvrIP, wsSwDhcpSvrPoolDnsSvrIP, wsSwDhcpSvrPoolNetbiosSvrIP, wsSwDhcpSvrPoolNoDefault, 
				wsSwDhcpSvrPoolLeaseTime, wsSwDhcpSvrPoolRowStatus, wsSwDhcpSvrIncludeRowStatus, wsSwDhcpBindingStatusHardwareAddr, wsSwDhcpBindingStatusLeaseExpired, 
				wsSwDhcpBindingStatusRowStatus, wsSwDhcpSvrPoolDdnsIp, wsSwDhcpSvrEnable, wsSwDhcpSvrPoolHostIp, wsSwDhcpSvrPoolClientId, 
				wsSwDhcpSvrExcludeLowIpAddr, wsSwDhcpSvrExcludeHighIpAddr, wsSwDhcpSvrPoolNameIndex, wsSwDhcpSvrIncludeLowIP, wsSwDhcpSvrIncludeHighIP, 
				wsSwDhcpBindingStatusIp, wsSwDhcpSvrGlobalOptionCode, wsSwDhcpSvrGlobalOptionType, wsSwDhcpSvrGlobalOptionRowStatus, wsSwDhcpSvrGlobalOptionName, 
				wsSwDhcpBindingStatusClientID, wsSwDhcpSvrPoolType, wsSwDhcpSvrPoolSubnetIpAndMask, wsSwDhcpSvrPoolClientName, wsSwDhcpSvrPoolHardWareAddrAndType, 
				wsSwDhcpSvrPoolOptionName, wsSwDhcpSvrPoolOptionValue, wsSwDhcpRelayInterface, wsSwDhcpRelayRowStatus, wsSwDhcpRelayTargetSet, 
				wsSwDhcpRelayTarget, wsSwDhcpSvrLastErrorMsg, wsSwDhcpSvrStatus, wsSwDhcpSvrPoolClassRowStatus, wsSwDhcpSvrPoolClassFourthHighIP, 
				wsSwDhcpSvrPoolClassFourthLowIP, wsSwDhcpSvrPoolClassThirdHighIP, wsSwDhcpSvrPoolClassThirdLowIP, wsSwDhcpSvrPoolClassSecHighIP, wsSwDhcpSvrPoolClassSecLowIP, 
				wsSwDhcpSvrPoolClassFirstHighIP, wsSwDhcpSvrPoolClassFirstLowIP, wsSwDhcpSvrPoolClassName, wsSwDhcpSvrPoolClassPoolName, wsSwDhcpSvrClassRowStatus, 
				wsSwDhcpSvrClassMutipleUserClass, wsSwDhcpSvrClassName, wsSwDhcpSvrPoolOptionRowStatus, wsSwDhcpSvrClassUsrClassOptValue8, wsSwDhcpSvrClassUsrClassOptValue7, 
				wsSwDhcpSvrClassUsrClassOptValue6, wsSwDhcpSvrClassUsrClassOptValue5, wsSwDhcpSvrClassUsrClassOptValue4, wsSwDhcpSvrClassUsrClassOptValue3, wsSwDhcpSvrDDNSName, 
				wsSwDhcpSvrDDNSAddress, wsSwDhcpDynamicBindingStatusRowStatus, wsSwDhcpDynamicBindingStatusLeaseExpiry, wsSwDhcpDynamicBindingStatusHardwareAddr, wsSwDhcpDynamicBindingStatusIp, 
				wsSwDhcpDeleteAllLease, wsSwDhcpSvrClassUsrClassOptValue2, wsSwDhcpSvrClassUsrClassOptValue1 }
			STATUS current
			DESCRIPTION 
				"Description."
			::= { wsSwDhcpServerGroups 1 }

		
		-- 1.3.6.1.4.1.388.14.2.3.5.100.3.2
		wsSwDhcpServerDeprecatedGroup OBJECT-GROUP
			OBJECTS { wsSwDhcpSvrRestart, wsSwDhcpBindingStatusLeaseType, wsSwDhcpSvrPoolDdnsUpdateAll }
			STATUS deprecated
			DESCRIPTION 
				"Description."
			::= { wsSwDhcpServerGroups 2 }

		
	
	END

--
-- WS-SW-DHCPSERVER-MIB.my
--
