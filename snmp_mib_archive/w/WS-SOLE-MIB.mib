--
-- WS-SOLE-MIB.my
-- MIB generated by MG-SOFT Visual MIB Builder Version 6.0  Build 88
-- Tuesday, October 14, 2008 at 18:35:22
--

--  WS-SOLE-MIB.my

	WS-SOLE-MIB DEFINITIONS ::= BEGIN
 
		IMPORTS
			OBJECT-GROUP			
				FROM SNMPv2-CONF			
			IpAddress, Integer32, Unsigned32, OBJECT-TYPE, MODULE-IDENTITY			
				FROM SNMPv2-SMI			
			DisplayString, TruthValue, DateAndTime			
				FROM SNMPv2-TC			
			PhysAddress			
				FROM SNMPv2-TC				
			wsSole			
				FROM WS-SMI;
	
	
		-- 1.3.6.1.4.1.388.14.8.1
		wsSoleMibModule MODULE-IDENTITY 
			LAST-UPDATED "200808071640Z"		-- August 07, 2008 at 16:40 GMT
			ORGANIZATION 
				"Motorola Inc."
			CONTACT-INFO 
				"Contact-info."
			DESCRIPTION 
				"MIB module for WiOS locationing services."
			REVISION "200808071639Z"		-- August 07, 2008 at 16:39 GMT
			DESCRIPTION 
				"01a11
				Added wsSoleApCoordinatesTable."
			REVISION "200807081612Z"		-- July 08, 2008 at 16:12 GMT
			DESCRIPTION 
				"Updated ranges for wsSoleAdapterEngineAdptrPort 
				and wsSoleAdapterCfgListenPort (1000..9000), 
				wsSoleSiteDimension Length (0..3000), 
				Width (0..3000), and Height (0..60), 
				wsSoleTagTimestamp type changed to 
				DateAndTime."
			REVISION "200806231455Z"		-- June 23, 2008 at 14:55 GMT
			DESCRIPTION 
				"Added wsSoleAdapterCfgMulticast field
				"
			REVISION "200806101649Z"		-- June 10, 2008 at 16:49 GMT
			DESCRIPTION 
				"01a08
				Added table for show rtls tags."
			REVISION "200805071015Z"		-- May 07, 2008 at 10:15 GMT
			DESCRIPTION 
				"01a07
				Changed value range of wsSoleLocateMuInterval."
			REVISION "200804111659Z"		-- April 11, 2008 at 16:59 GMT
			DESCRIPTION 
				"Added listening port (wsSoleAdapterCfgListenPort) to wsSoleAdapterCfgTable."
			REVISION "200801111703Z"		-- January 11, 2008 at 17:03 GMT
			DESCRIPTION 
				"Added two more objects to wsSoleAdapterCfgTable.
				Added nodes wsSoleSwitchInfo, wsSoleSiteInfo, 
				wsSoleMuLocateInfo and wsSoleSmartSurroundingsTable"
			REVISION "200708271455Z"		-- August 27, 2007 at 14:55 GMT
			DESCRIPTION 
				"Add site info scalars"
			REVISION "200708171632Z"		-- August 17, 2007 at 16:32 GMT
			DESCRIPTION 
				"Error String Update"
			REVISION "200708161418Z"		-- August 16, 2007 at 14:18 GMT
			DESCRIPTION 
				"01a02
				Second revision"
			::= { wsSole 1 }

		
	
--
-- Type definitions
--
	
		AbbrRowStatus ::= INTEGER
			{
			active(1),
			createAndGo(4),
			destroy(6)
			}

	
	
--
-- Node definitions
--
	
		-- 1.3.6.1.4.1.388.14.8.1.1
		wsSoleAdapterSwTable OBJECT-TYPE
			SYNTAX SEQUENCE OF WsSoleAdapterSwEntry
			MAX-ACCESS not-accessible
			STATUS current
			DESCRIPTION
				"A table which shows all the information of existing SOLE adapter modules."
			::= { wsSoleMibModule 1 }

		
		-- 1.3.6.1.4.1.388.14.8.1.1.1
		wsSoleAdapterSwEntry OBJECT-TYPE
			SYNTAX WsSoleAdapterSwEntry
			MAX-ACCESS not-accessible
			STATUS current
			DESCRIPTION
				"An entry in wsSoleAdapterSwTable."
			INDEX { wsSoleAdapterSwIndex }
			::= { wsSoleAdapterSwTable 1 }

		
		WsSoleAdapterSwEntry ::=
			SEQUENCE { 
				wsSoleAdapterSwIndex
					INTEGER,
				wsSoleAdapterSwAdptrType
					DisplayString,
				wsSoleAdapterSwVersion
					DisplayString,
				wsSoleAdapterSwBuildDate
					DisplayString
			 }

		-- 1.3.6.1.4.1.388.14.8.1.1.1.1
		wsSoleAdapterSwIndex OBJECT-TYPE
			SYNTAX INTEGER (1..10)
			MAX-ACCESS read-only
			STATUS current
			DESCRIPTION
				"Simple integer index."
			::= { wsSoleAdapterSwEntry 1 }

		
		-- 1.3.6.1.4.1.388.14.8.1.1.1.2
		wsSoleAdapterSwAdptrType OBJECT-TYPE
			SYNTAX DisplayString (SIZE (1..64))
			MAX-ACCESS read-only
			STATUS current
			DESCRIPTION
				"The type of the adapter."
			::= { wsSoleAdapterSwEntry 2 }

		
		-- 1.3.6.1.4.1.388.14.8.1.1.1.3
		wsSoleAdapterSwVersion OBJECT-TYPE
			SYNTAX DisplayString
			MAX-ACCESS read-only
			STATUS current
			DESCRIPTION
				"The software version of the adapter."
			::= { wsSoleAdapterSwEntry 3 }

		
		-- 1.3.6.1.4.1.388.14.8.1.1.1.4
		wsSoleAdapterSwBuildDate OBJECT-TYPE
			SYNTAX DisplayString
			MAX-ACCESS read-only
			STATUS current
			DESCRIPTION
				"The date and time when the adapter was compiled."
			::= { wsSoleAdapterSwEntry 4 }

		
		-- 1.3.6.1.4.1.388.14.8.1.2
		wsSoleAdapterCfgTable OBJECT-TYPE
			SYNTAX SEQUENCE OF WsSoleAdapterCfgEntry
			MAX-ACCESS not-accessible
			STATUS current
			DESCRIPTION
				"A table which is used to configure SOLE adapters."
			::= { wsSoleMibModule 2 }

		
		-- 1.3.6.1.4.1.388.14.8.1.2.1
		wsSoleAdapterCfgEntry OBJECT-TYPE
			SYNTAX WsSoleAdapterCfgEntry
			MAX-ACCESS not-accessible
			STATUS current
			DESCRIPTION
				"An entry in wsSoleAdapterCfgTable."
			INDEX { wsSoleAdapterCfgIndex }
			::= { wsSoleAdapterCfgTable 1 }

		
		WsSoleAdapterCfgEntry ::=
			SEQUENCE { 
				wsSoleAdapterCfgIndex
					INTEGER,
				wsSoleAdapterCfgAdptrType
					DisplayString,
				wsSoleAdapterCfgLocateInterval
					INTEGER,
				wsSoleAdapterCfgLocateEnable
					TruthValue,
				wsSoleAdapterCfgEnable
					TruthValue,
				wsSoleAdapterCfgLastErrorString
					DisplayString,
				wsSoleAdapterCfgMulticast
					PhysAddress
			 }

		-- 1.3.6.1.4.1.388.14.8.1.2.1.1
		wsSoleAdapterCfgIndex OBJECT-TYPE
			SYNTAX INTEGER (1..10)
			MAX-ACCESS read-only
			STATUS current
			DESCRIPTION
				"Simple integer index."
			::= { wsSoleAdapterCfgEntry 1 }

		
		-- 1.3.6.1.4.1.388.14.8.1.2.1.2
		wsSoleAdapterCfgAdptrType OBJECT-TYPE
			SYNTAX DisplayString (SIZE (1..64))
			MAX-ACCESS read-only
			STATUS current
			DESCRIPTION
				"The type of the adapter."
			::= { wsSoleAdapterCfgEntry 2 }

		
		-- 1.3.6.1.4.1.388.14.8.1.2.1.3
		wsSoleAdapterCfgLocateInterval OBJECT-TYPE
			SYNTAX INTEGER (5..3600)
			UNITS "secs"
			MAX-ACCESS read-write
			STATUS current
			DESCRIPTION
				"Location interval in secs."
			::= { wsSoleAdapterCfgEntry 3 }

		
		-- 1.3.6.1.4.1.388.14.8.1.2.1.4
		wsSoleAdapterCfgLocateEnable OBJECT-TYPE
			SYNTAX TruthValue
			MAX-ACCESS read-write
			STATUS current
			DESCRIPTION
				"Enable or disable locationing of adapter type tags by 
				on-board location engine."
			::= { wsSoleAdapterCfgEntry 4 }

		
		-- 1.3.6.1.4.1.388.14.8.1.2.1.5
		wsSoleAdapterCfgEnable OBJECT-TYPE
			SYNTAX TruthValue
			MAX-ACCESS read-write
			STATUS current
			DESCRIPTION
				"Enable or disable the adapter."
			::= { wsSoleAdapterCfgEntry 5 }

		
		-- 1.3.6.1.4.1.388.14.8.1.2.1.6
		wsSoleAdapterCfgLastErrorString OBJECT-TYPE
			SYNTAX DisplayString
			MAX-ACCESS read-only
			STATUS current
			DESCRIPTION
				"If any error happens during the enable/disable (config) operation, 
				this scalar will show the most recent error message."
			::= { wsSoleAdapterCfgEntry 6 }

		
		-- 1.3.6.1.4.1.388.14.8.1.2.1.7
		wsSoleAdapterCfgMulticast OBJECT-TYPE
			SYNTAX PhysAddress
			MAX-ACCESS read-write
			STATUS current
			DESCRIPTION
				"Multicast MAC address to which aeroscout tags will send messages to."
			::= { wsSoleAdapterCfgEntry 7 }

		
		-- 1.3.6.1.4.1.388.14.8.1.3
		wsSoleAdapterEngineTable OBJECT-TYPE
			SYNTAX SEQUENCE OF WsSoleAdapterEngineEntry
			MAX-ACCESS not-accessible
			STATUS current
			DESCRIPTION
				"A table which shows all the existing external location 
				engine connections."
			::= { wsSoleMibModule 3 }

		
		-- 1.3.6.1.4.1.388.14.8.1.3.1
		wsSoleAdapterEngineEntry OBJECT-TYPE
			SYNTAX WsSoleAdapterEngineEntry
			MAX-ACCESS not-accessible
			STATUS current
			DESCRIPTION
				"An entry in wsSoleAdapterEngineTable."
			INDEX { wsSoleAdapterEngineIndex }
			::= { wsSoleAdapterEngineTable 1 }

		
		WsSoleAdapterEngineEntry ::=
			SEQUENCE { 
				wsSoleAdapterEngineIndex
					INTEGER,
				wsSoleAdapterEngineAdptrType
					DisplayString,
				wsSoleAdapterEngineAdptrIp
					IpAddress,
				wsSoleAdapterEngineAdptrPort
					INTEGER,
				wsSoleAdapterEngineAdptrState
					INTEGER,
				wsSoleAdapterEngineNumMsgsRxFromEngine
					Unsigned32,
				wsSoleAdapterEngineNumMsgsTxToEngine
					Unsigned32,
				wsSoleAdapterEngineNumTagReportsTxToEngine
					Unsigned32,
				wsSoleAdapterEngineLastMsgRecvTime
					DisplayString,
				wsSoleAdapterEngineLastMsgSentTime
					DisplayString
			 }

		-- 1.3.6.1.4.1.388.14.8.1.3.1.1
		wsSoleAdapterEngineIndex OBJECT-TYPE
			SYNTAX INTEGER (1..10)
			MAX-ACCESS read-only
			STATUS current
			DESCRIPTION
				"Simple integer index."
			::= { wsSoleAdapterEngineEntry 1 }

		
		-- 1.3.6.1.4.1.388.14.8.1.3.1.2
		wsSoleAdapterEngineAdptrType OBJECT-TYPE
			SYNTAX DisplayString (SIZE (1..64))
			MAX-ACCESS read-only
			STATUS current
			DESCRIPTION
				"The type of the adapter."
			::= { wsSoleAdapterEngineEntry 2 }

		
		-- 1.3.6.1.4.1.388.14.8.1.3.1.3
		wsSoleAdapterEngineAdptrIp OBJECT-TYPE
			SYNTAX IpAddress
			MAX-ACCESS read-write
			STATUS current
			DESCRIPTION
				"The IP address of the location engine for adapter."
			::= { wsSoleAdapterEngineEntry 3 }

		
		-- 1.3.6.1.4.1.388.14.8.1.3.1.4
		wsSoleAdapterEngineAdptrPort OBJECT-TYPE
			SYNTAX INTEGER (1000..9000)
			MAX-ACCESS read-write
			STATUS current
			DESCRIPTION
				"The port on which the external location engine is listening on."
			::= { wsSoleAdapterEngineEntry 4 }

		
		-- 1.3.6.1.4.1.388.14.8.1.3.1.5
		wsSoleAdapterEngineAdptrState OBJECT-TYPE
			SYNTAX INTEGER
				{
				offline(1),
				idle(2),
				ready(3),
				tagReportingOn(4),
				muReportingOn(5),
				tagandmuReportingOn(6)
				}
			MAX-ACCESS read-only
			STATUS current
			DESCRIPTION
				"The state of the location engine."
			::= { wsSoleAdapterEngineEntry 5 }

		
		-- 1.3.6.1.4.1.388.14.8.1.3.1.6
		wsSoleAdapterEngineNumMsgsRxFromEngine OBJECT-TYPE
			SYNTAX Unsigned32
			MAX-ACCESS read-only
			STATUS current
			DESCRIPTION
				"Number of messages received from engine."
			::= { wsSoleAdapterEngineEntry 6 }

		
		-- 1.3.6.1.4.1.388.14.8.1.3.1.7
		wsSoleAdapterEngineNumMsgsTxToEngine OBJECT-TYPE
			SYNTAX Unsigned32
			MAX-ACCESS read-only
			STATUS current
			DESCRIPTION
				"Number of messages sent to engine."
			::= { wsSoleAdapterEngineEntry 7 }

		
		-- 1.3.6.1.4.1.388.14.8.1.3.1.8
		wsSoleAdapterEngineNumTagReportsTxToEngine OBJECT-TYPE
			SYNTAX Unsigned32
			MAX-ACCESS read-only
			STATUS current
			DESCRIPTION
				"Number of tag reports sent to engine."
			::= { wsSoleAdapterEngineEntry 8 }

		
		-- 1.3.6.1.4.1.388.14.8.1.3.1.9
		wsSoleAdapterEngineLastMsgRecvTime OBJECT-TYPE
			SYNTAX DisplayString
			MAX-ACCESS read-only
			STATUS current
			DESCRIPTION
				"Time at which last message was received by the engine."
			::= { wsSoleAdapterEngineEntry 9 }

		
		-- 1.3.6.1.4.1.388.14.8.1.3.1.10
		wsSoleAdapterEngineLastMsgSentTime OBJECT-TYPE
			SYNTAX DisplayString
			MAX-ACCESS read-only
			STATUS current
			DESCRIPTION
				"Time at which last message was sent by the engine."
			::= { wsSoleAdapterEngineEntry 10 }

		
		-- 1.3.6.1.4.1.388.14.8.1.4
		wsSoleSwitchInfo OBJECT IDENTIFIER ::= { wsSoleMibModule 4 }

		
		-- 1.3.6.1.4.1.388.14.8.1.4.1
		wsSoleSwitchSiteCoordinates OBJECT IDENTIFIER ::= { wsSoleSwitchInfo 1 }

		
		-- 1.3.6.1.4.1.388.14.8.1.4.1.1
		wsSoleSwitchSiteCoordinatesX OBJECT-TYPE
			SYNTAX INTEGER (0..65535)
			MAX-ACCESS read-write
			STATUS current
			DESCRIPTION
				"X coordinate for the switch's location. 
				The unit is same as configured for site."
			::= { wsSoleSwitchSiteCoordinates 1 }

		
		-- 1.3.6.1.4.1.388.14.8.1.4.1.2
		wsSoleSwitchSiteCoordinatesY OBJECT-TYPE
			SYNTAX INTEGER (0..65535)
			MAX-ACCESS read-write
			STATUS current
			DESCRIPTION
				"Y coordinate for the switch's location. 
				The unit is same as configured for site."
			::= { wsSoleSwitchSiteCoordinates 2 }

		
		-- 1.3.6.1.4.1.388.14.8.1.4.1.3
		wsSoleSwitchSiteCoordinatesZ OBJECT-TYPE
			SYNTAX INTEGER (0..65535)
			MAX-ACCESS read-write
			STATUS current
			DESCRIPTION
				"Z coordinate for the switch's location. 
				The unit is same as configured for site."
			::= { wsSoleSwitchSiteCoordinates 3 }

		
		-- 1.3.6.1.4.1.388.14.8.1.4.2
		wsSoleSwitchGeoCoordinates OBJECT IDENTIFIER ::= { wsSoleSwitchInfo 2 }

		
		-- 1.3.6.1.4.1.388.14.8.1.4.2.1
		wsSoleSwitchGeoCoordinatesWholeLongitude OBJECT-TYPE
			SYNTAX INTEGER (-180..180)
			UNITS "degree"
			MAX-ACCESS read-write
			STATUS current
			DESCRIPTION
				"The whole portion of longitude of switch location (in deg). 
				(example: if the longitude of switch location is -127.2345, 
				this var should be set to -127)"
			::= { wsSoleSwitchGeoCoordinates 1 }

		
		-- 1.3.6.1.4.1.388.14.8.1.4.2.2
		wsSoleSwitchGeoCoordinatesFractionLongitude OBJECT-TYPE
			SYNTAX INTEGER (0..9999)
			MAX-ACCESS read-write
			STATUS current
			DESCRIPTION
				"The decimal/fractional portion of longitude of switch location 
				(in deg).(example: if the longitude of switch location is -127.2345, 
				this var should be set to 2345)."
			::= { wsSoleSwitchGeoCoordinates 2 }

		
		-- 1.3.6.1.4.1.388.14.8.1.4.2.3
		wsSoleSwitchGeoCoordinatesWholeLatitude OBJECT-TYPE
			SYNTAX INTEGER (-180..180)
			UNITS "degree"
			MAX-ACCESS read-write
			STATUS current
			DESCRIPTION
				"The whole portion of latitude of switch location (in deg). 
				(example: if the latitude of switch location is -127.2345, 
				this var should be set to -127)."
			::= { wsSoleSwitchGeoCoordinates 3 }

		
		-- 1.3.6.1.4.1.388.14.8.1.4.2.4
		wsSoleSwitchGeoCoordinatesFractionLatitude OBJECT-TYPE
			SYNTAX INTEGER (0..9999)
			MAX-ACCESS read-write
			STATUS current
			DESCRIPTION
				"The decimal/fractional portion of latitude of switch location (in deg).
				(example: if the latitude of switch location is -127.2345, 
				this var should be set to 2345)."
			::= { wsSoleSwitchGeoCoordinates 4 }

		
		-- 1.3.6.1.4.1.388.14.8.1.5
		wsSoleSiteInfo OBJECT IDENTIFIER ::= { wsSoleMibModule 5 }

		
		-- 1.3.6.1.4.1.388.14.8.1.5.1
		wsSoleSiteName OBJECT-TYPE
			SYNTAX DisplayString (SIZE (1..32))
			MAX-ACCESS read-write
			STATUS current
			DESCRIPTION
				"Name of the site."
			::= { wsSoleSiteInfo 1 }

		
		-- 1.3.6.1.4.1.388.14.8.1.5.2
		wsSoleSiteDescription OBJECT-TYPE
			SYNTAX DisplayString (SIZE (1..64))
			MAX-ACCESS read-write
			STATUS current
			DESCRIPTION
				"Description of site."
			::= { wsSoleSiteInfo 2 }

		
		-- 1.3.6.1.4.1.388.14.8.1.5.3
		wsSoleSiteDimensionUnit OBJECT-TYPE
			SYNTAX INTEGER
				{
				feet(1),
				meters(2)
				}
			MAX-ACCESS read-write
			STATUS current
			DESCRIPTION
				"Unit of measurement for site (either feet or meters)."
			::= { wsSoleSiteInfo 3 }

		
		-- 1.3.6.1.4.1.388.14.8.1.5.4
		wsSoleSiteDimensionScale OBJECT-TYPE
			SYNTAX INTEGER (1..10)
			MAX-ACCESS read-only
			STATUS current
			DESCRIPTION
				"Scale factor for site dimesions. Used for larger sites"
			::= { wsSoleSiteInfo 4 }

		
		-- 1.3.6.1.4.1.388.14.8.1.5.5
		wsSoleSiteDimensionLength OBJECT-TYPE
			SYNTAX INTEGER (0..3000)
			MAX-ACCESS read-write
			STATUS current
			DESCRIPTION
				"Site dimension length."
			::= { wsSoleSiteInfo 5 }

		
		-- 1.3.6.1.4.1.388.14.8.1.5.6
		wsSoleSiteDimensionWidth OBJECT-TYPE
			SYNTAX INTEGER (0..3000)
			MAX-ACCESS read-write
			STATUS current
			DESCRIPTION
				"Site dimension width."
			::= { wsSoleSiteInfo 6 }

		
		-- 1.3.6.1.4.1.388.14.8.1.5.7
		wsSoleSiteDimensionHeight OBJECT-TYPE
			SYNTAX INTEGER (0..60)
			MAX-ACCESS read-write
			STATUS current
			DESCRIPTION
				"Site dimension height."
			::= { wsSoleSiteInfo 7 }

		
		-- 1.3.6.1.4.1.388.14.8.1.5.8
		wsSoleNumBarriers OBJECT-TYPE
			SYNTAX Unsigned32 (0..100)
			MAX-ACCESS read-only
			STATUS current
			DESCRIPTION
				"Number of barriers configured within the site."
			::= { wsSoleSiteInfo 8 }

		
		-- 1.3.6.1.4.1.388.14.8.1.5.9
		wsSoleNumDeployedAPs OBJECT-TYPE
			SYNTAX Unsigned32 (0..256)
			MAX-ACCESS read-only
			STATUS current
			DESCRIPTION
				"Number of APs deployed within the site."
			::= { wsSoleSiteInfo 9 }

		
		-- 1.3.6.1.4.1.388.14.8.1.5.10
		wsSoleSiteLastErrorString OBJECT-TYPE
			SYNTAX DisplayString (SIZE (1..128))
			MAX-ACCESS read-only
			STATUS current
			DESCRIPTION
				"If any error happens during any of site parameter config operation,
				this scalar will show the most recent error message."
			::= { wsSoleSiteInfo 10 }

		
		-- 1.3.6.1.4.1.388.14.8.1.5.11
		wsSoleSiteBarrierTable OBJECT-TYPE
			SYNTAX SEQUENCE OF WsSoleSiteBarrierEntry
			MAX-ACCESS not-accessible
			STATUS current
			DESCRIPTION
				"Barrier Information Table."
			::= { wsSoleSiteInfo 11 }

		
		-- 1.3.6.1.4.1.388.14.8.1.5.11.1
		wsSoleSiteBarrierEntry OBJECT-TYPE
			SYNTAX WsSoleSiteBarrierEntry
			MAX-ACCESS not-accessible
			STATUS current
			DESCRIPTION
				"Barrier Information Table Entry."
			INDEX { wsSoleSiteBarrierIndex }
			::= { wsSoleSiteBarrierTable 1 }

		
		WsSoleSiteBarrierEntry ::=
			SEQUENCE { 
				wsSoleSiteBarrierIndex
					INTEGER,
				wsSoleSiteBarrierName
					DisplayString,
				wsSoleSiteBarrierShape
					INTEGER,
				wsSoleSiteBarrierType
					INTEGER,
				wsSoleSiteBarrierAttenuation
					Integer32
			 }

		-- 1.3.6.1.4.1.388.14.8.1.5.11.1.1
		wsSoleSiteBarrierIndex OBJECT-TYPE
			SYNTAX INTEGER (1..100)
			MAX-ACCESS read-only
			STATUS current
			DESCRIPTION
				"Simple Index."
			::= { wsSoleSiteBarrierEntry 1 }

		
		-- 1.3.6.1.4.1.388.14.8.1.5.11.1.2
		wsSoleSiteBarrierName OBJECT-TYPE
			SYNTAX DisplayString (SIZE (1..32))
			MAX-ACCESS read-only
			STATUS current
			DESCRIPTION
				"Name of barrier."
			::= { wsSoleSiteBarrierEntry 2 }

		
		-- 1.3.6.1.4.1.388.14.8.1.5.11.1.3
		wsSoleSiteBarrierShape OBJECT-TYPE
			SYNTAX INTEGER
				{
				line(1),
				polyline(2),
				rectangle(3),
				polygon(4)
				}
			MAX-ACCESS read-only
			STATUS current
			DESCRIPTION
				"Shape of barrier."
			::= { wsSoleSiteBarrierEntry 3 }

		
		-- 1.3.6.1.4.1.388.14.8.1.5.11.1.4
		wsSoleSiteBarrierType OBJECT-TYPE
			SYNTAX INTEGER
				{
				concrete(1),
				dryWall(2),
				customWall(3),
				cubeWall(4),
				woodenDoor(5),
				metalDoor(6),
				metalShelf(7),
				merchandiseShelf(8)
				}
			MAX-ACCESS read-only
			STATUS current
			DESCRIPTION
				"Type of barrier (either of dry-wall, custom-wall, wooden door, 
				metal door, concrete, metal shelf or custom shelf)."
			::= { wsSoleSiteBarrierEntry 4 }

		
		-- 1.3.6.1.4.1.388.14.8.1.5.11.1.5
		wsSoleSiteBarrierAttenuation OBJECT-TYPE
			SYNTAX Integer32
			UNITS "dBm"
			MAX-ACCESS read-only
			STATUS current
			DESCRIPTION
				"Attenuation in dBm caused by barrier."
			::= { wsSoleSiteBarrierEntry 5 }

		
		-- 1.3.6.1.4.1.388.14.8.1.5.12
		wsSoleSiteApCoordinatesTable OBJECT-TYPE
			SYNTAX SEQUENCE OF WsSoleSiteApCoordinatesEntry
			MAX-ACCESS not-accessible
			STATUS current
			DESCRIPTION
				"A table where AP coordinates (x, y and z) can be configured."
			::= { wsSoleSiteInfo 12 }

		
		-- 1.3.6.1.4.1.388.14.8.1.5.12.1
		wsSoleSiteApCoordinatesEntry OBJECT-TYPE
			SYNTAX WsSoleSiteApCoordinatesEntry
			MAX-ACCESS not-accessible
			STATUS current
			DESCRIPTION
				"An entry in the wsSoleApCoordinatesTable, indexed by
				wsSoleApCoordinatesApMac."
			INDEX { wsSoleSiteApCoordinatesApMac }
			::= { wsSoleSiteApCoordinatesTable 1 }

		
		WsSoleSiteApCoordinatesEntry ::=
			SEQUENCE { 
				wsSoleSiteApCoordinatesApMac
					PhysAddress,
				wsSoleSiteApCoordinatesX
					INTEGER,
				wsSoleSiteApCoordinatesY
					INTEGER,
				wsSoleSiteApCoordinatesZ
					INTEGER,
				wsSoleSiteApCoordinatesRowStatus
					AbbrRowStatus
			 }

		-- 1.3.6.1.4.1.388.14.8.1.5.12.1.1
		wsSoleSiteApCoordinatesApMac OBJECT-TYPE
			SYNTAX PhysAddress
			MAX-ACCESS accessible-for-notify
			STATUS current
			DESCRIPTION
				"The MAC address of the AP, which is the index 
				to this table."
			::= { wsSoleSiteApCoordinatesEntry 1 }

		
		-- 1.3.6.1.4.1.388.14.8.1.5.12.1.2
		wsSoleSiteApCoordinatesX OBJECT-TYPE
			SYNTAX INTEGER (0..3000)
			MAX-ACCESS read-create
			STATUS current
			DESCRIPTION
				"The x-coordinate of the AP."
			::= { wsSoleSiteApCoordinatesEntry 2 }

		
		-- 1.3.6.1.4.1.388.14.8.1.5.12.1.3
		wsSoleSiteApCoordinatesY OBJECT-TYPE
			SYNTAX INTEGER (0..3000)
			MAX-ACCESS read-create
			STATUS current
			DESCRIPTION
				"The y-coordinate of the AP."
			::= { wsSoleSiteApCoordinatesEntry 3 }

		
		-- 1.3.6.1.4.1.388.14.8.1.5.12.1.4
		wsSoleSiteApCoordinatesZ OBJECT-TYPE
			SYNTAX INTEGER (0..60)
			MAX-ACCESS read-create
			STATUS current
			DESCRIPTION
				"The z-coordinate of the AP."
			::= { wsSoleSiteApCoordinatesEntry 4 }

		
		-- 1.3.6.1.4.1.388.14.8.1.5.12.1.5
		wsSoleSiteApCoordinatesRowStatus OBJECT-TYPE
			SYNTAX AbbrRowStatus
			MAX-ACCESS read-create
			STATUS current
			DESCRIPTION
				"Row status: only values createAndGo (4) and destroy(6) 
				can be set. A successfull created row shows row-status 
				value as active(1)."
			::= { wsSoleSiteApCoordinatesEntry 5 }

		
		-- 1.3.6.1.4.1.388.14.8.1.5.13
		wsSoleSiteApStatusTable OBJECT-TYPE
			SYNTAX SEQUENCE OF WsSoleSiteApStatusEntry
			MAX-ACCESS not-accessible
			STATUS current
			DESCRIPTION
				"A table where AP coordinates (x, y and z) can be configured."
			::= { wsSoleSiteInfo 13 }

		
		-- 1.3.6.1.4.1.388.14.8.1.5.13.1
		wsSoleSiteApStatusEntry OBJECT-TYPE
			SYNTAX WsSoleSiteApStatusEntry
			MAX-ACCESS not-accessible
			STATUS current
			DESCRIPTION
				"An entry in the wsSoleApCoordinatesTable, indexed by
				wsSoleApCoordinatesApMac."
			INDEX { wsSoleSiteApStatusApMac }
			::= { wsSoleSiteApStatusTable 1 }

		
		WsSoleSiteApStatusEntry ::=
			SEQUENCE { 
				wsSoleSiteApStatusApMac
					PhysAddress,
				wsSoleSiteApStatusCoordinatesX
					INTEGER,
				wsSoleSiteApStatusCoordinatesY
					INTEGER,
				wsSoleSiteApStatusCoordinatesZ
					INTEGER,
				wsSoleSiteApStatusStatus
					Integer32,
				wsSoleSiteApStatusSwitchIp
					IpAddress,
				wsSoleSiteApStatus11aRadioIndex
					Integer32,
				wsSoleSiteApStatus11aRadioMac
					PhysAddress,
				wsSoleSiteApStatus11aRadioPower
					Integer32,
				wsSoleSiteApStatus11aRadioChannel
					Integer32,
				wsSoleSiteApStatus11bgRadioIndex
					Integer32,
				wsSoleSiteApStatus11bgRadioMac
					PhysAddress,
				wsSoleSiteApStatus11bgRadioPower
					Integer32,
				wsSoleSiteApStatus11bgRadioChannel
					Integer32
			 }

		-- 1.3.6.1.4.1.388.14.8.1.5.13.1.1
		wsSoleSiteApStatusApMac OBJECT-TYPE
			SYNTAX PhysAddress
			MAX-ACCESS accessible-for-notify
			STATUS current
			DESCRIPTION
				"The MAC address of the AP, which is the index 
				to this table."
			::= { wsSoleSiteApStatusEntry 1 }

		
		-- 1.3.6.1.4.1.388.14.8.1.5.13.1.2
		wsSoleSiteApStatusCoordinatesX OBJECT-TYPE
			SYNTAX INTEGER (0..3000)
			MAX-ACCESS read-only
			STATUS current
			DESCRIPTION
				"The x-coordinate of the AP."
			::= { wsSoleSiteApStatusEntry 2 }

		
		-- 1.3.6.1.4.1.388.14.8.1.5.13.1.3
		wsSoleSiteApStatusCoordinatesY OBJECT-TYPE
			SYNTAX INTEGER (0..3000)
			MAX-ACCESS read-only
			STATUS current
			DESCRIPTION
				"The y-coordinate of the AP."
			::= { wsSoleSiteApStatusEntry 3 }

		
		-- 1.3.6.1.4.1.388.14.8.1.5.13.1.4
		wsSoleSiteApStatusCoordinatesZ OBJECT-TYPE
			SYNTAX INTEGER (0..60)
			MAX-ACCESS read-only
			STATUS current
			DESCRIPTION
				"The z-coordinate of the AP."
			::= { wsSoleSiteApStatusEntry 4 }

		
		-- 1.3.6.1.4.1.388.14.8.1.5.13.1.5
		wsSoleSiteApStatusStatus OBJECT-TYPE
			SYNTAX Integer32
			MAX-ACCESS read-only
			STATUS current
			DESCRIPTION
				"Ap's adoption status."
			::= { wsSoleSiteApStatusEntry 5 }

		
		-- 1.3.6.1.4.1.388.14.8.1.5.13.1.6
		wsSoleSiteApStatusSwitchIp OBJECT-TYPE
			SYNTAX IpAddress
			MAX-ACCESS read-only
			STATUS current
			DESCRIPTION
				"Switch to which the AP is adopted."
			::= { wsSoleSiteApStatusEntry 6 }

		
		-- 1.3.6.1.4.1.388.14.8.1.5.13.1.7
		wsSoleSiteApStatus11aRadioIndex OBJECT-TYPE
			SYNTAX Integer32
			MAX-ACCESS read-only
			STATUS current
			DESCRIPTION
				"Index of 11a radio"
			::= { wsSoleSiteApStatusEntry 7 }

		
		-- 1.3.6.1.4.1.388.14.8.1.5.13.1.8
		wsSoleSiteApStatus11aRadioMac OBJECT-TYPE
			SYNTAX PhysAddress
			MAX-ACCESS read-only
			STATUS current
			DESCRIPTION
				"MAC address of 11a radio."
			::= { wsSoleSiteApStatusEntry 8 }

		
		-- 1.3.6.1.4.1.388.14.8.1.5.13.1.9
		wsSoleSiteApStatus11aRadioPower OBJECT-TYPE
			SYNTAX Integer32
			MAX-ACCESS read-only
			STATUS current
			DESCRIPTION
				"Transmit power in dBm of 11a radio."
			::= { wsSoleSiteApStatusEntry 9 }

		
		-- 1.3.6.1.4.1.388.14.8.1.5.13.1.10
		wsSoleSiteApStatus11aRadioChannel OBJECT-TYPE
			SYNTAX Integer32
			MAX-ACCESS read-only
			STATUS current
			DESCRIPTION
				"Channel of 11a radio."
			::= { wsSoleSiteApStatusEntry 10 }

		
		-- 1.3.6.1.4.1.388.14.8.1.5.13.1.11
		wsSoleSiteApStatus11bgRadioIndex OBJECT-TYPE
			SYNTAX Integer32
			MAX-ACCESS read-only
			STATUS current
			DESCRIPTION
				"Index of 11bg radio"
			::= { wsSoleSiteApStatusEntry 11 }

		
		-- 1.3.6.1.4.1.388.14.8.1.5.13.1.12
		wsSoleSiteApStatus11bgRadioMac OBJECT-TYPE
			SYNTAX PhysAddress
			MAX-ACCESS read-only
			STATUS current
			DESCRIPTION
				"MAC address of 11bg radio."
			::= { wsSoleSiteApStatusEntry 12 }

		
		-- 1.3.6.1.4.1.388.14.8.1.5.13.1.13
		wsSoleSiteApStatus11bgRadioPower OBJECT-TYPE
			SYNTAX Integer32
			MAX-ACCESS read-only
			STATUS current
			DESCRIPTION
				"Transmit power in dBm of 11bg radio."
			::= { wsSoleSiteApStatusEntry 13 }

		
		-- 1.3.6.1.4.1.388.14.8.1.5.13.1.14
		wsSoleSiteApStatus11bgRadioChannel OBJECT-TYPE
			SYNTAX Integer32
			MAX-ACCESS read-only
			STATUS current
			DESCRIPTION
				"Channel of 11bg radio."
			::= { wsSoleSiteApStatusEntry 14 }

		
		-- 1.3.6.1.4.1.388.14.8.1.6
		wsSoleLocateMuInfo OBJECT IDENTIFIER ::= { wsSoleMibModule 6 }

		
		-- 1.3.6.1.4.1.388.14.8.1.6.1
		wsSoleLocateMuAll OBJECT-TYPE
			SYNTAX TruthValue
			MAX-ACCESS read-write
			STATUS current
			DESCRIPTION
				"Boolean flag to enable Locating all MUs or stop locating all MUs."
			::= { wsSoleLocateMuInfo 1 }

		
		-- 1.3.6.1.4.1.388.14.8.1.6.2
		wsSoleLocateMuInterval OBJECT-TYPE
			SYNTAX Unsigned32 (5..3600)
			UNITS "secs"
			MAX-ACCESS read-write
			STATUS current
			DESCRIPTION
				"MU Location Interval in secs. This decides how frequently the MUs 
				are located (applicable to all located MUs)."
			::= { wsSoleLocateMuInfo 2 }

		
		-- 1.3.6.1.4.1.388.14.8.1.6.3
		wsSoleLocateMuTable OBJECT-TYPE
			SYNTAX SEQUENCE OF WsSoleLocateMuEntry
			MAX-ACCESS not-accessible
			STATUS current
			DESCRIPTION
				"Sole MU location table."
			::= { wsSoleLocateMuInfo 3 }

		
		-- 1.3.6.1.4.1.388.14.8.1.6.3.1
		wsSoleLocateMuEntry OBJECT-TYPE
			SYNTAX WsSoleLocateMuEntry
			MAX-ACCESS not-accessible
			STATUS current
			DESCRIPTION
				"Located MU list."
			INDEX { wsSoleLocateMuIndex }
			::= { wsSoleLocateMuTable 1 }

		
		WsSoleLocateMuEntry ::=
			SEQUENCE { 
				wsSoleLocateMuIndex
					INTEGER,
				wsSoleLocateMuMAC
					PhysAddress,
				wsSoleLocateMuRowStatus
					AbbrRowStatus
			 }

		-- 1.3.6.1.4.1.388.14.8.1.6.3.1.1
		wsSoleLocateMuIndex OBJECT-TYPE
			SYNTAX INTEGER (1..200)
			MAX-ACCESS read-only
			STATUS current
			DESCRIPTION
				"Simple Index."
			::= { wsSoleLocateMuEntry 1 }

		
		-- 1.3.6.1.4.1.388.14.8.1.6.3.1.2
		wsSoleLocateMuMAC OBJECT-TYPE
			SYNTAX PhysAddress
			MAX-ACCESS read-create
			STATUS current
			DESCRIPTION
				"MAC address of MU to be located."
			::= { wsSoleLocateMuEntry 2 }

		
		-- 1.3.6.1.4.1.388.14.8.1.6.3.1.3
		wsSoleLocateMuRowStatus OBJECT-TYPE
			SYNTAX AbbrRowStatus
			MAX-ACCESS read-create
			STATUS current
			DESCRIPTION
				"row status for a row in wsSoleLocateMuTable.
				
				"
			::= { wsSoleLocateMuEntry 3 }

		
		-- 1.3.6.1.4.1.388.14.8.1.7
		wsSoleSmartSurroundingsTable OBJECT-TYPE
			SYNTAX SEQUENCE OF WsSoleSmartSurroundingsEntry
			MAX-ACCESS not-accessible
			STATUS current
			DESCRIPTION
				"Smart Surroundings object table."
			::= { wsSoleMibModule 7 }

		
		-- 1.3.6.1.4.1.388.14.8.1.7.1
		wsSoleSmartSurroundingsEntry OBJECT-TYPE
			SYNTAX WsSoleSmartSurroundingsEntry
			MAX-ACCESS not-accessible
			STATUS current
			DESCRIPTION
				"Smart Surrounding table entry."
			INDEX { wsSoleSmartSurroundingsIndex }
			::= { wsSoleSmartSurroundingsTable 1 }

		
		WsSoleSmartSurroundingsEntry ::=
			SEQUENCE { 
				wsSoleSmartSurroundingsIndex
					INTEGER,
				wsSoleSmartSurroundingsType
					INTEGER,
				wsSoleSmartSurroundingID
					DisplayString,
				wsSoleSmartSurroundingsLocX
					INTEGER,
				wsSoleSmartSurroundingsLocY
					INTEGER,
				wsSoleSmartSurroundingsLocZ
					INTEGER,
				wsSoleSmartSurroundingsRange
					INTEGER,
				wsSoleSmartSurroundingsOrientation
					INTEGER,
				wsSoleSmartSurroundingsRowStatus
					AbbrRowStatus
			 }

		-- 1.3.6.1.4.1.388.14.8.1.7.1.1
		wsSoleSmartSurroundingsIndex OBJECT-TYPE
			SYNTAX INTEGER (1..100)
			MAX-ACCESS read-create
			STATUS current
			DESCRIPTION
				"Simple Index."
			::= { wsSoleSmartSurroundingsEntry 1 }

		
		-- 1.3.6.1.4.1.388.14.8.1.7.1.2
		wsSoleSmartSurroundingsType OBJECT-TYPE
			SYNTAX INTEGER
				{
				passive(1),
				fixedMU(2)
				}
			MAX-ACCESS read-create
			STATUS current
			DESCRIPTION
				"Type of smart surroundings object: passive tag or fixed-mu."
			::= { wsSoleSmartSurroundingsEntry 2 }

		
		-- 1.3.6.1.4.1.388.14.8.1.7.1.3
		wsSoleSmartSurroundingID OBJECT-TYPE
			SYNTAX DisplayString (SIZE (1..128))
			MAX-ACCESS read-create
			STATUS current
			DESCRIPTION
				"ID for smart surrounding object. Passive TAG ID or MU MAC."
			::= { wsSoleSmartSurroundingsEntry 3 }

		
		-- 1.3.6.1.4.1.388.14.8.1.7.1.4
		wsSoleSmartSurroundingsLocX OBJECT-TYPE
			SYNTAX INTEGER (0..65535)
			MAX-ACCESS read-create
			STATUS current
			DESCRIPTION
				"X coordinate for smart surrounding object."
			::= { wsSoleSmartSurroundingsEntry 4 }

		
		-- 1.3.6.1.4.1.388.14.8.1.7.1.5
		wsSoleSmartSurroundingsLocY OBJECT-TYPE
			SYNTAX INTEGER (0..65535)
			MAX-ACCESS read-create
			STATUS current
			DESCRIPTION
				"Y coordinate for smart surrounding object."
			::= { wsSoleSmartSurroundingsEntry 5 }

		
		-- 1.3.6.1.4.1.388.14.8.1.7.1.6
		wsSoleSmartSurroundingsLocZ OBJECT-TYPE
			SYNTAX INTEGER (0..65535)
			MAX-ACCESS read-create
			STATUS current
			DESCRIPTION
				"Z coordinate for smart surrounding object."
			::= { wsSoleSmartSurroundingsEntry 6 }

		
		-- 1.3.6.1.4.1.388.14.8.1.7.1.7
		wsSoleSmartSurroundingsRange OBJECT-TYPE
			SYNTAX INTEGER (1..50)
			MAX-ACCESS read-create
			STATUS current
			DESCRIPTION
				"Read range for smart surrounding object. 
				(Valid only for passive tags)."
			::= { wsSoleSmartSurroundingsEntry 7 }

		
		-- 1.3.6.1.4.1.388.14.8.1.7.1.8
		wsSoleSmartSurroundingsOrientation OBJECT-TYPE
			SYNTAX INTEGER
				{
				incrOnlyX(1),
				decrOnlyX(2),
				decrOnlyY(3),
				incrOnlyY(4)
				}
			MAX-ACCESS read-create
			STATUS current
			DESCRIPTION
				"Orientation (field of view) of smart surrounding object. 
				(Valid only for passive tags)."
			::= { wsSoleSmartSurroundingsEntry 8 }

		
		-- 1.3.6.1.4.1.388.14.8.1.7.1.9
		wsSoleSmartSurroundingsRowStatus OBJECT-TYPE
			SYNTAX AbbrRowStatus
			MAX-ACCESS read-create
			STATUS current
			DESCRIPTION
				"Row status for a row in wsSoleSmartSurroundingsTable."
			::= { wsSoleSmartSurroundingsEntry 9 }

		
		-- 1.3.6.1.4.1.388.14.8.1.8
		wsSoleTagTable OBJECT-TYPE
			SYNTAX SEQUENCE OF WsSoleTagEntry
			MAX-ACCESS not-accessible
			STATUS current
			DESCRIPTION
				"Show rtls tags table."
			::= { wsSoleMibModule 8 }

		
		-- 1.3.6.1.4.1.388.14.8.1.8.1
		wsSoleTagEntry OBJECT-TYPE
			SYNTAX WsSoleTagEntry
			MAX-ACCESS not-accessible
			STATUS current
			DESCRIPTION
				"Show rtls tags entry."
			INDEX { wsSoleTagIndex }
			::= { wsSoleTagTable 1 }

		
		WsSoleTagEntry ::=
			SEQUENCE { 
				wsSoleTagIndex
					INTEGER,
				wsSoleTagID
					DisplayString,
				wsSoleTagType
					DisplayString,
				wsSoleTagTimestamp
					DateAndTime,
				wsSoleTagLocX
					INTEGER,
				wsSoleTagLocY
					INTEGER,
				wsSoleTagZone
					INTEGER,
				wsSoleTagSiteName
					DisplayString
			 }

		-- 1.3.6.1.4.1.388.14.8.1.8.1.1
		wsSoleTagIndex OBJECT-TYPE
			SYNTAX INTEGER (1..4000)
			MAX-ACCESS read-only
			STATUS current
			DESCRIPTION
				"Index."
			::= { wsSoleTagEntry 1 }

		
		-- 1.3.6.1.4.1.388.14.8.1.8.1.2
		wsSoleTagID OBJECT-TYPE
			SYNTAX DisplayString
			MAX-ACCESS read-only
			STATUS current
			DESCRIPTION
				"Raw Tag ID."
			::= { wsSoleTagEntry 2 }

		
		-- 1.3.6.1.4.1.388.14.8.1.8.1.3
		wsSoleTagType OBJECT-TYPE
			SYNTAX DisplayString
			MAX-ACCESS read-only
			STATUS current
			DESCRIPTION
				"Tag type."
			::= { wsSoleTagEntry 3 }

		
		-- 1.3.6.1.4.1.388.14.8.1.8.1.4
		wsSoleTagTimestamp OBJECT-TYPE
			SYNTAX DateAndTime
			MAX-ACCESS read-only
			STATUS current
			DESCRIPTION
				"Timestamp."
			::= { wsSoleTagEntry 4 }

		
		-- 1.3.6.1.4.1.388.14.8.1.8.1.5
		wsSoleTagLocX OBJECT-TYPE
			SYNTAX INTEGER (0..65535)
			MAX-ACCESS read-only
			STATUS current
			DESCRIPTION
				"Location X (real coordinates). Depends on wsSoleSiteDimensionUnit for the site."
			::= { wsSoleTagEntry 5 }

		
		-- 1.3.6.1.4.1.388.14.8.1.8.1.6
		wsSoleTagLocY OBJECT-TYPE
			SYNTAX INTEGER (0..65535)
			MAX-ACCESS read-only
			STATUS current
			DESCRIPTION
				"Location Y (real coordinates). Depends on wsSoleSiteDimensionUnit for the site."
			::= { wsSoleTagEntry 6 }

		
		-- 1.3.6.1.4.1.388.14.8.1.8.1.7
		wsSoleTagZone OBJECT-TYPE
			SYNTAX INTEGER (1..48)
			MAX-ACCESS read-only
			STATUS current
			DESCRIPTION
				"Zone ID."
			::= { wsSoleTagEntry 7 }

		
		-- 1.3.6.1.4.1.388.14.8.1.8.1.8
		wsSoleTagSiteName OBJECT-TYPE
			SYNTAX DisplayString
			MAX-ACCESS read-only
			STATUS current
			DESCRIPTION
				"Corresponding site."
			::= { wsSoleTagEntry 8 }

		
		-- 1.3.6.1.4.1.388.14.8.1.100
		wsSoleConformance OBJECT IDENTIFIER ::= { wsSoleMibModule 100 }

		
		-- 1.3.6.1.4.1.388.14.8.1.100.2
		wsSoleCompliances OBJECT IDENTIFIER ::= { wsSoleConformance 2 }

		
		-- 1.3.6.1.4.1.388.14.8.1.100.1
		wsSoleGroups OBJECT IDENTIFIER ::= { wsSoleConformance 1 }

		
		-- 1.3.6.1.4.1.388.14.8.1.100.1.1
		wsSoleGroup OBJECT-GROUP
			OBJECTS { wsSoleAdapterSwIndex, wsSoleAdapterSwAdptrType, wsSoleAdapterSwVersion, wsSoleAdapterSwBuildDate, wsSoleAdapterCfgIndex, 
				wsSoleAdapterCfgAdptrType, wsSoleAdapterCfgLocateInterval, wsSoleAdapterCfgLocateEnable, wsSoleAdapterCfgEnable, wsSoleAdapterCfgLastErrorString, 
				wsSoleAdapterCfgMulticast, wsSoleAdapterEngineIndex, wsSoleAdapterEngineAdptrType, wsSoleAdapterEngineAdptrIp, wsSoleAdapterEngineAdptrPort, 
				wsSoleAdapterEngineAdptrState, wsSoleAdapterEngineNumMsgsRxFromEngine, wsSoleAdapterEngineNumMsgsTxToEngine, wsSoleAdapterEngineNumTagReportsTxToEngine, wsSoleAdapterEngineLastMsgRecvTime, 
				wsSoleAdapterEngineLastMsgSentTime, wsSoleSwitchSiteCoordinatesX, wsSoleSwitchSiteCoordinatesY, wsSoleSwitchSiteCoordinatesZ, wsSoleSwitchGeoCoordinatesWholeLongitude, 
				wsSoleSwitchGeoCoordinatesFractionLongitude, wsSoleSwitchGeoCoordinatesWholeLatitude, wsSoleSwitchGeoCoordinatesFractionLatitude, wsSoleSiteName, wsSoleSiteDescription, 
				wsSoleSiteDimensionUnit, wsSoleSiteDimensionScale, wsSoleSiteDimensionLength, wsSoleSiteDimensionWidth, wsSoleSiteDimensionHeight, 
				wsSoleNumBarriers, wsSoleNumDeployedAPs, wsSoleSiteLastErrorString, wsSoleSiteBarrierIndex, wsSoleSiteBarrierName, 
				wsSoleSiteBarrierShape, wsSoleSiteBarrierType, wsSoleSiteBarrierAttenuation, wsSoleLocateMuAll, wsSoleLocateMuInterval, 
				wsSoleLocateMuIndex, wsSoleLocateMuMAC, wsSoleLocateMuRowStatus, wsSoleSmartSurroundingsIndex, wsSoleSmartSurroundingsType, 
				wsSoleSmartSurroundingID, wsSoleSmartSurroundingsLocX, wsSoleSmartSurroundingsLocY, wsSoleSmartSurroundingsLocZ, wsSoleSmartSurroundingsRange, 
				wsSoleSmartSurroundingsOrientation, wsSoleSmartSurroundingsRowStatus, wsSoleTagIndex, wsSoleTagID, wsSoleTagType, 
				wsSoleTagTimestamp, wsSoleTagLocX, wsSoleTagLocY, wsSoleSiteApCoordinatesApMac, wsSoleSiteApCoordinatesX, 
				wsSoleSiteApCoordinatesY, wsSoleSiteApCoordinatesZ, wsSoleSiteApCoordinatesRowStatus, wsSoleSiteApStatusApMac, wsSoleSiteApStatusCoordinatesX, 
				wsSoleSiteApStatusCoordinatesY, wsSoleSiteApStatusCoordinatesZ, wsSoleSiteApStatusStatus, wsSoleSiteApStatusSwitchIp, wsSoleSiteApStatus11aRadioIndex, 
				wsSoleSiteApStatus11aRadioMac, wsSoleSiteApStatus11aRadioPower, wsSoleSiteApStatus11aRadioChannel, wsSoleSiteApStatus11bgRadioIndex, wsSoleSiteApStatus11bgRadioMac, 
				wsSoleSiteApStatus11bgRadioPower, wsSoleSiteApStatus11bgRadioChannel, wsSoleTagZone, wsSoleTagSiteName }
			STATUS current
			DESCRIPTION 
				"The group of current objects in wsSoleMibModule."
			::= { wsSoleGroups 1 }

		
	
	END

--
-- WS-SOLE-MIB.my
--
