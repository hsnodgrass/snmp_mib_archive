--
-- WS-SW-PORTVLAN-MIB.my
-- MIB generated by MG-SOFT Visual MIB Builder Version 6.0  Build 88
-- Thursday, March 20, 2008 at 14:32:53
--

	WS-SW-PORTVLAN-MIB DEFINITIONS ::= BEGIN
 
		IMPORTS
			OBJECT-GROUP, MODULE-COMPLIANCE			
				FROM SNMPv2-CONF			
			OBJECT-TYPE, MODULE-IDENTITY			
				FROM SNMPv2-SMI			
			TruthValue			
				FROM SNMPv2-TC			
			wsSwVlan			
				FROM WS-SW-SMI;
	
	
		-- 1.3.6.1.4.1.388.14.2.8.1
		wsSwPortVlanModule MODULE-IDENTITY 
			LAST-UPDATED "200803201500Z"		-- March 20, 2008 at 15:00 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Description."
			REVISION "200803201359Z"		-- March 20, 2008 at 13:59 GMT
			DESCRIPTION 
				"02a05
				Added wsSwPortNativeTagged to tag packets
				on the native vlan in trunking mode."
			REVISION "200611011504Z"		-- November 01, 2006 at 15:04 GMT
			DESCRIPTION 
				"02a04"
			REVISION "200606281042Z"		-- June 28, 2006 at 10:42 GMT
			DESCRIPTION 
				"02a03"
			REVISION "200605241733Z"		-- May 24, 2006 at 17:33 GMT
			DESCRIPTION 
				"02a02"
			REVISION "200604171417Z"		-- April 17, 2006 at 14:17 GMT
			DESCRIPTION 
				"02a01"
			REVISION "200603291604Z"		-- March 29, 2006 at 16:04 GMT
			DESCRIPTION 
				"01a02"
			REVISION "200603021105Z"		-- March 02, 2006 at 11:05 GMT
			DESCRIPTION 
				"01a01"
			::= { wsSwVlan 1 }

		
	
	
--
-- Node definitions
--
	
		-- 1.3.6.1.4.1.388.14.2.8.1.1
		wsSwPortVlanTable OBJECT-TYPE
			SYNTAX SEQUENCE OF WsSwPortVlanEntry
			MAX-ACCESS not-accessible
			STATUS current
			DESCRIPTION
				"Description."
			::= { wsSwPortVlanModule 1 }

		
		-- 1.3.6.1.4.1.388.14.2.8.1.1.1
		wsSwPortVlanEntry OBJECT-TYPE
			SYNTAX WsSwPortVlanEntry
			MAX-ACCESS not-accessible
			STATUS current
			DESCRIPTION
				"Description."
			INDEX { wsSwPortIfindex }
			::= { wsSwPortVlanTable 1 }

		
		WsSwPortVlanEntry ::=
			SEQUENCE { 
				wsSwPortIfindex
					INTEGER,
				wsSwPortSwitchportMode
					INTEGER,
				wsSwPortNativeVLAN
					INTEGER,
				wsSwPortVlan1K
					OCTET STRING,
				wsSwPortVlan2K
					OCTET STRING,
				wsSwPortVlan3K
					OCTET STRING,
				wsSwPortVlan4K
					OCTET STRING,
				wsSwPortNativeTagged
					TruthValue
			 }

		-- 1.3.6.1.4.1.388.14.2.8.1.1.1.1
		wsSwPortIfindex OBJECT-TYPE
			SYNTAX INTEGER (1..65536)
			MAX-ACCESS read-only
			STATUS current
			DESCRIPTION
				"Description."
			::= { wsSwPortVlanEntry 1 }

		
		-- 1.3.6.1.4.1.388.14.2.8.1.1.1.2
		wsSwPortSwitchportMode OBJECT-TYPE
			SYNTAX INTEGER
				{
				trunk(1),
				access(2)
				}
			MAX-ACCESS read-write
			STATUS current
			DESCRIPTION
				"Description."
			::= { wsSwPortVlanEntry 2 }

		
		-- 1.3.6.1.4.1.388.14.2.8.1.1.1.3
		wsSwPortNativeVLAN OBJECT-TYPE
			SYNTAX INTEGER
			MAX-ACCESS read-write
			STATUS current
			DESCRIPTION
				"Description."
			::= { wsSwPortVlanEntry 3 }

		
		-- 1.3.6.1.4.1.388.14.2.8.1.1.1.4
		wsSwPortVlan1K OBJECT-TYPE
			SYNTAX OCTET STRING (SIZE (128))
			MAX-ACCESS read-write
			STATUS current
			DESCRIPTION
				"Description."
			::= { wsSwPortVlanEntry 4 }

		
		-- 1.3.6.1.4.1.388.14.2.8.1.1.1.5
		wsSwPortVlan2K OBJECT-TYPE
			SYNTAX OCTET STRING (SIZE (128))
			MAX-ACCESS read-write
			STATUS current
			DESCRIPTION
				"Description."
			::= { wsSwPortVlanEntry 5 }

		
		-- 1.3.6.1.4.1.388.14.2.8.1.1.1.6
		wsSwPortVlan3K OBJECT-TYPE
			SYNTAX OCTET STRING (SIZE (128))
			MAX-ACCESS read-write
			STATUS current
			DESCRIPTION
				"Description."
			::= { wsSwPortVlanEntry 6 }

		
		-- 1.3.6.1.4.1.388.14.2.8.1.1.1.7
		wsSwPortVlan4K OBJECT-TYPE
			SYNTAX OCTET STRING (SIZE (128))
			MAX-ACCESS read-write
			STATUS current
			DESCRIPTION
				"Description."
			::= { wsSwPortVlanEntry 7 }

		
		-- 1.3.6.1.4.1.388.14.2.8.1.1.1.8
		wsSwPortNativeTagged OBJECT-TYPE
			SYNTAX TruthValue
			MAX-ACCESS read-write
			STATUS current
			DESCRIPTION
				"Tag packets on the native vlan in trunking mode."
			DEFVAL { false }
			::= { wsSwPortVlanEntry 8 }

		
		-- 1.3.6.1.4.1.388.14.2.8.1.2
		wsSwPortVlanCanSpanPort OBJECT-TYPE
			SYNTAX TruthValue
			MAX-ACCESS read-only
			STATUS current
			DESCRIPTION
				"On Monach, this value will return false since a VLAN can exist on only one 
				physical port (or MLT) or another. On QS5, it will return true since a VLAN
				can exist on many physical ports (or MLTs)."
			::= { wsSwPortVlanModule 2 }

		
		-- 1.3.6.1.4.1.388.14.2.8.1.100
		wsSwVlanConformance OBJECT IDENTIFIER ::= { wsSwPortVlanModule 100 }

		
		-- 1.3.6.1.4.1.388.14.2.8.1.100.1
		wsSwVlanCompliances OBJECT IDENTIFIER ::= { wsSwVlanConformance 1 }

		
		-- 1.3.6.1.4.1.388.14.2.8.1.100.1.1
		wsSwVlanCompliance MODULE-COMPLIANCE
			STATUS current
			DESCRIPTION 
				"Description."
			MODULE -- this module
				MANDATORY-GROUPS { wsSwVlanGroup }
			::= { wsSwVlanCompliances 1 }

		
		-- 1.3.6.1.4.1.388.14.2.8.1.100.2
		wsSwVlanGroups OBJECT IDENTIFIER ::= { wsSwVlanConformance 2 }

		
		-- 1.3.6.1.4.1.388.14.2.8.1.100.2.1
		wsSwVlanGroup OBJECT-GROUP
			OBJECTS { wsSwPortIfindex, wsSwPortSwitchportMode, wsSwPortNativeVLAN, wsSwPortVlan1K, wsSwPortVlan2K, 
				wsSwPortVlan3K, wsSwPortVlan4K, wsSwPortVlanCanSpanPort, wsSwPortNativeTagged }
			STATUS current
			DESCRIPTION 
				"Description."
			::= { wsSwVlanGroups 1 }

		
	
	END

--
-- WS-SW-PORTVLAN-MIB.my
--
