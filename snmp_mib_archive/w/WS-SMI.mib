--
-- WS-SMI.my
-- MIB generated by MG-SOFT Visual MIB Builder Version 6.0  Build 88
-- Wednesday, March 12, 2008 at 14:10:11
--

	WS-SMI DEFINITIONS ::= BEGIN
 
		IMPORTS
			enterprises, MODULE-IDENTITY, OBJECT-IDENTITY			
				FROM SNMPv2-SMI;
	
	
		-- 1.3.6.1.4.1.388
		symbol MODULE-IDENTITY 
			LAST-UPDATED "200803121500Z"		-- March 12, 2008 at 15:00 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"symbol smi mib"
			REVISION "200803121359Z"		-- March 12, 2008 at 13:59 GMT
			DESCRIPTION 
				"02a06
				Added OID for ws5000"
			REVISION "200708301859Z"		-- August 30, 2007 at 18:59 GMT
			DESCRIPTION 
				"02a05
				added OID for rfs6000"
			REVISION "200705221846Z"		-- May 22, 2007 at 18:46 GMT
			DESCRIPTION 
				"02a04
				added wsLs node for locationing services MIB"
			REVISION "200702221600Z"		-- February 22, 2007 at 16:00 GMT
			DESCRIPTION 
				"02a03"
			REVISION "200701241605Z"		-- January 24, 2007 at 16:05 GMT
			DESCRIPTION 
				"02a02"
			REVISION "200701161742Z"		-- January 16, 2007 at 17:42 GMT
			DESCRIPTION 
				"02a01"
			REVISION "200605241346Z"		-- May 24, 2006 at 13:46 GMT
			DESCRIPTION 
				"01a06"
			REVISION "200509242337Z"		-- September 24, 2005 at 23:37 GMT
			DESCRIPTION 
				"01a05"
			REVISION "200507071202Z"		-- July 07, 2005 at 12:02 GMT
			DESCRIPTION 
				"01a04"
			REVISION "200505171107Z"		-- May 17, 2005 at 11:07 GMT
			DESCRIPTION 
				"01a03"
			REVISION "200505051111Z"		-- May 05, 2005 at 11:11 GMT
			DESCRIPTION 
				"01a02"
			REVISION "200505041022Z"		-- May 04, 2005 at 10:22 GMT
			DESCRIPTION 
				"01a01"
			::= { enterprises 388 }

		
	
--
-- Node definitions
--
	
		-- 1.3.6.1.4.1.388.1
		spectrum24 OBJECT IDENTIFIER ::= { symbol 1 }

		
		-- 1.3.6.1.4.1.388.2
		wnms OBJECT IDENTIFIER ::= { symbol 2 }

		
		-- 1.3.6.1.4.1.388.3
		wlan OBJECT IDENTIFIER ::= { symbol 3 }

		
		-- 1.3.6.1.4.1.388.4
		customProducts1 OBJECT IDENTIFIER ::= { symbol 4 }

		
		-- 1.3.6.1.4.1.388.5
		customProducts2 OBJECT IDENTIFIER ::= { symbol 5 }

		
		-- 1.3.6.1.4.1.388.6
		ws5000 OBJECT IDENTIFIER ::= { symbol 6 }

		
		-- 1.3.6.1.4.1.388.7
		symbolProducts OBJECT IDENTIFIER ::= { symbol 7 }

		
		-- 1.3.6.1.4.1.388.8
		uk OBJECT IDENTIFIER ::= { symbol 8 }

		
		-- 1.3.6.1.4.1.388.9
		emm OBJECT IDENTIFIER ::= { symbol 9 }

		
		-- 1.3.6.1.4.1.388.10
		mk OBJECT IDENTIFIER ::= { symbol 10 }

		
		-- 1.3.6.1.4.1.388.11
		wsd OBJECT IDENTIFIER ::= { symbol 11 }

		
		-- 1.3.6.1.4.1.388.11.1
		sysoids OBJECT IDENTIFIER ::= { wsd 1 }

		
		-- 1.3.6.1.4.1.388.11.1.1
		ws2000 OBJECT-IDENTITY
			STATUS current
			DESCRIPTION 
				"Description."
			::= { sysoids 1 }

		
		-- 1.3.6.1.4.1.388.11.3
		wsdProduct OBJECT-IDENTITY
			STATUS current
			DESCRIPTION 
				"Description."
			::= { wsd 3 }

		
		-- 1.3.6.1.4.1.388.11.4
		wsdFeature OBJECT-IDENTITY
			STATUS current
			DESCRIPTION 
				"Description."
			::= { wsd 4 }

		
		-- 1.3.6.1.4.1.388.14
		ws OBJECT IDENTIFIER ::= { symbol 14 }

		
		-- 1.3.6.1.4.1.388.14.1
		wsInfra OBJECT IDENTIFIER ::= { ws 1 }

		
		-- 1.3.6.1.4.1.388.14.2
		wsSw OBJECT IDENTIFIER ::= { ws 2 }

		
		-- 1.3.6.1.4.1.388.14.3
		wsCc OBJECT IDENTIFIER ::= { ws 3 }

		
		-- 1.3.6.1.4.1.388.14.4
		wsMgmt OBJECT IDENTIFIER ::= { ws 4 }

		
		-- 1.3.6.1.4.1.388.14.5
		wsTrap OBJECT IDENTIFIER ::= { ws 5 }

		
		-- 1.3.6.1.4.1.388.14.6
		wsSec OBJECT IDENTIFIER ::= { ws 6 }

		
		-- 1.3.6.1.4.1.388.14.7
		wsRns OBJECT IDENTIFIER ::= { ws 7 }

		
		-- 1.3.6.1.4.1.388.14.8
		wsSole OBJECT IDENTIFIER ::= { ws 8 }

		
		-- 1.3.6.1.4.1.388.15
		rfs7000 OBJECT-IDENTITY
			STATUS current
			DESCRIPTION 
				"RFS7000 sys OID"
			::= { symbol 15 }

		
		-- 1.3.6.1.4.1.388.16
		rfs6000 OBJECT-IDENTITY
			STATUS current
			DESCRIPTION 
				"RFS6000 sys OID."
			::= { symbol 16 }

		
		-- 1.3.6.1.4.1.388.17
		ws5000SysObjectID OBJECT-IDENTITY
			STATUS current
			DESCRIPTION 
				"ws5000 sys OID"
			::= { symbol 17 }

		
	
	END

--
-- WS-SMI.my
--
