RC-TLS-MIB DEFINITIONS ::= BEGIN

IMPORTS
    MODULE-IDENTITY, OBJECT-TYPE, Integer32, IpAddress, Counter64, Counter32, Gauge32
        FROM SNMPv2-SMI
    DisplayString, TruthValue, MacAddress, RowStatus, DateAndTime, TimeStamp
        FROM SNMPv2-TC
    InterfaceIndex
        FROM IF-MIB
    rcTls, rcCos, rcBanRing, rcTdc, IdList, EnableValue
        FROM RAPID-CITY;

rcTlsMib MODULE-IDENTITY
       LAST-UPDATED     "200507280000Z"
       ORGANIZATION     "Bay Networks, Rapid-City Group"
       CONTACT-INFO     "
                                        Edwin Tsang
                         Postal:        Bay Networks, Inc.
                                        4401 Great America Parkway
                                        Santa Clara, CA 95052-8185

                         Tel:           408-495-6159
                         Fax:           408-495-5215
                         E-mail:        edwin_tsang@baynetworks.com
                        "
       DESCRIPTION      "Enterprise MIB for the Accelar product family."

       REVISION "200507280000Z" -- 28 July 2005
       DESCRIPTION "Version 15: Added rcBanRingNumOfUni to rcBanRingTable. 
			        Added rcBanDhRingNumOfUni to rcBanDhRingEntry"

       REVISION "200507190000Z" -- 19 July 2005
       DESCRIPTION "Version 14: Changed rcTlsUniAdminState  syntax to INTEGER enum"

       REVISION "200506140000Z" -- 14 June 2005 
       DESCRIPTION "Version 13:  Correct the range for rcTlsTdcPeriodicRate"
       
       REVISION "200505020000Z" -- 2 May 2005 
       DESCRIPTION "Version 12:  Depricated rcTlsUniQinqEtherType amd added rcTlsUniQinQEtherType 
				 Added new attributes: rcBanRingRrpHello,rcBanRingRrpHelloInterval,
					rcBanRingClearRrpStats and rcBanRingClearRdpStats to 
					rcBanRingTable.
				 Added new attributes: rcBanDhRingRrpHello, rcBanDhRingRrpHelloInterval, 
					rcBanDhRingClearRrpStats and rcBanDhRingClearRdpStats to 
					rcBanDhRingTable.
				 Added new tabels: rcBanRingStatsTable and rcBanDhRingStatsTable"			 
       
       REVISION "200504140000Z" -- 14 April 2005 
       DESCRIPTION "Version 11:  Obsolete rcTlsTestTdcHistoryMax and rcTlsTestTdcHistoryRemaining"

       REVISION "200503280000Z" -- 28 March 2005 
       DESCRIPTION "Version 10:  Added new attributes to rcTlsTdiStatsTable,rcCosProfileTable,
			   	rcTlsEndptStatsTable and rcTlsUniIpServiceStatsTable"

       REVISION "200503080000Z" -- 08 March 2005 
       DESCRIPTION "Version 9:  Added rcTlsUniIpServiceWatermarkIndication"
     
       REVISION "200502210000Z" -- 21 February 2005 
       DESCRIPTION "Version 8:  Added correct range for rcBanRingSaRbsBanPort"
      
       REVISION "200412220000Z" -- 22 December 2004 
       DESCRIPTION "Version 7:  Increased rcCosProfileTblIndex range for feature enhancement"
 	
       REVISION "200412020000Z" -- 02 December 2004 
       DESCRIPTION "Version 6:  Changed rcEsmPortStatsLastSample range to fix CR"

       REVISION "200411110000Z" -- 11 November 2004 
       DESCRIPTION "Version 5:  Cleaned up REVISIONs and fixed typo"

       REVISION "200410200000Z" -- 20 October 2004 
       DESCRIPTION "Version 4:  Updated rcTlsUniIpServiceTable for OE
                                Added rcTlsUniIpServiceStatsTable for OE
                                Added rcBanDhRingTablefor ESU Dual Homing Ring"

       REVISION "200410040000Z" -- 04 October 2004 
       DESCRIPTION "Version 3:  Added rorc1000BaseTX, rc100BaseTXPOE, rcGbicBx
                                to rcTlsEsmGroupLegacyType"  

       REVISION "200406250000Z" -- 25 June 2004 
       DESCRIPTION "Version 2:  Added rcTlsTdiSecMappedVlan, 
                                Added Egress attributes to rcTlsTdiEndptTable
                                Added TDI and Endpt stats attributes to
                                      rcTlsTdiStatsTable and rcTlsEndptStatsTable,
                                Added new MIB table rcTlsUniIpServiceTable for
                                      Ip Mcast feaure
                                Added new attributes to rcCosProfileTable"
       ::= { rcTls 0 }


-- TLSTDI Table

rcTlsTdiTable OBJECT-TYPE
        SYNTAX        SEQUENCE OF RcTlsTdiEntry
        MAX-ACCESS    not-accessible
        STATUS        current
        DESCRIPTION   ""
        ::= { rcTls 1 }
 
rcTlsTdiEntry OBJECT-TYPE
        SYNTAX        RcTlsTdiEntry
        MAX-ACCESS    not-accessible
        STATUS        current
        DESCRIPTION   "A TlsTdi (IPLT) table entry."
        INDEX         {  rcTlsTdiId }
        ::= { rcTlsTdiTable 1 }
 
RcTlsTdiEntry ::=
        SEQUENCE {
                rcTlsTdiId                    INTEGER,
                rcTlsTdiName                  DisplayString,
                rcTlsTdiMappedVlan            INTEGER,
                rcTlsTdiMuxMode               INTEGER,	
                rcTlsTdiADMEnabled            EnableValue,
                rcTlsTdiAction                INTEGER,
                rcTlsTdiAdminState            EnableValue,
                rcTlsTdiRowStatus             RowStatus,
                rcTlsTdiNumDestUniAddr        Integer32,
		rcTlsTdiDestUniAddr           OCTET STRING,
		rcTlsTdiMgmt                  EnableValue,
		rcTlsTdiSecMappedVlan         INTEGER
       }

rcTlsTdiId OBJECT-TYPE
        SYNTAX        INTEGER (1..16777215)
        MAX-ACCESS    read-only
        STATUS        current
        DESCRIPTION   "Transparent Domaine Identifier."
        ::= { rcTlsTdiEntry 1 }
 
rcTlsTdiName OBJECT-TYPE
        SYNTAX        DisplayString (SIZE (0..25)) 
        MAX-ACCESS    read-write
        STATUS        current
        DESCRIPTION   "Name of Transparent Domaine."
        ::= { rcTlsTdiEntry 2 }
 
rcTlsTdiMappedVlan OBJECT-TYPE
        SYNTAX        INTEGER (1..4094)
        MAX-ACCESS    read-write
        STATUS        current
        DESCRIPTION   "Vlan Tag used to distribute IPLT packets."
	DEFVAL        { 1 }	
        ::= { rcTlsTdiEntry 3 }

rcTlsTdiMuxMode  OBJECT-TYPE 
	 SYNTAX        INTEGER {
                         oneToone(1),       -- Only one qtag as member
                         manyToOne(2)       -- Many qtags as member
                        }
        MAX-ACCESS    read-write
        STATUS        current
        DESCRIPTION   "An end point for this TDI can have many qtags mapped to it 
		       only if the MuxMode is set to manyToOne.For a mantToOne Tdi
	               there will not be any remapping og qtags at the local egress."
        DEFVAL        { oneToone }
        ::= { rcTlsTdiEntry 4 }

rcTlsTdiADMEnabled OBJECT-TYPE
        SYNTAX        EnableValue
        MAX-ACCESS    read-write
        STATUS        current
        DESCRIPTION   "This Tdi will be included in the ADM message
                       only if this attribute is set."
	DEFVAL        { enable }
        ::= { rcTlsTdiEntry 5 }

rcTlsTdiAction  OBJECT-TYPE 
	 SYNTAX        INTEGER {
                         none(1),            -- none of the following
                         flushMacFdb(2)     -- flush MAC forwarding table
                        }
        MAX-ACCESS    read-write
        STATUS        current
        DESCRIPTION   "TDI related action- Flush Learned MAC addresses."
        DEFVAL        { none }
        ::= { rcTlsTdiEntry 6 }

rcTlsTdiAdminState OBJECT-TYPE
        SYNTAX        EnableValue
        MAX-ACCESS    read-write
        STATUS        current
        DESCRIPTION   "Administratively enable or disable a TDI."
	DEFVAL        { disable }
        ::= { rcTlsTdiEntry 7 }

rcTlsTdiRowStatus OBJECT-TYPE
        SYNTAX        RowStatus
        MAX-ACCESS    read-write
        STATUS        current
        DESCRIPTION   "Uses for controlling the creation and
                       deletion of this row."
        ::= { rcTlsTdiEntry 8 }

rcTlsTdiNumDestUniAddr   OBJECT-TYPE
	SYNTAX        Integer32	
	MAX-ACCESS    read-only
        STATUS        current
        DESCRIPTION   "number of Destination Uni Addreess in TDI"
        ::= { rcTlsTdiEntry 9 }

rcTlsTdiDestUniAddr   OBJECT-TYPE
	SYNTAX        OCTET STRING (SIZE(320))	
	MAX-ACCESS    read-write
        STATUS        current
        DESCRIPTION   "A list of Destination Uni Addreess, 4 byte per uni 
		       address. Up to 80 destination uni"
        ::= { rcTlsTdiEntry 10 }

rcTlsTdiMgmt OBJECT-TYPE
        SYNTAX        EnableValue
        MAX-ACCESS    read-write
        STATUS        current
        DESCRIPTION   "Enable/Disable TDI to a Mgmt TDI"
	DEFVAL        { disable }
        ::= { rcTlsTdiEntry 11 }

rcTlsTdiSecMappedVlan OBJECT-TYPE
        SYNTAX        INTEGER (1..4094)
        MAX-ACCESS    read-write
        STATUS        current
        DESCRIPTION   "Secondary Vlan Tag used to distribute IPLT packets."
	DEFVAL        { 1 }	
        ::= { rcTlsTdiEntry 12 }

-- TLS UNI Table  

rcTlsUniTable OBJECT-TYPE
        SYNTAX        SEQUENCE OF RcTlsUniEntry
        MAX-ACCESS    not-accessible
        STATUS        current
        DESCRIPTION   ""
        ::= { rcTls 2 }

rcTlsUniEntry OBJECT-TYPE
        SYNTAX        RcTlsUniEntry
        MAX-ACCESS    not-accessible
        STATUS        current
        DESCRIPTION   "LPE UNI table entry."
        INDEX         { rcTlsUniAddr }
        ::= { rcTlsUniTable 1 }

RcTlsUniEntry ::=
        SEQUENCE {
                rcTlsUniAddr              IpAddress,
                rcTlsUniPort              InterfaceIndex,
                rcTlsUniServiceType       INTEGER,
                rcTlsUniRingId            INTEGER,
                rcTlsUniRbsId             INTEGER,
                rcTlsUniRbsPort           INTEGER,
                rcTlsUniQinqEtherType     OCTET STRING,
		rcTlsUniServerPort	  InterfaceIndex,
                rcTlsUniAdminState        INTEGER,
                rcTlsUniOperState         INTEGER,
                rcTlsUniRowStatus         RowStatus,
		rcTlsUniName              DisplayString,
		rcTlsUniStandaloneRbsId   INTEGER,
		rcTlsUniStandaloneRbsPort INTEGER
        }

rcTlsUniAddr OBJECT-TYPE
        SYNTAX        IpAddress 
        MAX-ACCESS    read-only
        STATUS        current
        DESCRIPTION   "Address of this Uni Instance, it should be no 
                       more than 24 bits."
        ::= { rcTlsUniEntry 1 }

rcTlsUniPort OBJECT-TYPE
        SYNTAX        InterfaceIndex
        MAX-ACCESS    read-write
        STATUS        current
        DESCRIPTION   "BAN port where the UNI is a member."
        ::= { rcTlsUniEntry 2 }

rcTlsUniServiceType  OBJECT-TYPE
        SYNTAX         INTEGER {
                          tlstransparent (1),
                          tlsswitched(2),
		          ipmcuni(3),
			  ipmcbi(4),
			  qnq1(5),
			  qnq2(6)
                         } 
        MAX-ACCESS     read-write 
        STATUS         current
        DESCRIPTION    "Uni service type for the end-point. It is also
			releated with rcPortServiceType ."
        DEFVAL         { tlsswitched }
        ::= { rcTlsUniEntry 3 }

rcTlsUniRingId OBJECT-TYPE
        SYNTAX        INTEGER (0..254)
        MAX-ACCESS    read-write
        STATUS        current
        DESCRIPTION   "Ring ID where the UNI is a member."
	DEFVAL       { 0 }	
        ::= { rcTlsUniEntry 4 }

rcTlsUniRbsId OBJECT-TYPE
        SYNTAX        INTEGER (0..24)
        MAX-ACCESS    read-write
        STATUS        current
        DESCRIPTION   "RBS Module ID where the UNI is a member. 
                       Applicable only if rcTlsUniPort is part of an
                       RBS ring."
	DEFVAL       { 0 }
        ::= { rcTlsUniEntry 5 }

rcTlsUniRbsPort OBJECT-TYPE
        SYNTAX        INTEGER (0..28)
        MAX-ACCESS    read-write
        STATUS        current
        DESCRIPTION   "RBS port number where the UNI is a member.
                       Applicable only if rcTlsUniPort is part of an
                       RBS ring."
	DEFVAL        { 0 }
        ::= { rcTlsUniEntry 6 }


rcTlsUniQinqEtherType OBJECT-TYPE
        SYNTAX        OCTET STRING (SIZE(4))
        MAX-ACCESS    read-write
        STATUS        current
        DESCRIPTION   "The qinq ether type value. The string represents the hex value of ethert ype, e.g. 8600"
        DEFVAL       { "00:00:80:20"  }
        ::= { rcTlsUniEntry 7 }

rcTlsUniServerPort OBJECT-TYPE
        SYNTAX        InterfaceIndex
        MAX-ACCESS    read-write
        STATUS        current
        DESCRIPTION   "Server port associated with the legacy  UNI. 
			Valid only if rcTlsUniPort is an OPM server port."
        ::= { rcTlsUniEntry 8 }

rcTlsUniAdminState OBJECT-TYPE
        SYNTAX        INTEGER {
                         enable(1), 
                         disable(2),
                         forcedisable(3)
                      }
        MAX-ACCESS    read-write
        STATUS        current
        DESCRIPTION   "Value indicating whether the UNI is enabled"
        DEFVAL        { disable }
        ::= { rcTlsUniEntry 9 }

rcTlsUniOperState OBJECT-TYPE
        SYNTAX        INTEGER { 
                          up(1), 
                          down(2) 
                       }
        MAX-ACCESS    read-only
        STATUS        current
        DESCRIPTION   "The current operational state of this UNI."
        ::= { rcTlsUniEntry 10 }

rcTlsUniRowStatus   OBJECT-TYPE
        SYNTAX        RowStatus
        MAX-ACCESS    read-write
        STATUS        current
        DESCRIPTION   "Used for controlling the creation and deletion
                       of this row."
        ::= { rcTlsUniEntry 11}

rcTlsUniName OBJECT-TYPE
        SYNTAX        DisplayString (SIZE (0..25)) 
        MAX-ACCESS    read-write
        STATUS        current
        DESCRIPTION   "Name of UNI. By default, It is UNI-<uni id>"
        ::= { rcTlsUniEntry 12 }

rcTlsUniStandaloneRbsId OBJECT-TYPE
        SYNTAX        INTEGER (0..24)
        MAX-ACCESS    read-write
        STATUS        current
        DESCRIPTION   "Standalone Module ID where the UNI is a member. 
                       Applicable only if rcTlsUniPort is part of the UNI."
	DEFVAL       { 0 }
        ::= { rcTlsUniEntry 13 }

rcTlsUniStandaloneRbsPort OBJECT-TYPE
        SYNTAX        INTEGER (0..28)
        MAX-ACCESS    read-write
        STATUS        current
        DESCRIPTION   "RBS port number where the UNI is a member.
                       Applicable only if rcTlsUniPort is part of the UNI"
	DEFVAL        { 0 }
        ::= { rcTlsUniEntry 14 } 

-- TLSTDI EndPoint Table

rcTlsTdiEndptTable OBJECT-TYPE
        SYNTAX        SEQUENCE OF RcTlsTdiEndptEntry
        MAX-ACCESS    not-accessible
        STATUS        current
        DESCRIPTION   ""
        ::= { rcTls 3 }
 
rcTlsTdiEndptEntry OBJECT-TYPE
        SYNTAX        RcTlsTdiEndptEntry
        MAX-ACCESS    not-accessible
        STATUS        current
        DESCRIPTION   "A TlsTdiEndpt (IPLT) table entry."
        INDEX         { rcTlsTdiEndptTdId, rcTlsTdiEndptUniAddr }
        ::= { rcTlsTdiEndptTable 1 }
 
RcTlsTdiEndptEntry ::=
        SEQUENCE {
                rcTlsTdiEndptTdId                  INTEGER,
                rcTlsTdiEndptUniAddr               IpAddress,	
		rcTlsTdiEndptQtags                 OCTET STRING,
                rcTlsTdiEndptAdminState            EnableValue,
                rcTlsTdiEndptConMode               INTEGER,
                rcTlsTdiEndptHubUniAddr            IpAddress,
                rcTlsTdiEndptMacAddr               MacAddress,
                rcTlsTdiEndptCosProfileName        DisplayString,
                rcTlsTdiEndptPriMapping            OCTET STRING,
		rcTlsTdiEndptName 		   DisplayString,
                rcTlsTdiEndptMacTblSize            INTEGER,
                rcTlsTdiEndptMacTblWaterMk         INTEGER,
                rcTlsTdiEndptRemoteMacAgeTimer     INTEGER,
                rcTlsTdiEndptLocalMacAgeTimer      INTEGER,
                rcTlsTdiEndptOperState             INTEGER,
                rcTlsTdiEndptPriOverride           TruthValue,
              	rcTlsTdiEndptBpduTraffic           INTEGER,
                rcTlsTdiEndptAction                INTEGER,
                rcTlsTdiEndptRowStatus             RowStatus,
                rcTlsTdiEndptOuterQtag             INTEGER,
		rcTlsTdiEndptNumQtagIds            Integer32,
		rcTlsTdiEndptEgressCosProfileName  DisplayString,
		rcTlsTdiEndptIngressPolicer        EnableValue,
		rcTlsTdiEndptEgressPolicer         EnableValue

       }

 rcTlsTdiEndptTdId OBJECT-TYPE
        SYNTAX        INTEGER (1..16777215)
        MAX-ACCESS    read-only
        STATUS        current
        DESCRIPTION   "Tdi that the end-point is a member of."
        ::= { rcTlsTdiEndptEntry 1 }

rcTlsTdiEndptUniAddr OBJECT-TYPE
        SYNTAX        IpAddress
        MAX-ACCESS    read-only
        STATUS        current
        DESCRIPTION   "Uni Address of the end-point."
        ::= { rcTlsTdiEndptEntry 2 }

rcTlsTdiEndptQtags  OBJECT-TYPE
        SYNTAX        OCTET STRING (SIZE(512))
        MAX-ACCESS    read-write  
        STATUS        current
        DESCRIPTION  "A bitfield used to identify which QTAG is 
		      includes in this end point.	
		      The Most significant Bit field (bit 0) set represents 
		      the Qtag 1; The Less significant Bit field (bit 4095) 
		      set repesents the Qtag 4096,"
        ::= { rcTlsTdiEndptEntry 3 }

rcTlsTdiEndptAdminState OBJECT-TYPE
        SYNTAX        EnableValue
        MAX-ACCESS    read-write
        STATUS        current
        DESCRIPTION   "Admin control of the end-point state."
	DEFVAL        { disable }
        ::= { rcTlsTdiEndptEntry 4 }
 
rcTlsTdiEndptConMode OBJECT-TYPE
        SYNTAX        INTEGER {
                          any2any (0),
                          hub     (1),
                          spoke   (2),
                          pt2pt   (3)
                         } 
        MAX-ACCESS    read-write
        STATUS        current
        DESCRIPTION   "Type of end-point"
        DEFVAL       { any2any }
        ::= { rcTlsTdiEndptEntry 5 }
 
rcTlsTdiEndptHubUniAddr OBJECT-TYPE
        SYNTAX        IpAddress
        MAX-ACCESS    read-write
        STATUS        current
        DESCRIPTION   "Hub Uni address if connection mode (ConnMode) is
                       spoke. If the connection mode is pt2pt then this
                       is the Uni address of the other end-point."
        ::= { rcTlsTdiEndptEntry 6 }
 
rcTlsTdiEndptMacAddr OBJECT-TYPE
        SYNTAX        MacAddress
        MAX-ACCESS    read-write
        STATUS        current
        DESCRIPTION   "Hub OPM Mac address if connectio mode is spoke.
                       if the connection mode is pt2pt theb this is 
                       the OPM Mac address of the other end-point."
        ::= { rcTlsTdiEndptEntry 7 }
 
rcTlsTdiEndptCosProfileName OBJECT-TYPE
        SYNTAX        DisplayString (SIZE (0..20)) 
        MAX-ACCESS    read-write
        STATUS        current
        DESCRIPTION   "COS Profile Table Name."
        DEFVAL       { "DEFAULT_PROFILE"  } 
        ::= { rcTlsTdiEndptEntry 8 }
 
rcTlsTdiEndptPriMapping OBJECT-TYPE
        SYNTAX        OCTET STRING (SIZE(8))
        MAX-ACCESS    read-write
        STATUS        current
        DESCRIPTION   "Maps 802.1p priorities (0-7) to Optical Ethernet
                       Class of Service (COS) values (0-7) for packets
                       across a Uni. The first bytes represent the COS
                       for 802.1p priority 0. Subsequent bytes represent
                       the mappings of the remaining 802.1p priorities."
        DEFVAL       { "00:00:02:04:00:06:06:07"  }
        ::= { rcTlsTdiEndptEntry 9 }

rcTlsTdiEndptName OBJECT-TYPE
        SYNTAX        DisplayString (SIZE (0..30)) 
        MAX-ACCESS    read-write
        STATUS        current
        DESCRIPTION   "Name of Endpoint, By default, it would be EP-<tdi>.<uni>.
		       Example: tdi = 1, uni = 0.0.0.1, rcTlsTdiEndptName would
		       be EP-1.0.0.0.1"
        ::= { rcTlsTdiEndptEntry 10 }

rcTlsTdiEndptMacTblSize OBJECT-TYPE
        SYNTAX        INTEGER (0..97000) 
        MAX-ACCESS    read-write
        STATUS        current
        DESCRIPTION   "The maximum size of the MAC table. No limit if
                       it's set to 0."
        DEFVAL       { 0 }
        ::= { rcTlsTdiEndptEntry 11 }
 
rcTlsTdiEndptMacTblWaterMk OBJECT-TYPE
        SYNTAX        INTEGER (0..90)
        MAX-ACCESS    read-write
        STATUS        current
        DESCRIPTION   "The Low Water Mark for MAC table size. Set to 90%
                       of the table size, can be over-written."
        DEFVAL       { 0 }
        ::= { rcTlsTdiEndptEntry 12 }
 
rcTlsTdiEndptRemoteMacAgeTimer OBJECT-TYPE
        SYNTAX        INTEGER (1..65535)
        MAX-ACCESS    read-write
        STATUS        current
        DESCRIPTION   "Remote MAC address ageout timer in seconds."
	DEFVAL        { 300 }
        ::= { rcTlsTdiEndptEntry 13 }
 
rcTlsTdiEndptLocalMacAgeTimer OBJECT-TYPE
        SYNTAX        INTEGER (1..65535)
        MAX-ACCESS    read-write
        STATUS        current
        DESCRIPTION   "Local MAC address ageout timer in seconds."
	DEFVAL        { 300 }
        ::= { rcTlsTdiEndptEntry 14 }
 
rcTlsTdiEndptOperState OBJECT-TYPE
        SYNTAX        INTEGER { 
                          up(1), 
                          down(2) 
                       }
        MAX-ACCESS    read-only
        STATUS        current
        DESCRIPTION   "The current operational state of this ENDPOINT."
        ::= { rcTlsTdiEndptEntry 15 }

rcTlsTdiEndptPriOverride  OBJECT-TYPE
        SYNTAX          TruthValue
        MAX-ACCESS      read-write
        STATUS          current
        DESCRIPTION     "Enable or disable to override the Priority Mapping."
        DEFVAL          { false }
        ::= { rcTlsTdiEndptEntry 16 }

rcTlsTdiEndptBpduTraffic  OBJECT-TYPE
        SYNTAX          INTEGER {
			normal(1),
			expedite(2),
			drop(3)
			}
        MAX-ACCESS      read-write
        STATUS          current
        DESCRIPTION     "Bpdu traffic control."
        DEFVAL          { normal }
        ::= { rcTlsTdiEndptEntry 17 }

rcTlsTdiEndptAction  OBJECT-TYPE 
	 SYNTAX        INTEGER {
                         none(1),            -- none of the following
                         flushMacFdb(2)     -- flush MAC forwarding table
                        }
        MAX-ACCESS    read-write
        STATUS        current
        DESCRIPTION   "EndPt  related action- Flush Learned MAC addresses."
        DEFVAL        { none }
        ::= { rcTlsTdiEndptEntry 18 }

rcTlsTdiEndptRowStatus OBJECT-TYPE
        SYNTAX        RowStatus
        MAX-ACCESS    read-write
        STATUS        current
        DESCRIPTION   "Uses for controlling the creation and
                       deletion of this row."
        ::= { rcTlsTdiEndptEntry 19 }

rcTlsTdiEndptOuterQtag OBJECT-TYPE
        SYNTAX        INTEGER (0..4096) 
        MAX-ACCESS    read-write
        STATUS        current
        DESCRIPTION   "Outer qtag for QingQ"
	DEFVAL        { 0 }
        ::= { rcTlsTdiEndptEntry 20 }

rcTlsTdiEndptNumQtagIds OBJECT-TYPE
        SYNTAX        	Integer32
        MAX-ACCESS      read-only
        STATUS        	current
        DESCRIPTION   	"Used to indicate the number of Qtag IDs that
                      	are stored in the rcTlsTdiEndptQtags variable."
        ::= { rcTlsTdiEndptEntry 21 }

rcTlsTdiEndptEgressCosProfileName OBJECT-TYPE
        SYNTAX        DisplayString (SIZE (0..20)) 
        MAX-ACCESS    read-write
        STATUS        current
        DESCRIPTION   "Egress COS Profile Table Name."
        DEFVAL       { "DEFAULT_PROFILE"  } 
        ::= { rcTlsTdiEndptEntry 22 }

rcTlsTdiEndptIngressPolicer OBJECT-TYPE
        SYNTAX        EnableValue
        MAX-ACCESS    read-write
        STATUS        current
        DESCRIPTION   "Enable/disable to use Ingress Cos Profile table 
			(rcTlsTdiEndptCosProfileName) "
	DEFVAL        { enable }
        ::= { rcTlsTdiEndptEntry 23 }

rcTlsTdiEndptEgressPolicer OBJECT-TYPE
        SYNTAX        EnableValue
        MAX-ACCESS    read-write
        STATUS        current
        DESCRIPTION   "Enable/disable to use Egress Cos Profile table 
			(rcTlsTdiEndptEgressCosProfileName) "
	DEFVAL        { enable }
        ::= { rcTlsTdiEndptEntry 24 }

-- TLS REMOTE UNI MAC Table

rcTlsRemoteUniMacTable OBJECT-TYPE
        SYNTAX        SEQUENCE OF RcTlsRemoteUniMacEntry
        MAX-ACCESS    not-accessible
        STATUS        current
        DESCRIPTION   ""
        ::= { rcTls 4 }

rcTlsRemoteUniMacEntry OBJECT-TYPE
        SYNTAX        RcTlsRemoteUniMacEntry
        MAX-ACCESS    not-accessible
        STATUS        current
        DESCRIPTION   " UNI Mac table entry."
        INDEX         { rcTlsRemoteUniAddr }
        ::= { rcTlsRemoteUniMacTable 1 }

RcTlsRemoteUniMacEntry ::=
        SEQUENCE {
                rcTlsRemoteUniAddr           IpAddress,
                rcTlsRemoteUniMacOpm         MacAddress,
                rcTlsRemoteUniMacRowStatus   RowStatus
        }

rcTlsRemoteUniAddr OBJECT-TYPE
        SYNTAX        IpAddress
        MAX-ACCESS    read-only
        STATUS        current
        DESCRIPTION   "Uni address of this instance."
        ::= { rcTlsRemoteUniMacEntry 1 }

rcTlsRemoteUniMacOpm OBJECT-TYPE
        SYNTAX        MacAddress
        MAX-ACCESS    read-write
        STATUS        current
        DESCRIPTION   "Mac address of the OPM port associated with
                       this UNI address."
        ::= { rcTlsRemoteUniMacEntry 2 }

rcTlsRemoteUniMacRowStatus   OBJECT-TYPE
        SYNTAX        RowStatus
        MAX-ACCESS    read-write
        STATUS        current
        DESCRIPTION   "Used for controlling the creation and deletion
                       of this row."
        ::= { rcTlsRemoteUniMacEntry 3 }


-- TLSTDI USER MAC Table

rcTlsTdiUserMacTable OBJECT-TYPE
        SYNTAX        SEQUENCE OF RcTlsTdiUserMacEntry
        MAX-ACCESS    not-accessible
        STATUS        current
        DESCRIPTION   ""
        ::= { rcTls 5 }
 
rcTlsTdiUserMacEntry OBJECT-TYPE
        SYNTAX        RcTlsTdiUserMacEntry
        MAX-ACCESS    not-accessible
        STATUS        current
        DESCRIPTION   "A TlsTdiUserMac table entry."
        INDEX         { rcTlsTdiUserMacTdId , rcTlsTdiUserMacAddr  }
        ::= { rcTlsTdiUserMacTable 1 }
 
RcTlsTdiUserMacEntry ::=
        SEQUENCE {
                rcTlsTdiUserMacTdId       INTEGER,
                rcTlsTdiUserMacAddr       MacAddress,
                rcTlsTdiUserUniAddr       IpAddress,
                rcTlsTdiUserMacRowStatus  RowStatus
       }

rcTlsTdiUserMacTdId OBJECT-TYPE
        SYNTAX        INTEGER (1..16777215)
        MAX-ACCESS    read-only
        STATUS        current
        DESCRIPTION   "TDI Id associated with this user Mac."
        ::= { rcTlsTdiUserMacEntry 1 }
 
rcTlsTdiUserMacAddr OBJECT-TYPE
        SYNTAX        MacAddress
        MAX-ACCESS    read-only
        STATUS        current
        DESCRIPTION   "User Mac address of this instaance."
        ::= { rcTlsTdiUserMacEntry 2 }

rcTlsTdiUserUniAddr OBJECT-TYPE
        SYNTAX        IpAddress
        MAX-ACCESS    read-write
        STATUS        current
        DESCRIPTION   "Uni address associated with this user
                       Mac address."
        ::= { rcTlsTdiUserMacEntry 3 }

rcTlsTdiUserMacRowStatus OBJECT-TYPE
        SYNTAX        RowStatus
        MAX-ACCESS    read-write
        STATUS        current
        DESCRIPTION   "Used for controlling the creation and
                       deletion of this row."
        ::= { rcTlsTdiUserMacEntry 4 }

-- TLSTDI MEMBER UNI Table 

rcTlsTdiMemberUniTable OBJECT-TYPE
        SYNTAX        SEQUENCE OF RcTlsTdiMemberUniEntry
        MAX-ACCESS    not-accessible
        STATUS        current
        DESCRIPTION   ""
        ::= { rcTls 6 }
 
rcTlsTdiMemberUniEntry OBJECT-TYPE
        SYNTAX        RcTlsTdiMemberUniEntry
        MAX-ACCESS    not-accessible
        STATUS        current
        DESCRIPTION   "A TlsTdiMemberUni table entry."
        INDEX         { rcTlsTdiMemberUniTdId , rcTlsTdiMemberUniAddr  }
        ::= { rcTlsTdiMemberUniTable 1 }
 
RcTlsTdiMemberUniEntry ::=
        SEQUENCE {
                rcTlsTdiMemberUniTdId       INTEGER,
                rcTlsTdiMemberUniAddr       IpAddress,
                rcTlsTdiMemberUniRowStatus  RowStatus
       }

rcTlsTdiMemberUniTdId OBJECT-TYPE
        SYNTAX        INTEGER (1..16777215)
        MAX-ACCESS    read-only
        STATUS        current
        DESCRIPTION   "TDI Id associated with this user Mac."
        ::= { rcTlsTdiMemberUniEntry 1 }
 
rcTlsTdiMemberUniAddr OBJECT-TYPE
        SYNTAX        IpAddress
        MAX-ACCESS    read-only
        STATUS        current
        DESCRIPTION   "Uni address associated with this Tdi Member."
        ::= { rcTlsTdiMemberUniEntry 2 }

rcTlsTdiMemberUniRowStatus OBJECT-TYPE
        SYNTAX        RowStatus
        MAX-ACCESS    read-write
        STATUS        current
        DESCRIPTION   "Used for controlling the creation and
                       deletion of this row."
        ::= { rcTlsTdiMemberUniEntry 3 }


--TLSTDI STATS TABLE

rcTlsTdiStatsTable OBJECT-TYPE
        SYNTAX        SEQUENCE OF RcTlsTdiStatsEntry
        MAX-ACCESS    not-accessible
        STATUS        current
        DESCRIPTION   ""
        ::= { rcTls 7 }
 
rcTlsTdiStatsEntry OBJECT-TYPE
        SYNTAX        RcTlsTdiStatsEntry
        MAX-ACCESS    not-accessible
        STATUS        current
        DESCRIPTION   "A TlsTdi Statistics  table entry."
        INDEX         {  rcTlsTdiStatsId }
        ::= { rcTlsTdiStatsTable 1 }
 
RcTlsTdiStatsEntry ::=
        SEQUENCE {
                rcTlsTdiStatsId               INTEGER,
                rcTlsTdiStatsName             DisplayString,
                rcTlsTdiPremRxOctets	       Counter64,	
                rcTlsTdiPremRxDroppedOctets   Counter64,
	        rcTlsTdiGoldRxOctets	       Counter64,	
	        rcTlsTdiGoldRxDroppedOctets   Counter64,
	        rcTlsTdiSilverRxOctets	       Counter64,	
	        rcTlsTdiSilverRxDroppedOctets Counter64,
	        rcTlsTdiStndRxOctets	       Counter64,	
	        rcTlsTdiStndRxDroppedOctets   Counter64,
	        rcTlsTdiPremTxOctets	       Counter64,	
	        rcTlsTdiGoldTxOctets	       Counter64,	
	        rcTlsTdiSilverTxOctets	       Counter64,
	        rcTlsTdiStndTxOctets	       Counter64,	
	        rcTlsTdiPremTxMcastOctets     Counter64,	
                rcTlsTdiGoldTxMcastOctets     Counter64,	
	        rcTlsTdiSilverTxMcastOctets   Counter64,
	        rcTlsTdiStndTxMcastOctets     Counter64,
                rcTlsTdiStatsClear            TruthValue,
		rcTlsTdiPremCongestionDropOctets Counter64,
		rcTlsTdiGoldCongestionDropOctets Counter64,
		rcTlsTdiSilverCongestionDropOctets Counter64,	
		rcTlsTdiStndCongestionDropOctets Counter64,	
		rcTlsTdiPremCirDroppedOctets   Counter64,
		rcTlsTdiPremPirDroppedOctets   Counter64,
		rcTlsTdiGoldCirDroppedOctets   Counter64,
		rcTlsTdiGoldPirDroppedOctets   Counter64,
		rcTlsTdiSilverCirDroppedOctets   Counter64,
		rcTlsTdiSilverPirDroppedOctets   Counter64,
		rcTlsTdiStndCirDroppedOctets   Counter64,
		rcTlsTdiStndPirDroppedOctets   Counter64,
		rcTlsTdiPremTxDroppedOctets	       Counter64,	
	        rcTlsTdiGoldTxDroppedOctets	       Counter64,	
	        rcTlsTdiSilverTxDroppedOctets	       Counter64,
	        rcTlsTdiStndTxDroppedOctets	       Counter64,	
		rcTlsTdiPremTxCongestionDropOctets    Counter64,
		rcTlsTdiGoldTxCongestionDropOctets    Counter64,
		rcTlsTdiSilverTxCongestionDropOctets  Counter64,	
		rcTlsTdiStndTxCongestionDropOctets    Counter64,	
		rcTlsTdiPremTxCirDroppedOctets        Counter64,
		rcTlsTdiPremTxPirDroppedOctets        Counter64,
		rcTlsTdiGoldTxCirDroppedOctets        Counter64,
		rcTlsTdiGoldTxPirDroppedOctets        Counter64,
		rcTlsTdiSilverTxCirDroppedOctets      Counter64,
		rcTlsTdiSilverTxPirDroppedOctets      Counter64,
		rcTlsTdiStndTxCirDroppedOctets        Counter64,
		rcTlsTdiStndTxPirDroppedOctets        Counter64,
		rcTlsTdiRxMcastTotalOctets   	      Counter64,
		rcTlsTdiTxMcastTotalOctets   	      Counter64,
		rcTlsTdiPremRxMcastDroppedOctets      Counter64,
		rcTlsTdiGoldRxMcastDroppedOctets      Counter64,
		rcTlsTdiSilverRxMcastDroppedOctets    Counter64,
		rcTlsTdiStndRxMcastDroppedOctets      Counter64
   	}  

rcTlsTdiStatsId OBJECT-TYPE
        SYNTAX        INTEGER (1..16777215)
        MAX-ACCESS    read-only
        STATUS        current
        DESCRIPTION   "Transparent Domaine Identifier."
        ::= { rcTlsTdiStatsEntry 1 }
 
rcTlsTdiStatsName OBJECT-TYPE
        SYNTAX        DisplayString (SIZE (0..15)) 
        MAX-ACCESS    read-write
        STATUS        current
        DESCRIPTION   "Name of Transparent Domaine."
        ::= { rcTlsTdiStatsEntry 2 }
 
 rcTlsTdiPremRxOctets	OBJECT-TYPE
        SYNTAX        Counter64
        MAX-ACCESS    read-only
        STATUS        current
        DESCRIPTION  "Number of Premium Service Octets received from This End-Point."
        ::= { rcTlsTdiStatsEntry 3 } 

 rcTlsTdiPremRxDroppedOctets	OBJECT-TYPE
        SYNTAX        Counter64
        MAX-ACCESS    read-only
        STATUS        current
        DESCRIPTION  "Number of Premium Service Octets dropped from This End-Point."
        ::= { rcTlsTdiStatsEntry 4 } 
       
 rcTlsTdiGoldRxOctets	OBJECT-TYPE
        SYNTAX        Counter64
        MAX-ACCESS    read-only
        STATUS        current
        DESCRIPTION  "Number of Gold Service Octets received from This End-Point."
        ::= { rcTlsTdiStatsEntry 5 } 

 rcTlsTdiGoldRxDroppedOctets	OBJECT-TYPE
        SYNTAX        Counter64
        MAX-ACCESS    read-only
        STATUS        current
        DESCRIPTION  "Number of Gold Service Octets dropped from This End-Point."
        ::= { rcTlsTdiStatsEntry 6 } 
       

 rcTlsTdiSilverRxOctets	OBJECT-TYPE
        SYNTAX        Counter64
        MAX-ACCESS    read-only
        STATUS        current
        DESCRIPTION  "Number of Silver Service Octets received from This End-Point."
        ::= { rcTlsTdiStatsEntry 7 } 

 rcTlsTdiSilverRxDroppedOctets	OBJECT-TYPE
        SYNTAX        Counter64
        MAX-ACCESS    read-only
        STATUS        current
        DESCRIPTION  "Number of Silver Service Octets dropped from This End-Point."
        ::= { rcTlsTdiStatsEntry 8 } 
       
 rcTlsTdiStndRxOctets	OBJECT-TYPE
        SYNTAX        Counter64
        MAX-ACCESS    read-only
        STATUS        current
        DESCRIPTION  "Number of Standard (Best Effort) Service Octets received from This End-Point."
        ::= { rcTlsTdiStatsEntry 9 } 

 rcTlsTdiStndRxDroppedOctets	OBJECT-TYPE
        SYNTAX        Counter64
        MAX-ACCESS    read-only
        STATUS        current
        DESCRIPTION  "Number of Standard(BestEffort) Service Octets dropped from this End-Point."
        ::= { rcTlsTdiStatsEntry 10 } 
       
 rcTlsTdiPremTxOctets	OBJECT-TYPE
        SYNTAX        Counter64
        MAX-ACCESS    read-only
        STATUS        current
        DESCRIPTION  "Number of Premium Service Octets sent to his End-Point."
        ::= { rcTlsTdiStatsEntry 11 } 

 rcTlsTdiGoldTxOctets	OBJECT-TYPE
        SYNTAX        Counter64
        MAX-ACCESS    read-only
        STATUS        current
        DESCRIPTION  "Number of Gold Service Octets sent to his End-Point."
        ::= { rcTlsTdiStatsEntry 12 } 

 rcTlsTdiSilverTxOctets	OBJECT-TYPE
        SYNTAX        Counter64
        MAX-ACCESS    read-only
        STATUS        current
        DESCRIPTION  "Number of Silver Service Octets sent to his End-Point."
        ::= { rcTlsTdiStatsEntry 13 } 

 rcTlsTdiStndTxOctets	OBJECT-TYPE
        SYNTAX        Counter64
        MAX-ACCESS    read-only
        STATUS        current
        DESCRIPTION  "Number of Standard Service Octets sent to his End-Point."
        ::= { rcTlsTdiStatsEntry 14 } 
		

 rcTlsTdiPremTxMcastOctets	OBJECT-TYPE
        SYNTAX        Counter64
        MAX-ACCESS    read-only
        STATUS        current
        DESCRIPTION  "Number of Premium Service Multicast sent to his End-Point."
        ::= { rcTlsTdiStatsEntry 15 } 

rcTlsTdiGoldTxMcastOctets	OBJECT-TYPE
        SYNTAX        Counter64
        MAX-ACCESS    read-only
        STATUS        current
        DESCRIPTION  "Number of GoldService Multicast sent to his End-Point."
        ::= { rcTlsTdiStatsEntry 16 } 
		

rcTlsTdiSilverTxMcastOctets	OBJECT-TYPE
        SYNTAX        Counter64
        MAX-ACCESS    read-only
        STATUS        current
        DESCRIPTION  "Number of SilverService Multicast sent to his End-Point."
        ::= { rcTlsTdiStatsEntry 17 } 

rcTlsTdiStndTxMcastOctets	OBJECT-TYPE
        SYNTAX        Counter64
        MAX-ACCESS    read-only
        STATUS        current
        DESCRIPTION  "Number of Premium Service Multicast sent to his End-Point."
        ::= { rcTlsTdiStatsEntry 18 } 

rcTlsTdiStatsClear 	OBJECT-TYPE
        SYNTAX        TruthValue
        MAX-ACCESS    read-write
        STATUS        current
        DESCRIPTION   "Clear statistic."
        ::= { rcTlsTdiStatsEntry 19 }

rcTlsTdiPremCongestionDropOctets	OBJECT-TYPE
        SYNTAX        Counter64
        MAX-ACCESS    read-only
        STATUS        current
        DESCRIPTION  "Number of Prem Service Octets congestion drop"
        ::= { rcTlsTdiStatsEntry 20 } 
       
rcTlsTdiGoldCongestionDropOctets	OBJECT-TYPE
        SYNTAX        Counter64
        MAX-ACCESS    read-only
        STATUS        current
        DESCRIPTION  "Number of Gold Service Octets congestion drop"
        ::= { rcTlsTdiStatsEntry 21 } 

rcTlsTdiSilverCongestionDropOctets	OBJECT-TYPE
        SYNTAX        Counter64
        MAX-ACCESS    read-only
        STATUS        current
        DESCRIPTION  "Number of Silver Service Octets congestion drop"
        ::= { rcTlsTdiStatsEntry 22 } 

rcTlsTdiStndCongestionDropOctets	OBJECT-TYPE
        SYNTAX        Counter64
        MAX-ACCESS    read-only
        STATUS        current
        DESCRIPTION  "Number of Standard Service Octets congestion drop"
        ::= { rcTlsTdiStatsEntry 23 }

rcTlsTdiPremCirDroppedOctets	OBJECT-TYPE
        SYNTAX        Counter64
        MAX-ACCESS    read-only
        STATUS        current
        DESCRIPTION  "Number of Prem Service Octets CIR drop"
        ::= { rcTlsTdiStatsEntry 24 }

rcTlsTdiPremPirDroppedOctets	OBJECT-TYPE
        SYNTAX        Counter64
        MAX-ACCESS    read-only
        STATUS        current
        DESCRIPTION  "Number of Prem Service Octets PIR drop"
        ::= { rcTlsTdiStatsEntry 25 }
  
rcTlsTdiGoldCirDroppedOctets	OBJECT-TYPE
        SYNTAX        Counter64
        MAX-ACCESS    read-only
        STATUS        current
        DESCRIPTION  "Number of Gold Service Octets CIR drop"
        ::= { rcTlsTdiStatsEntry 26 }

rcTlsTdiGoldPirDroppedOctets	OBJECT-TYPE
        SYNTAX        Counter64
        MAX-ACCESS    read-only
        STATUS        current
        DESCRIPTION  "Number of Gold Service Octets PIR drop"
        ::= { rcTlsTdiStatsEntry 27 }

rcTlsTdiSilverCirDroppedOctets	OBJECT-TYPE
        SYNTAX        Counter64
        MAX-ACCESS    read-only
        STATUS        current
        DESCRIPTION  "Number of Silver Service Octets CIR drop"
        ::= { rcTlsTdiStatsEntry 28 }

rcTlsTdiSilverPirDroppedOctets	OBJECT-TYPE
        SYNTAX        Counter64
        MAX-ACCESS    read-only
        STATUS        current
        DESCRIPTION  "Number of Silver Service Octets PIR drop"
        ::= { rcTlsTdiStatsEntry 29 }

rcTlsTdiStndCirDroppedOctets	OBJECT-TYPE
        SYNTAX        Counter64
        MAX-ACCESS    read-only
        STATUS        current
        DESCRIPTION  "Number of Standard Service Octets CIR drop"
        ::= { rcTlsTdiStatsEntry 30 }  

rcTlsTdiStndPirDroppedOctets	OBJECT-TYPE
        SYNTAX        Counter64
        MAX-ACCESS    read-only
        STATUS        current
        DESCRIPTION  "Number of Standard Service Octets PIR drop"
        ::= { rcTlsTdiStatsEntry 31 } 

rcTlsTdiPremTxDroppedOctets	OBJECT-TYPE
        SYNTAX        Counter64
        MAX-ACCESS    read-only
        STATUS        current
        DESCRIPTION  "Tx Number of Premium Service Octets dropped from This End-Point."
        ::= { rcTlsTdiStatsEntry 32 } 
       
rcTlsTdiGoldTxDroppedOctets	OBJECT-TYPE
        SYNTAX        Counter64
        MAX-ACCESS    read-only
        STATUS        current
        DESCRIPTION  "Tx Number of Gold Service Octets dropped from This End-Point."
        ::= { rcTlsTdiStatsEntry 33 } 
       
rcTlsTdiSilverTxDroppedOctets	OBJECT-TYPE
        SYNTAX        Counter64
        MAX-ACCESS    read-only
        STATUS        current
        DESCRIPTION  "Tx Number of Silver Service Octets dropped from This End-Point."
        ::= { rcTlsTdiStatsEntry 34 } 
       
rcTlsTdiStndTxDroppedOctets	OBJECT-TYPE
        SYNTAX        Counter64
        MAX-ACCESS    read-only
        STATUS        current
        DESCRIPTION  "Tx Number of Standard(BestEffort) Service Octets dropped from this End-Point."
        ::= { rcTlsTdiStatsEntry 35 } 

rcTlsTdiPremTxCongestionDropOctets	OBJECT-TYPE
        SYNTAX        Counter64
        MAX-ACCESS    read-only
        STATUS        current
        DESCRIPTION  "Number of Prem Service Octets congestion drop"
        ::= { rcTlsTdiStatsEntry 36} 
       
rcTlsTdiGoldTxCongestionDropOctets	OBJECT-TYPE
        SYNTAX        Counter64
        MAX-ACCESS    read-only
        STATUS        current
        DESCRIPTION  "Number of Gold Service Octets congestion drop"
        ::= { rcTlsTdiStatsEntry 37 } 

rcTlsTdiSilverTxCongestionDropOctets	OBJECT-TYPE
        SYNTAX        Counter64
        MAX-ACCESS    read-only
        STATUS        current
        DESCRIPTION  "Number of Silver Service Octets congestion drop"
        ::= { rcTlsTdiStatsEntry 38 } 

rcTlsTdiStndTxCongestionDropOctets	OBJECT-TYPE
        SYNTAX        Counter64
        MAX-ACCESS    read-only
        STATUS        current
        DESCRIPTION  "Number of Standard Service Octets congestion drop"
        ::= { rcTlsTdiStatsEntry 39 }

rcTlsTdiPremTxCirDroppedOctets	OBJECT-TYPE
        SYNTAX        Counter64
        MAX-ACCESS    read-only
        STATUS        current
        DESCRIPTION  "Number of Prem Service Octets CIR drop"
        ::= { rcTlsTdiStatsEntry 40 }

rcTlsTdiPremTxPirDroppedOctets	OBJECT-TYPE
        SYNTAX        Counter64
        MAX-ACCESS    read-only
        STATUS        current
        DESCRIPTION  "Number of Prem Service Octets PIR drop"
        ::= { rcTlsTdiStatsEntry 41 }
  
rcTlsTdiGoldTxCirDroppedOctets	OBJECT-TYPE
        SYNTAX        Counter64
        MAX-ACCESS    read-only
        STATUS        current
        DESCRIPTION  "Number of Gold Service Octets CIR drop"
        ::= { rcTlsTdiStatsEntry 42 }

rcTlsTdiGoldTxPirDroppedOctets	OBJECT-TYPE
        SYNTAX        Counter64
        MAX-ACCESS    read-only
        STATUS        current
        DESCRIPTION  "Number of Gold Service Octets PIR drop"
        ::= { rcTlsTdiStatsEntry 43 }

rcTlsTdiSilverTxCirDroppedOctets	OBJECT-TYPE
        SYNTAX        Counter64
        MAX-ACCESS    read-only
        STATUS        current
        DESCRIPTION  "Number of Silver Service Octets CIR drop"
        ::= { rcTlsTdiStatsEntry 44 }

rcTlsTdiSilverTxPirDroppedOctets	OBJECT-TYPE
        SYNTAX        Counter64
        MAX-ACCESS    read-only
        STATUS        current
        DESCRIPTION  "Number of Silver Service Octets PIR drop"
        ::= { rcTlsTdiStatsEntry 45 }

rcTlsTdiStndTxCirDroppedOctets	OBJECT-TYPE
        SYNTAX        Counter64
        MAX-ACCESS    read-only
        STATUS        current
        DESCRIPTION  "Number of Standard Service Octets CIR drop"
        ::= { rcTlsTdiStatsEntry 46 }  

rcTlsTdiStndTxPirDroppedOctets	OBJECT-TYPE
        SYNTAX        Counter64
        MAX-ACCESS    read-only
        STATUS        current
        DESCRIPTION  "Number of Standard Service Octets PIR drop"
        ::= { rcTlsTdiStatsEntry 47 }  

rcTlsTdiRxMcastTotalOctets   OBJECT-TYPE
        SYNTAX        Counter64
        MAX-ACCESS    read-only
        STATUS        current
        DESCRIPTION  "Rx total Number of Mcast Octet"
        ::= { rcTlsTdiStatsEntry 48 }
  
rcTlsTdiTxMcastTotalOctets  OBJECT-TYPE
        SYNTAX        Counter64
        MAX-ACCESS    read-only
        STATUS        current
        DESCRIPTION  "Tx total Number of Mcast Octet"
        ::= { rcTlsTdiStatsEntry 49 }

rcTlsTdiPremRxMcastDroppedOctets	OBJECT-TYPE
        SYNTAX        Counter64
        MAX-ACCESS    read-only
        STATUS        current
        DESCRIPTION  "Number of Premium Service Rx Mcast Octets dropped from 
		      This TDI."
        ::= { rcTlsTdiStatsEntry 50 } 

rcTlsTdiGoldRxMcastDroppedOctets	OBJECT-TYPE
        SYNTAX        Counter64
        MAX-ACCESS    read-only
        STATUS        current
        DESCRIPTION  "Number of Gold Service Rx Mcast Octets dropped from 
		      This TDI."
        ::= { rcTlsTdiStatsEntry 51 } 

rcTlsTdiSilverRxMcastDroppedOctets	OBJECT-TYPE
        SYNTAX        Counter64
        MAX-ACCESS    read-only
        STATUS        current
        DESCRIPTION  "Number of Silver Service Rx Mcast Octets dropped from 
		      This TDI."
        ::= { rcTlsTdiStatsEntry 52 } 
                            
rcTlsTdiStndRxMcastDroppedOctets	OBJECT-TYPE
        SYNTAX        Counter64
        MAX-ACCESS    read-only
        STATUS        current
        DESCRIPTION  "Number of Standard Service Rx Mcast Octets dropped from 
		      This TDI."
        ::= { rcTlsTdiStatsEntry 53 } 
  
-- TLS ENDPT STATS TABLE

rcTlsEndptStatsTable OBJECT-TYPE
        SYNTAX        SEQUENCE OF RcTlsEndptStatsEntry
        MAX-ACCESS    not-accessible
        STATUS        current
        DESCRIPTION   ""
        ::= { rcTls 8 }
 
rcTlsEndptStatsEntry OBJECT-TYPE
        SYNTAX        RcTlsEndptStatsEntry
        MAX-ACCESS    not-accessible
        STATUS        current
        DESCRIPTION   "A Tls End-Point Statistics  table entry."
        INDEX         { rcTlsEndptStatsTdId,rcTlsEndptStatsUniAddr }
        ::= { rcTlsEndptStatsTable 1 }
 
RcTlsEndptStatsEntry ::=
        SEQUENCE {
                rcTlsEndptStatsTdId		INTEGER, 
 		rcTlsEndptStatsUniAddr          INTEGER,	
                rcTlsEndptPremRxOctets		      Counter64,	
       		rcTlsEndptPremRxDroppedOctets   Counter64,
		rcTlsEndptGoldRxOctets		      Counter64,	
		rcTlsEndptGoldRxDroppedOctets   Counter64,
		rcTlsEndptSilverRxOctets	      Counter64,	
		rcTlsEndptSilverRxDroppedOctets Counter64,
		rcTlsEndptStndRxOctets	      	Counter64,	
		rcTlsEndptStndRxDroppedOctets   Counter64,
		rcTlsEndptPremTxOctets	      	Counter64,	
		rcTlsEndptGoldTxOctets	      	Counter64,	
		rcTlsEndptSilverTxOctets	      Counter64,
		rcTlsEndptStndTxOctets	      	Counter64,	
		rcTlsEndptPremTxMcastOctets     Counter64,	
		rcTlsEndptGoldTxMcastOctets     Counter64,	
		rcTlsEndptSilverTxMcastOctets   Counter64,
		rcTlsEndptStndTxMcastOctets     Counter64,
                rcTlsEndptStatsClear            TruthValue,
		rcTlsEndptPremCongestionDropOctets Counter64,
		rcTlsEndptGoldCongestionDropOctets Counter64,
		rcTlsEndptSilverCongestionDropOctets Counter64,	
		rcTlsEndptStndCongestionDropOctets Counter64,	
		rcTlsEndptPremCirDroppedOctets   Counter64,
		rcTlsEndptPremPirDroppedOctets   Counter64,
		rcTlsEndptGoldCirDroppedOctets   Counter64,
		rcTlsEndptGoldPirDroppedOctets   Counter64,
		rcTlsEndptSilverCirDroppedOctets   Counter64,
		rcTlsEndptSilverPirDroppedOctets   Counter64,
		rcTlsEndptStndCirDroppedOctets   Counter64,
		rcTlsEndptStndPirDroppedOctets   Counter64,
		rcTlsEndptName                   DisplayString,
		rcTlsEndptPremTxDroppedOctets	       Counter64,	
		rcTlsEndptGoldTxDroppedOctets	       Counter64,	
		rcTlsEndptSilverTxDroppedOctets	       Counter64,
		rcTlsEndptStndTxDroppedOctets	       Counter64,	
		rcTlsEndptPremTxCongestionDropOctets   Counter64,
		rcTlsEndptGoldTxCongestionDropOctets   Counter64,
		rcTlsEndptSilverTxCongestionDropOctets Counter64,	
		rcTlsEndptStndTxCongestionDropOctets   Counter64,	
		rcTlsEndptPremTxCirDroppedOctets       Counter64,
		rcTlsEndptPremTxPirDroppedOctets       Counter64,
		rcTlsEndptGoldTxCirDroppedOctets       Counter64,
		rcTlsEndptGoldTxPirDroppedOctets       Counter64,
		rcTlsEndptSilverTxCirDroppedOctets     Counter64,
		rcTlsEndptSilverTxPirDroppedOctets     Counter64,
		rcTlsEndptStndTxCirDroppedOctets       Counter64,
		rcTlsEndptStndTxPirDroppedOctets       Counter64,
		rcTlsEndptRxMcastTotalOctets           Counter64,
		rcTlsEndptTxMcastTotalOctets           Counter64,
		rcTlsEndptPremRxMcastDroppedOctets     Counter64,
		rcTlsEndptGoldRxMcastDroppedOctets     Counter64,
		rcTlsEndptSilverRxMcastDroppedOctets   Counter64,
		rcTlsEndptStndRxMcastDroppedOctets     Counter64
      }

rcTlsEndptStatsTdId OBJECT-TYPE
        SYNTAX        INTEGER (1..16777215)
        MAX-ACCESS    read-only
        STATUS        current
        DESCRIPTION   "Tdi that the end-point is a member of."
        ::= { rcTlsEndptStatsEntry 1 }

 rcTlsEndptStatsUniAddr OBJECT-TYPE
        SYNTAX        INTEGER (1..16777215)
        MAX-ACCESS    read-only
        STATUS        current
        DESCRIPTION   "Transparent Domaine Identifier."
        ::= { rcTlsEndptStatsEntry 2 }
 
 rcTlsEndptPremRxOctets	OBJECT-TYPE
        SYNTAX        Counter64
        MAX-ACCESS    read-only
        STATUS        current
        DESCRIPTION  "Number of Premium Service Octets received from This End-Point."
        ::= { rcTlsEndptStatsEntry 3 } 

 rcTlsEndptPremRxDroppedOctets	OBJECT-TYPE
        SYNTAX        Counter64
        MAX-ACCESS    read-only
        STATUS        current
        DESCRIPTION  "Number of Premium Service Octets dropped from This End-Point."
        ::= { rcTlsEndptStatsEntry 4 } 
       
 rcTlsEndptGoldRxOctets	OBJECT-TYPE
        SYNTAX        Counter64
        MAX-ACCESS    read-only
        STATUS        current
        DESCRIPTION  "Number of Gold Service Octets received from This End-Point."
        ::= { rcTlsEndptStatsEntry 5 } 

 rcTlsEndptGoldRxDroppedOctets	OBJECT-TYPE
        SYNTAX        Counter64
        MAX-ACCESS    read-only
        STATUS        current
        DESCRIPTION  "Number of Gold Service Octets dropped from This End-Point."
        ::= { rcTlsEndptStatsEntry 6 } 
       

 rcTlsEndptSilverRxOctets	OBJECT-TYPE
        SYNTAX        Counter64
        MAX-ACCESS    read-only
        STATUS        current
        DESCRIPTION  "Number of Silver Service Octets received from This End-Point."
        ::= { rcTlsEndptStatsEntry 7 } 

 rcTlsEndptSilverRxDroppedOctets	OBJECT-TYPE
        SYNTAX        Counter64
        MAX-ACCESS    read-only
        STATUS        current
        DESCRIPTION  "Number of Silver Service Octets dropped from This End-Point."
        ::= { rcTlsEndptStatsEntry 8 } 
       
 rcTlsEndptStndRxOctets	OBJECT-TYPE
        SYNTAX        Counter64
        MAX-ACCESS    read-only
        STATUS        current
        DESCRIPTION  "Number of Standard (Best Effort) Service Octets received from This End-Point."
        ::= { rcTlsEndptStatsEntry 9 } 

 rcTlsEndptStndRxDroppedOctets	OBJECT-TYPE
        SYNTAX        Counter64
        MAX-ACCESS    read-only
        STATUS        current
        DESCRIPTION  "Number of Standard(BestEffort) Service Octets dropped from this End-Point."
        ::= { rcTlsEndptStatsEntry 10 } 
       
 rcTlsEndptPremTxOctets	OBJECT-TYPE
        SYNTAX        Counter64
        MAX-ACCESS    read-only
        STATUS        current
        DESCRIPTION  "Number of Premium Service Octets sent to his End-Point."
        ::= { rcTlsEndptStatsEntry 11 } 

 rcTlsEndptGoldTxOctets	OBJECT-TYPE
        SYNTAX        Counter64
        MAX-ACCESS    read-only
        STATUS        current
        DESCRIPTION  "Number of Gold Service Octets sent to his End-Point."
        ::= { rcTlsEndptStatsEntry 12 } 

 rcTlsEndptSilverTxOctets	OBJECT-TYPE
        SYNTAX        Counter64
        MAX-ACCESS    read-only
        STATUS        current
        DESCRIPTION  "Number of Silver Service Octets sent to his End-Point."
        ::= { rcTlsEndptStatsEntry 13 } 

 rcTlsEndptStndTxOctets	OBJECT-TYPE
        SYNTAX        Counter64
        MAX-ACCESS    read-only
        STATUS        current
        DESCRIPTION  "Number of Standard Service Octets sent to his End-Point."
        ::= { rcTlsEndptStatsEntry 14 } 
		

 rcTlsEndptPremTxMcastOctets	OBJECT-TYPE
        SYNTAX        Counter64
        MAX-ACCESS    read-only
        STATUS        current
        DESCRIPTION  "Number of Premium Service Multicast sent to his End-Point."
        ::= { rcTlsEndptStatsEntry 15 } 

rcTlsEndptGoldTxMcastOctets	OBJECT-TYPE
        SYNTAX        Counter64
        MAX-ACCESS    read-only
        STATUS        current
        DESCRIPTION  "Number of GoldService Multicast sent to his End-Point."
        ::= { rcTlsEndptStatsEntry 16 } 
		

rcTlsEndptSilverTxMcastOctets	OBJECT-TYPE
        SYNTAX        Counter64
        MAX-ACCESS    read-only
        STATUS        current
        DESCRIPTION  "Number of SilverService Multicast sent to his End-Point."
        ::= { rcTlsEndptStatsEntry 17 } 

rcTlsEndptStndTxMcastOctets	OBJECT-TYPE
        SYNTAX        Counter64
        MAX-ACCESS    read-only
        STATUS        current 
        DESCRIPTION  "Number of Premium Service Multicast sent to his End-Point."
        ::= { rcTlsEndptStatsEntry 18     } 

rcTlsEndptStatsClear      OBJECT-TYPE
        SYNTAX        TruthValue
        MAX-ACCESS    read-write
        STATUS        current
        DESCRIPTION   "Clear statistic."
        ::= { rcTlsEndptStatsEntry 19 }

rcTlsEndptPremCongestionDropOctets	OBJECT-TYPE
        SYNTAX        Counter64
        MAX-ACCESS    read-only
        STATUS        current
        DESCRIPTION  "Number of Prem Service Octets congestion drop"
        ::= { rcTlsEndptStatsEntry 20 } 
       
rcTlsEndptGoldCongestionDropOctets	OBJECT-TYPE
        SYNTAX        Counter64
        MAX-ACCESS    read-only
        STATUS        current
        DESCRIPTION  "Number of Gold Service Octets congestion drop"
        ::= { rcTlsEndptStatsEntry 21 } 

rcTlsEndptSilverCongestionDropOctets	OBJECT-TYPE
        SYNTAX        Counter64
        MAX-ACCESS    read-only
        STATUS        current
        DESCRIPTION  "Number of Silver Service Octets congestion drop"
        ::= { rcTlsEndptStatsEntry 22 } 

rcTlsEndptStndCongestionDropOctets	OBJECT-TYPE
        SYNTAX        Counter64
        MAX-ACCESS    read-only
        STATUS        current
        DESCRIPTION  "Number of Standard Service Octets congestion drop"
        ::= { rcTlsEndptStatsEntry 23 }

rcTlsEndptPremCirDroppedOctets	OBJECT-TYPE
        SYNTAX        Counter64
        MAX-ACCESS    read-only
        STATUS        current
        DESCRIPTION  "Number of Prem Service Octets CIR drop"
        ::= { rcTlsEndptStatsEntry 24 }

rcTlsEndptPremPirDroppedOctets	OBJECT-TYPE
        SYNTAX        Counter64
        MAX-ACCESS    read-only
        STATUS        current
        DESCRIPTION  "Number of Prem Service Octets PIR drop"
        ::= { rcTlsEndptStatsEntry 25 }
  
rcTlsEndptGoldCirDroppedOctets	OBJECT-TYPE
        SYNTAX        Counter64
        MAX-ACCESS    read-only
        STATUS        current
        DESCRIPTION  "Number of Gold Service Octets CIR drop"
        ::= { rcTlsEndptStatsEntry 26 }

rcTlsEndptGoldPirDroppedOctets	OBJECT-TYPE
        SYNTAX        Counter64
        MAX-ACCESS    read-only
        STATUS        current
        DESCRIPTION  "Number of Gold Service Octets PIR drop"
        ::= { rcTlsEndptStatsEntry 27 }

rcTlsEndptSilverCirDroppedOctets	OBJECT-TYPE
        SYNTAX        Counter64
        MAX-ACCESS    read-only
        STATUS        current
        DESCRIPTION  "Number of Silver Service Octets CIR drop"
        ::= { rcTlsEndptStatsEntry 28 }

rcTlsEndptSilverPirDroppedOctets	OBJECT-TYPE
        SYNTAX        Counter64
        MAX-ACCESS    read-only
        STATUS        current
        DESCRIPTION  "Number of Silver Service Octets PIR drop"
        ::= { rcTlsEndptStatsEntry 29 }

rcTlsEndptStndCirDroppedOctets	OBJECT-TYPE
        SYNTAX        Counter64
        MAX-ACCESS    read-only
        STATUS        current
        DESCRIPTION  "Number of Standard Service Octets CIR drop"
        ::= { rcTlsEndptStatsEntry 30 }  

rcTlsEndptStndPirDroppedOctets	OBJECT-TYPE
        SYNTAX        Counter64
        MAX-ACCESS    read-only
        STATUS        current
        DESCRIPTION  "Number of Standard Service Octets PIR drop"
        ::= { rcTlsEndptStatsEntry 31 } 
 
rcTlsEndptName OBJECT-TYPE
        SYNTAX        DisplayString (SIZE (0..30)) 
        MAX-ACCESS    read-only
        STATUS        current
        DESCRIPTION   "Name of Endpoint, By default, it would be EP-<tdi>.<uni>.
		       Example: tdi = 1, uni = 0.0.0.1, rcTlsTdiEndptName would
		       be EP-1.0.0.0.1"
        ::= { rcTlsEndptStatsEntry 32 }

rcTlsEndptPremTxDroppedOctets	OBJECT-TYPE
        SYNTAX        Counter64
        MAX-ACCESS    read-only
        STATUS        current
        DESCRIPTION  "Tx Number of Premium Service Octets dropped from This End-Point."
        ::= { rcTlsEndptStatsEntry 33 } 

rcTlsEndptGoldTxDroppedOctets	OBJECT-TYPE
        SYNTAX        Counter64
        MAX-ACCESS    read-only
        STATUS        current
        DESCRIPTION  "Tx Number of Gold Service Octets dropped from This End-Point."
        ::= { rcTlsEndptStatsEntry 34 } 
       
rcTlsEndptSilverTxDroppedOctets	OBJECT-TYPE
        SYNTAX        Counter64
        MAX-ACCESS    read-only
        STATUS        current
        DESCRIPTION  "Tx Number of Silver Service Octets dropped from This End-Point."
        ::= { rcTlsEndptStatsEntry 35 } 
       
rcTlsEndptStndTxDroppedOctets	OBJECT-TYPE
        SYNTAX        Counter64
        MAX-ACCESS    read-only
        STATUS        current
        DESCRIPTION  "Tx Number of Standard(BestEffort) Service Octets dropped from this End-Point."
        ::= { rcTlsEndptStatsEntry 36 } 

rcTlsEndptPremTxCongestionDropOctets	OBJECT-TYPE
        SYNTAX        Counter64
        MAX-ACCESS    read-only
        STATUS        current
        DESCRIPTION  "Tx Number of Prem Service Octets congestion drop"
        ::= { rcTlsEndptStatsEntry 37 } 
       
rcTlsEndptGoldTxCongestionDropOctets	OBJECT-TYPE
        SYNTAX        Counter64
        MAX-ACCESS    read-only
        STATUS        current
        DESCRIPTION  "Tx Number of Gold Service Octets congestion drop"
        ::= { rcTlsEndptStatsEntry 38 } 

rcTlsEndptSilverTxCongestionDropOctets	OBJECT-TYPE
        SYNTAX        Counter64
        MAX-ACCESS    read-only
        STATUS        current
        DESCRIPTION  "Tx Number of Silver Service Octets congestion drop"
        ::= { rcTlsEndptStatsEntry 39 } 

rcTlsEndptStndTxCongestionDropOctets	OBJECT-TYPE
        SYNTAX        Counter64
        MAX-ACCESS    read-only
        STATUS        current
        DESCRIPTION  "Tx Number of Standard Service Octets congestion drop"
        ::= { rcTlsEndptStatsEntry 40 }

rcTlsEndptPremTxCirDroppedOctets	OBJECT-TYPE
        SYNTAX        Counter64
        MAX-ACCESS    read-only
        STATUS        current
        DESCRIPTION  "Tx Number of Prem Service Octets CIR drop"
        ::= { rcTlsEndptStatsEntry 41 }

rcTlsEndptPremTxPirDroppedOctets	OBJECT-TYPE
        SYNTAX        Counter64
        MAX-ACCESS    read-only
        STATUS        current
        DESCRIPTION  "Tx Number of Prem Service Octets PIR drop"
        ::= { rcTlsEndptStatsEntry 42 }
  
rcTlsEndptGoldTxCirDroppedOctets	OBJECT-TYPE
        SYNTAX        Counter64
        MAX-ACCESS    read-only
        STATUS        current
        DESCRIPTION  "Tx Number of Gold Service Octets CIR drop"
        ::= { rcTlsEndptStatsEntry 43 }

rcTlsEndptGoldTxPirDroppedOctets	OBJECT-TYPE
        SYNTAX        Counter64
        MAX-ACCESS    read-only
        STATUS        current
        DESCRIPTION  "Tx Number of Gold Service Octets PIR drop"
        ::= { rcTlsEndptStatsEntry 44 }

rcTlsEndptSilverTxCirDroppedOctets	OBJECT-TYPE
        SYNTAX        Counter64
        MAX-ACCESS    read-only
        STATUS        current
        DESCRIPTION  "Tx Number of Silver Service Octets CIR drop"
        ::= { rcTlsEndptStatsEntry 45 }

rcTlsEndptSilverTxPirDroppedOctets	OBJECT-TYPE
        SYNTAX        Counter64
        MAX-ACCESS    read-only
        STATUS        current
        DESCRIPTION  "Tx Number of Silver Service Octets PIR drop"
        ::= { rcTlsEndptStatsEntry 46 }

rcTlsEndptStndTxCirDroppedOctets	OBJECT-TYPE
        SYNTAX        Counter64
        MAX-ACCESS    read-only
        STATUS        current
        DESCRIPTION  "Tx Number of Standard Service Octets CIR drop"
        ::= { rcTlsEndptStatsEntry 47 }  

rcTlsEndptStndTxPirDroppedOctets	OBJECT-TYPE
        SYNTAX        Counter64
        MAX-ACCESS    read-only
        STATUS        current
        DESCRIPTION  "TX Number of Standard Service Octets PIR drop"
        ::= { rcTlsEndptStatsEntry 48 }
 
rcTlsEndptRxMcastTotalOctets	OBJECT-TYPE
        SYNTAX        Counter64
        MAX-ACCESS    read-only
        STATUS        current
        DESCRIPTION  "Rx Total Number of Mcast Octets"
        ::= { rcTlsEndptStatsEntry 49 }
 
rcTlsEndptTxMcastTotalOctets	OBJECT-TYPE
        SYNTAX        Counter64
        MAX-ACCESS    read-only
        STATUS        current
        DESCRIPTION  "TX total Number of Mcast Octets"
        ::= { rcTlsEndptStatsEntry 50 }  

rcTlsEndptPremRxMcastDroppedOctets	OBJECT-TYPE
        SYNTAX        Counter64
        MAX-ACCESS    read-only
        STATUS        current
        DESCRIPTION  "Number of Premium Service Rx Mcast Octets dropped from 
		      This Endpoint."
        ::= { rcTlsEndptStatsEntry 51 } 

rcTlsEndptGoldRxMcastDroppedOctets	OBJECT-TYPE
        SYNTAX        Counter64
        MAX-ACCESS    read-only
        STATUS        current
        DESCRIPTION  "Number of Gold Service Rx Mcast Octets dropped from 
		      This Endpoint."
        ::= { rcTlsEndptStatsEntry 52 } 

rcTlsEndptSilverRxMcastDroppedOctets	OBJECT-TYPE
        SYNTAX        Counter64
        MAX-ACCESS    read-only
        STATUS        current
        DESCRIPTION  "Number of Silver Service Rx Mcast Octets dropped from 
		      This Endpoint."
        ::= { rcTlsEndptStatsEntry 53 } 
                            
rcTlsEndptStndRxMcastDroppedOctets	OBJECT-TYPE
        SYNTAX        Counter64
        MAX-ACCESS    read-only
        STATUS        current
        DESCRIPTION  "Number of Standard Service Rx Mcast Octets dropped from 
		      This Endpoint."
        ::= { rcTlsEndptStatsEntry 54 } 
      

-- Watermark type
rcTlsTrap OBJECT IDENTIFIER ::= { rcTls 9 } 

rcTlsEndptWatermarkIndication	OBJECT-TYPE
        SYNTAX        INTEGER { 
       			threasholdReached(1),
			tableFull(2)
       	   	      }	
        MAX-ACCESS    read-only
        STATUS        current 
        DESCRIPTION  " A Watermark indication signifies that the
                       Mac Table for the endpoint has reached its high watermark or already full "
        ::= { rcTlsTrap 1 } 

rcTlsUniIpServiceWatermarkIndication	OBJECT-TYPE
        SYNTAX        INTEGER { 
       			threasholdReached(1),
			tableFull(2)
       	   	      }	
        MAX-ACCESS    read-only
        STATUS        current 
        DESCRIPTION  " A Watermark indication signifies that the
                       Ip Table for the Uni Ip (Cust Ip) has reached its 
		       high watermark or already full "
        ::= { rcTlsTrap 2 } 


-- tlsEsmPort

rcTlsEsmGroupTable OBJECT-TYPE
        SYNTAX        SEQUENCE OF RcTlsEsmGroupEntry
        MAX-ACCESS    not-accessible
        STATUS        current
        DESCRIPTION   "Tls ESM port group table"
        ::= { rcTls 10 }

rcTlsEsmGroupEntry OBJECT-TYPE
        SYNTAX        RcTlsEsmGroupEntry
        MAX-ACCESS    not-accessible
        STATUS        current
        DESCRIPTION   "Entry containing info. for a particular group"
        INDEX         { rcTlsEsmGroupEsmPort, rcTlsEsmGroupLegacyPort, rcTlsEsmGroupUniAddr}
        ::= { rcTlsEsmGroupTable 1 }

RcTlsEsmGroupEntry ::= SEQUENCE {
	rcTlsEsmGroupEsmPort          InterfaceIndex,
	rcTlsEsmGroupLegacyPort       InterfaceIndex,
	rcTlsEsmGroupUniAddr	      IpAddress,
	rcTlsEsmGroupLegacyType       INTEGER,
	rcTlsEsmGroupTlsOverride      EnableValue,
	rcTlsEsmGroupVlanIds          IdList,	   
	rcTlsEsmGroupNumVlanIds       Integer32   	
	}

rcTlsEsmGroupEsmPort OBJECT-TYPE
        SYNTAX        InterfaceIndex	 
        MAX-ACCESS    not-accessible	
        STATUS        current
        DESCRIPTION   "ESM server port"
        ::= { rcTlsEsmGroupEntry 1}

rcTlsEsmGroupLegacyPort OBJECT-TYPE
        SYNTAX        InterfaceIndex	 
        MAX-ACCESS    not-accessible		
        STATUS        current
        DESCRIPTION   "ESM legacy port"
        ::= { rcTlsEsmGroupEntry 2}

rcTlsEsmGroupUniAddr OBJECT-TYPE
        SYNTAX        IpAddress 
        MAX-ACCESS    not-accessible
        STATUS        current
        DESCRIPTION   "Address of this Uni Instance, it should be no 
                       more than 24 bits."
        ::= { rcTlsEsmGroupEntry 3 }

rcTlsEsmGroupLegacyType OBJECT-TYPE
        SYNTAX        INTEGER {
			 other(0),           -- no port installed
                         rc100BaseTX(1),     -- (cat 5)
                         rc100BaseT2(2),     -- (cat 3)
                         rc100BaseF(3),      -- (100 mbps fiber)
                         rc1000BaseF(4),     -- (1000 mbps fiber)
                         rc1000BaseDualF(5), -- (fiber - dual connector)
                         rc10BaseF(6),       -- (10 mbps fiber)
                         rcPosMMF(7),        -- (multi mode fiber)
                         rcPosSMF(8),        -- (single mode fiber)
                         rcAtm(9),           -- (oc3, oc12, ds3, e3)
                         rcGbicLx(10),       -- (gigabit long haul)
                         rcGbicSx(11),       -- (gigabit short haul)
                         rcGbicXd(12),       -- (gigabit extended distance)
                         rcGbicCu(13),       -- (gigabit copper)
                         rcGbicOther(14),    -- (gigabit other)
                         rcOc3cSM(15),       -- (OC-3c SM)
                         rcOc3cMM(16),       -- (OC-3c MM)
                         rcOc3cCOPPER(17),   -- (OC-3c COPPER)
                         rcOc12cSM(18),      -- (OC-12c SM)
                         rcOc12cMM(19),      -- (OC-12c MM)
                         rcDs3(20),          -- (Ds3)
                         rcE3(21),           -- (E3)
                         rcGbicNone(22),     -- (Gbic card feature)
                         rc1000BaseT(23),    -- (1000 base copper)
                         rcGbicZx(24),       -- (gigabit very extended distance)
                         rcOc3cAtmSM(25),    -- (Atm OC-3c SM)
                         rcOc3cAtmMM(26),    -- (Atm OC-3c MM)
                         rcOc12cAtmSM(27),   -- (Atm OC-12c SM)
                         rcOc12cAtmMM(28),   -- (Atm OC-12c MM)
                         rcOc3cPosSM(29),    -- (Pos OC-3c SM)
                         rcOc3cPosMM(30),    -- (Pos OC-3c MM)
                         rcOc12cPosSM(31),   -- (Pos OC-12c SM)
                         rcOc12cPosMM(32),   -- (Pos OC-12c MM)
                         rcGbic1470(33),     -- (gigabit wavelength 1470)
                         rcGbic1490(34),     -- (gigabit wavelength 1490)
                         rcGbic1510(35),     -- (gigabit wavelength 1510)
                         rcGbic1530(36),     -- (gigabit wavelength 1530)
                         rcGbic1550(37),     -- (gigabit wavelength 1550)
                         rcGbic1570(38),     -- (gigabit wavelength 1570)
                         rcGbic1590(39),     -- (gigabit wavelength 1590)
                         rcGbic1610(40),     -- (gigabit wavelength 1610)
                         rcRmon(41),         -- (1000 base TProbe)
                         rcGbic1470APD(42),  -- (gigabit wavelength 1470-APD)
                         rcGbic1490APD(43),  -- (gigabit wavelength 1490-APD)
                         rcGbic1510APD(44),  -- (gigabit wavelength 1510-APD)
                         rcGbic1530APD(45),  -- (gigabit wavelength 1530-APD)
                         rcGbic1550APD(46),  -- (gigabit wavelength 1550-APD)
                         rcGbic1570APD(47),  -- (gigabit wavelength 1570-APD)
                         rcGbic1590APD(48),  -- (gigabit wavelength 1590-APD)
                         rcGbic1610APD(49),  -- (gigabit wavelength 1610-APD)
			 rc10GbLW(50),       -- (10 Gig Ethernet LW)
			 rc10GbLR(51),       -- (10 Gig Ethernet LR) 
                         rcLogicalServerPort(52), -- opm Prism used as a server for MPLS
			 rc1000BaseTX(53),   -- (tripple speed)
                         rc100BaseTXPOE(54), -- (tripple speed with POE support)
                         rcGbicBx(55)        -- (gigabit medium haul)
		}	
        MAX-ACCESS    read-only
        STATUS        current
        DESCRIPTION   "Address of this Uni Instance, it should be no 
                       more than 24 bits."
        ::= { rcTlsEsmGroupEntry 4 }

rcTlsEsmGroupTlsOverride OBJECT-TYPE
        SYNTAX        EnableValue
        MAX-ACCESS    read-only
        STATUS        current
        DESCRIPTION   "Indicate the legacy port prority bit setting" 
        ::= { rcTlsEsmGroupEntry 5 }

rcTlsEsmGroupVlanIds OBJECT-TYPE
        SYNTAX        IdList (SIZE (4096))
        MAX-ACCESS    read-only  
        STATUS        current
        DESCRIPTION   "An array used to identify which VLANs this ESM port 
                      is assigned to.  Each VLAN ID is stored as a two
                      octet value. The first octet in the pair holds
                      bits 15-8 of the VLAN ID, while the second octet
                      holds bits 7-0 of the VLAN ID."
        ::= { rcTlsEsmGroupEntry 6 }

rcTlsEsmGroupNumVlanIds OBJECT-TYPE
        SYNTAX        Integer32
        MAX-ACCESS    read-only
        STATUS        current
        DESCRIPTION   "Used to indicate the number of VLAN IDs that
                      are stored in the rcTlsEsmGroupVlanIds variable."
        ::= { rcTlsEsmGroupEntry 7 }

-- ESM port stats

rcTlsEsmPortStatsTable OBJECT-TYPE
        SYNTAX        SEQUENCE OF RcTlsEsmPortStatsEntry
        MAX-ACCESS    not-accessible
        STATUS        current
        DESCRIPTION   "Tls Ethernet Service Module(ESM) port Traffic rate Stats table. 
	               Which contains maximum 1440 samples for each ESM port for 
		       24 hours. Each entry contains the minimum traffic rate, 
		       the maximum traffic rate and the average traffic rate 
		       within this particular minute for this port"
        ::= { rcTls 11 }

rcTlsEsmPortStatsEntry OBJECT-TYPE
        SYNTAX        RcTlsEsmPortStatsEntry
        MAX-ACCESS    not-accessible
        STATUS        current
        DESCRIPTION   "Entry contains maximum 1440 samples (24 hours) traffice rate stats
	               for a particular port. Each entry is 1 mintue traffic rate stats.
		       Contains the minimum traffic rate, the maximum traffic rate and 
		       average traffic rate within this particular minute for this port"
	INDEX         { rcTlsEsmPortStatsPort, rcTlsEsmPortStatsSample}
        ::= { rcTlsEsmPortStatsTable 1 }

RcTlsEsmPortStatsEntry ::= SEQUENCE {
	rcTlsEsmPortStatsPort         InterfaceIndex,
	rcTlsEsmPortStatsSample       INTEGER,
	rcTlsEsmPortStatsTimestamp    OCTET STRING,
	rcTlsEsmPortStatsMin          Gauge32,
	rcTlsEsmPortStatsMax          Gauge32,
	rcTlsEsmPortStatsAve          Gauge32	
	}

rcTlsEsmPortStatsPort OBJECT-TYPE
        SYNTAX        InterfaceIndex	 
        MAX-ACCESS    not-accessible
        STATUS        current
        DESCRIPTION   "ESM server port interface"
        ::= { rcTlsEsmPortStatsEntry 1}

rcTlsEsmPortStatsSample OBJECT-TYPE
        SYNTAX        INTEGER (1..1440)	 
        MAX-ACCESS    not-accessible
        STATUS        current
        DESCRIPTION   "Sample of the time as minute over 24 houre. The maximum 
	               samples is 1440 for each port since the data is collected.
		       (60 minute * 24 hours)."
        ::= { rcTlsEsmPortStatsEntry 2}

rcTlsEsmPortStatsTimestamp OBJECT-TYPE
        SYNTAX        OCTET STRING (SIZE (17)) 	 
        MAX-ACCESS    read-only	
        STATUS        current
        DESCRIPTION   "Date and time string of the sampling time, 
		       Format:DD:MM:YY|HH:MM:SS (10:02:04|11:00:00)"
        ::= { rcTlsEsmPortStatsEntry 3}

rcTlsEsmPortStatsMin  OBJECT-TYPE
        SYNTAX        Gauge32 	 
        MAX-ACCESS    read-only	
        STATUS        current
        DESCRIPTION   "Minimum traffic rate within this minute interval. 
	               unit: byte per second"
        ::= { rcTlsEsmPortStatsEntry 4}

rcTlsEsmPortStatsMax  OBJECT-TYPE
        SYNTAX        Gauge32 	 
        MAX-ACCESS    read-only	
        STATUS        current
        DESCRIPTION   "Maximum traffic rate within this minute interval.
	               unit: byte per second"
        ::= { rcTlsEsmPortStatsEntry 5}

rcTlsEsmPortStatsAve  OBJECT-TYPE
        SYNTAX        Gauge32 	 
        MAX-ACCESS    read-only	
        STATUS        current
        DESCRIPTION   "Average traffic rate within this minute interval.
	               unit: byte per second"
        ::= { rcTlsEsmPortStatsEntry 6}

-- ESM port last 15 minutes stats 

rcEsmPortStatsLastTable OBJECT-TYPE
        SYNTAX        SEQUENCE OF RcEsmPortStatsLastEntry
        MAX-ACCESS    not-accessible
        STATUS        current
        DESCRIPTION   "Tls Ethernet Service Module (ESM) port last 15 samples traffic 
	               rate Stats table. Contains the last 15 samples for each ESM port. 
		       Each entry contains the minimum traffic rate, the maximum traffic 
		       rate and the average traffic rate within this particular minute 
		       for this port. This table provide the capability to the SNMP 
		       agent call to get the last 15 minute stats efficently."
        ::= { rcTls 12 }

rcEsmPortStatsLastEntry OBJECT-TYPE
        SYNTAX        RcEsmPortStatsLastEntry
        MAX-ACCESS    not-accessible
        STATUS        current
        DESCRIPTION   "Entry contains the minimum traffic rate, the maximum traffic 
		       rate and the average traffic rate within this particular minute 
		       for this port."
        INDEX         { rcEsmPortStatsLastPort, rcEsmPortStatsLastSample}
        ::= { rcEsmPortStatsLastTable 1 }

RcEsmPortStatsLastEntry ::= SEQUENCE {
	rcEsmPortStatsLastPort         InterfaceIndex,
	rcEsmPortStatsLastSample       INTEGER,
	rcEsmPortStatsLastTimestamp    OCTET STRING,
	rcEsmPortStatsLastMin          Gauge32,
	rcEsmPortStatsLastMax          Gauge32,
	rcEsmPortStatsLastAve          Gauge32 	
	}

rcEsmPortStatsLastPort OBJECT-TYPE
        SYNTAX        InterfaceIndex	 
        MAX-ACCESS    not-accessible	
        STATUS        current
        DESCRIPTION   "ESM server port interface"
        ::= { rcEsmPortStatsLastEntry 1}

rcEsmPortStatsLastSample OBJECT-TYPE
        SYNTAX        INTEGER (1..15)	 
        MAX-ACCESS    not-accessible	
        STATUS        current
        DESCRIPTION   "The last 15 minute-sample of rcTlsEsmPortStatsEntry"
        ::= { rcEsmPortStatsLastEntry 2}

rcEsmPortStatsLastTimestamp OBJECT-TYPE
        SYNTAX        OCTET STRING (SIZE (17)) 	 
        MAX-ACCESS    read-only	
        STATUS        current
        DESCRIPTION   "Date and time string of the sampling time, 
		       Format:DD:MM:YY|HH:MM:SS (10:02:04|11:00:00AM)"
        ::= { rcEsmPortStatsLastEntry 3}

rcEsmPortStatsLastMin  OBJECT-TYPE
        SYNTAX        Gauge32 	 
        MAX-ACCESS    read-only	
        STATUS        current
        DESCRIPTION   "Minimum traffic rate within this minute interval. 
	               unit: byte per second"
        ::= { rcEsmPortStatsLastEntry 4}

rcEsmPortStatsLastMax  OBJECT-TYPE
        SYNTAX        Gauge32 	 
        MAX-ACCESS    read-only	
        STATUS        current
        DESCRIPTION   "Maximum traffic rate within this minute interval.
	               unit: byte per second"
        ::= { rcEsmPortStatsLastEntry 5}

rcEsmPortStatsLastAve  OBJECT-TYPE
        SYNTAX        Gauge32 	 
        MAX-ACCESS    read-only	
        STATUS        current
        DESCRIPTION   "Average traffic rate within this minute interval.
	               unit: byte per second"
        ::= { rcEsmPortStatsLastEntry 6}

-- ESM port 60 sample average stats 

rcEsmPortStatsHourTable OBJECT-TYPE
        SYNTAX        SEQUENCE OF RcEsmPortStatsHourEntry
        MAX-ACCESS    not-accessible
        STATUS        current
        DESCRIPTION   "Tls Ethernet Service Module (ESM) port Hour traffic rate Stats table,
	               Contains maximum 24 entries for each port . Each entry represent one hour 
		       average traffic rate. Which is average of 60 samples rcTlsEsmPortStatsAve 
		       of the rcTlsEsmPortStatsTable for that particular hour"
        ::= { rcTls 13 }

rcEsmPortStatsHourEntry OBJECT-TYPE
        SYNTAX        RcEsmPortStatsHourEntry
        MAX-ACCESS    not-accessible
        STATUS        current
        DESCRIPTION   "Contains maximum 24 entries for each port . Each entry represent one hour 
		       average traffic rate. Which is average of 60 samples rcTlsEsmPortStatsAve 
		       of the rcTlsEsmPortStatsTable for that particular hour"
        INDEX         { rcEsmPortStatsHourPort, rcEsmPortStatsHourHour}
        ::= { rcEsmPortStatsHourTable 1 }

RcEsmPortStatsHourEntry ::= SEQUENCE {
	rcEsmPortStatsHourPort          InterfaceIndex,
	rcEsmPortStatsHourHour          INTEGER,
	rcEsmPortStatsHourFromTimestamp OCTET STRING,
	rcEsmPortStatsHourToTimestamp   OCTET STRING,
	rcEsmPortStatsHourAve           Gauge32 	
	}

rcEsmPortStatsHourPort OBJECT-TYPE
        SYNTAX        InterfaceIndex	 
        MAX-ACCESS    not-accessible	
        STATUS        current
        DESCRIPTION   "ESM server port interface"
        ::= { rcEsmPortStatsHourEntry 1}

rcEsmPortStatsHourHour OBJECT-TYPE
        SYNTAX        INTEGER (1..24)	 
        MAX-ACCESS    not-accessible	
        STATUS        current
        DESCRIPTION   "Hour index of the 24 hours sampling"
        ::= { rcEsmPortStatsHourEntry 2}

rcEsmPortStatsHourFromTimestamp OBJECT-TYPE
        SYNTAX        OCTET STRING (SIZE (17)) 	 
        MAX-ACCESS    read-only	
        STATUS        current
        DESCRIPTION   "Time stamp of starting time for the hour average traffic 
	               rate calculation.  
		       Format:DD:MM:YY|HH:MM:SS (10:02:04|11:00:00)"
        ::= { rcEsmPortStatsHourEntry 3}

rcEsmPortStatsHourToTimestamp OBJECT-TYPE
        SYNTAX        OCTET STRING (SIZE (17)) 	 
        MAX-ACCESS    read-only	
        STATUS        current
        DESCRIPTION   "Time stamp of ending time for the hour average traffic 
	               rate calculation.  
		       Format:DD:MM:YY|HH:MM:SS (10:02:04|11:00:00)" 
        ::= { rcEsmPortStatsHourEntry 4}

rcEsmPortStatsHourAve  OBJECT-TYPE
        SYNTAX        Gauge32 	 
        MAX-ACCESS    read-only	
        STATUS        current
        DESCRIPTION   "Average traffic rate for this hour interval. 
	               unit: byte per second"
        ::= { rcEsmPortStatsHourEntry 5}

-- Esm Port Stats daily static

rcEsmPortStatsDailyTable OBJECT-TYPE
        SYNTAX        SEQUENCE OF RcEsmPortStatsDailyEntry
        MAX-ACCESS    not-accessible
        STATUS        current
        DESCRIPTION   "Tls Ethernet Service Module(ESM) port daily Stats table contains 
	               24 hours sample stats for each port. Each entry contain 24 hours 
		       average traffic rate. WHich is average of all 1440 samples 
		       rcTlsEsmPortStatsAve of the rcTlsEsmPortStatsTable"
        ::= { rcTls 14 }

rcEsmPortStatsDailyEntry OBJECT-TYPE
        SYNTAX        RcEsmPortStatsDailyEntry
        MAX-ACCESS    not-accessible
        STATUS        current
        DESCRIPTION   "Entry contains average of all 1440 samples 
		       rcTlsEsmPortStatsAve of the rcTlsEsmPortStatsTable"
        INDEX         { rcEsmPortStatsDailyPort}
        ::= { rcEsmPortStatsDailyTable 1 }

RcEsmPortStatsDailyEntry ::= SEQUENCE {
	rcEsmPortStatsDailyPort          InterfaceIndex,
	rcEsmPortStatsDailyFromTimestamp OCTET STRING,
	rcEsmPortStatsDailyToTimestamp   OCTET STRING,
	rcEsmPortStatsDailyAve           Gauge32 	
	}

rcEsmPortStatsDailyPort OBJECT-TYPE
        SYNTAX        InterfaceIndex	 
        MAX-ACCESS    not-accessible	
        STATUS        current
        DESCRIPTION   "ESM server port interface"
        ::= { rcEsmPortStatsDailyEntry 1}

rcEsmPortStatsDailyFromTimestamp OBJECT-TYPE
        SYNTAX        OCTET STRING (SIZE (17)) 	 
        MAX-ACCESS    read-only	
        STATUS        current
        DESCRIPTION   "Time stamp of starting time for the daily average traffic 
	               rate calculation.  
		       Format:DD:MM:YY|HH:MM:SS (10:02:04|11:00:00)"
        ::= { rcEsmPortStatsDailyEntry 2}

rcEsmPortStatsDailyToTimestamp OBJECT-TYPE
        SYNTAX        OCTET STRING (SIZE (17)) 	 
        MAX-ACCESS    read-only	
        STATUS        current
        DESCRIPTION   "Time stamp of ending time for the daily average traffic 
	               rate calculation.  
		       Format:DD:MM:YY|HH:MM:SS (10:02:04|11:00:00)"
        ::= { rcEsmPortStatsDailyEntry 3}

rcEsmPortStatsDailyAve  OBJECT-TYPE
        SYNTAX        Gauge32 	 
        MAX-ACCESS    read-only	
        STATUS        current
        DESCRIPTION   "Average daily traffic rate for last 24 hours, unit: byte per second"
        ::= { rcEsmPortStatsDailyEntry 4}

-- Esm Port Stats total sample

rcEsmPortStatsSizeTable OBJECT-TYPE
        SYNTAX        SEQUENCE OF RcEsmPortStatsSizeEntry
        MAX-ACCESS    not-accessible
        STATUS        current
        DESCRIPTION   "Tls ESM port Stats total sample size for each port table"
        ::= { rcTls 15 }

rcEsmPortStatsSizeEntry OBJECT-TYPE
        SYNTAX        RcEsmPortStatsSizeEntry
        MAX-ACCESS    not-accessible
        STATUS        current
        DESCRIPTION   "Entry contain total samples size for a particular port"
        INDEX         { rcEsmPortStatsSizePort}
        ::= { rcEsmPortStatsSizeTable 1 }

RcEsmPortStatsSizeEntry ::= SEQUENCE {
	rcEsmPortStatsSizePort         InterfaceIndex,
	rcEsmPortStatsSizeTotal        Integer32
	}

rcEsmPortStatsSizePort OBJECT-TYPE
        SYNTAX        InterfaceIndex	 
        MAX-ACCESS    not-accessible	
        STATUS        current
        DESCRIPTION   "ESM server port"
        ::= { rcEsmPortStatsSizeEntry 1}

rcEsmPortStatsSizeTotal OBJECT-TYPE
        SYNTAX        Integer32 
        MAX-ACCESS    read-only	
        STATUS        current
        DESCRIPTION   "Times of the sample"
        ::= { rcEsmPortStatsSizeEntry 2}

-- ESM port stats clear
rcTlsEsmPortTable OBJECT-TYPE
        SYNTAX        SEQUENCE OF RcTlsEsmPortEntry
        MAX-ACCESS    not-accessible
        STATUS        current
        DESCRIPTION   "Tls ESM port table, which is used for reset the stats 
	               counter for each port"
        ::= { rcTls 16 }

rcTlsEsmPortEntry OBJECT-TYPE
        SYNTAX        RcTlsEsmPortEntry
        MAX-ACCESS    not-accessible
        STATUS        current
        DESCRIPTION   "Entry contain attribute for reset the stats counter 
	               for a particular port"
        INDEX         { rcTlsEsmPortPort}
        ::= { rcTlsEsmPortTable 1 }

RcTlsEsmPortEntry ::= SEQUENCE {
	rcTlsEsmPortPort             InterfaceIndex,
	rcTlsEsmPortClearStats       TruthValue
	}

rcTlsEsmPortPort OBJECT-TYPE
        SYNTAX        InterfaceIndex	 
        MAX-ACCESS    not-accessible	
        STATUS        current
        DESCRIPTION   "ESM server port"
        ::= { rcTlsEsmPortEntry 1}

rcTlsEsmPortClearStats OBJECT-TYPE
       SYNTAX        TruthValue
       MAX-ACCESS    read-write
       STATUS        current
       DESCRIPTION   "Clear Esm port Statistics"
       ::= {rcTlsEsmPortEntry 2 }  


-- rcTlsUniIpServiceTable 

rcTlsUniIpServiceTable OBJECT-TYPE
        SYNTAX        SEQUENCE OF RcTlsUniIpServiceEntry
        MAX-ACCESS    not-accessible
        STATUS        current
        DESCRIPTION   "Table contains a customer IP Vlan and the local IP 
		       Vlan for IP Mcast service over UNI in the BAN box "
        ::= { rcTls 17 }

rcTlsUniIpServiceEntry OBJECT-TYPE
        SYNTAX        RcTlsUniIpServiceEntry
        MAX-ACCESS    not-accessible
        STATUS        current
        DESCRIPTION   "Entry contains the customer IP Vlan and the Local 
		       Vlan for for the IP Mcast service over UNI in the BAN box"
        INDEX         { rcTlsUniIpServiceAddr, rcTlsUniIpServiceCustIpVlan }
        ::= { rcTlsUniIpServiceTable 1 }

RcTlsUniIpServiceEntry ::=
        SEQUENCE {
                rcTlsUniIpServiceAddr                       IpAddress,
                rcTlsUniIpServiceCustIpVlan                 INTEGER,
                rcTlsUniIpServiceServiceProviderIpVlan      INTEGER,
                rcTlsUniIpServiceRowStatus                  RowStatus,
		rcTlsUniIpServiceName                       DisplayString,
		rcTlsUniIpServiceAgeTimer                   INTEGER,
		rcTlsUniIpServiceIngressCosProfileName      DisplayString,
		rcTlsUniIpServiceIngressPolicer             EnableValue,
		rcTlsUniIpServiceEgressCosProfileName       DisplayString,
		rcTlsUniIpServiceEgressPolicer              EnableValue,
		rcTlsUniIpServiceAction                     INTEGER,
		rcTlsUniIpServiceAdminState                 EnableValue,
                rcTlsUniIpServiceOperState                  INTEGER,
	        rcTlsUniIpServicePriMapping                 OCTET STRING,
	        rcTlsUniIpServicePriOverride                TruthValue,
		rcTlsUniIpServiceIpTblSize                  INTEGER,	
		rcTlsUniIpServiceIpTblWaterMk               INTEGER	
        }

rcTlsUniIpServiceAddr OBJECT-TYPE
        SYNTAX        IpAddress 
        MAX-ACCESS    not-accessible
        STATUS        current
        DESCRIPTION   "Address of the Uni Instance - rcTlsUniAddr"
        ::= { rcTlsUniIpServiceEntry 1 }

rcTlsUniIpServiceCustIpVlan OBJECT-TYPE
        SYNTAX        INTEGER (1..4096)
        MAX-ACCESS    not-accessible
        STATUS        current
        DESCRIPTION   "Customer IP Vlan for UNI IP Mcast Vlan mapping"
        ::= { rcTlsUniIpServiceEntry 2 }

rcTlsUniIpServiceServiceProviderIpVlan OBJECT-TYPE
        SYNTAX        INTEGER (1..4096)
        MAX-ACCESS    read-create
        STATUS        current
        DESCRIPTION   "Service Provider IP Vlan for UNI IP Mcast Vlan mapping"
        ::= { rcTlsUniIpServiceEntry 3 }

rcTlsUniIpServiceName  OBJECT-TYPE
        SYNTAX        DisplayString (SIZE (0..30)) 
        MAX-ACCESS    read-create
        STATUS        current
        DESCRIPTION   "Name of UNI IP Service Vlan Entry. By default, It is 
		       VLAN-<uni id>-<cust ip vlan>"
        ::= { rcTlsUniIpServiceEntry 4 } 

rcTlsUniIpServiceRowStatus  OBJECT-TYPE
        SYNTAX        RowStatus
        MAX-ACCESS    read-create
        STATUS        current
        DESCRIPTION   "Used to create/delete entries in the rcTlsUniIpServiceEntry."
        ::= { rcTlsUniIpServiceEntry 5 }

rcTlsUniIpServiceAgeTimer  OBJECT-TYPE
        SYNTAX        INTEGER (1..1966020)
        MAX-ACCESS    read-create
        STATUS        current
        DESCRIPTION   "Mac address ageout timer in seconds.
		       Valid only if rcTlsUniIpService is Enabled"
	DEFVAL        { 300 }
        ::= { rcTlsUniIpServiceEntry 6 }

rcTlsUniIpServiceIngressCosProfileName OBJECT-TYPE
        SYNTAX        DisplayString (SIZE (1..20)) 
        MAX-ACCESS    read-write
        STATUS        current
        DESCRIPTION   "Ingress COS Profile Table Name for Customer Ip Service"
        DEFVAL       { "DEFAULT_PROFILE"  } 
        ::= { rcTlsUniIpServiceEntry 7 }

rcTlsUniIpServiceIngressPolicer OBJECT-TYPE
        SYNTAX        EnableValue
        MAX-ACCESS    read-create
        STATUS        current
        DESCRIPTION   "Enable/disable to use Ingress Cos Profile table 
			(rcTlsUniIpServiceIngressCosProfileName) for this 
			customer IP service"
	DEFVAL        { enable }
        ::= { rcTlsUniIpServiceEntry 8 }

rcTlsUniIpServiceEgressCosProfileName OBJECT-TYPE
        SYNTAX        DisplayString (SIZE (0..20)) 
        MAX-ACCESS    read-create
        STATUS        current
        DESCRIPTION   "Egress COS Profile Table Name for this customer IP
			Service."
        DEFVAL       { "DEFAULT_PROFILE"  } 
        ::= { rcTlsUniIpServiceEntry 9 }

rcTlsUniIpServiceEgressPolicer OBJECT-TYPE
        SYNTAX        EnableValue
        MAX-ACCESS    read-create
        STATUS        current
        DESCRIPTION   "Enable/disable to use Egress Cos Profile table 
			(rcTlsUniIpServiceEgressCosProfileName) for this 
			customer Ip Service"
	DEFVAL        { disable }
        ::= { rcTlsUniIpServiceEntry 10 }

rcTlsUniIpServiceAction  OBJECT-TYPE 
	SYNTAX        INTEGER {
                         none(1),       -- none of the following
                         flushIp(2)     -- flush Ip forwarding table
                      }
        MAX-ACCESS    read-create
        STATUS        current
        DESCRIPTION   "Mcast UNI related action- Flush learningMac addresse"
        DEFVAL        { none }
	::= { rcTlsUniIpServiceEntry 11 }

rcTlsUniIpServiceAdminState OBJECT-TYPE
        SYNTAX        EnableValue
        MAX-ACCESS    read-create
        STATUS        current
        DESCRIPTION   "Value indicating whether the Ip Service is enabled"
        DEFVAL        { disable }
        ::= { rcTlsUniIpServiceEntry 12 }

rcTlsUniIpServiceOperState OBJECT-TYPE
        SYNTAX        INTEGER { 
                          up(1), 
                          down(2) 
                       }
        MAX-ACCESS    read-only
        STATUS        current
        DESCRIPTION   "The current operational state of this Customer IP Vlan."
        ::= { rcTlsUniIpServiceEntry 13 }

rcTlsUniIpServicePriMapping OBJECT-TYPE
        SYNTAX        OCTET STRING (SIZE(8))
        MAX-ACCESS    read-create
        STATUS        current
        DESCRIPTION   "Maps 802.1p priorities (0-7) to Optical Ethernet
                       Class of Service (COS) values (0-7) for packets
                       across a Uni. The first bytes represent the COS
                       for 802.1p priority 0. Subsequent bytes represent
                       the mappings of the remaining 802.1p priorities."
        DEFVAL       { "00:00:02:04:00:06:06:07"  }
        ::= { rcTlsUniIpServiceEntry 14 }

rcTlsUniIpServicePriOverride  OBJECT-TYPE
        SYNTAX          TruthValue
        MAX-ACCESS      read-create
        STATUS          current
        DESCRIPTION     "Enable or disable to override the Priority Mapping."
        DEFVAL          { false }
        ::= {rcTlsUniIpServiceEntry 15 }

rcTlsUniIpServiceIpTblSize OBJECT-TYPE
        SYNTAX        INTEGER (0..97000) 
        MAX-ACCESS    read-create
        STATUS        current
        DESCRIPTION   "The maximum size of the IP table. No limit if
                       it's set to 0."
        DEFVAL       { 0 }
        ::= { rcTlsUniIpServiceEntry 16 }

rcTlsUniIpServiceIpTblWaterMk OBJECT-TYPE
        SYNTAX        INTEGER (0..90)
        MAX-ACCESS    read-create
        STATUS        current
        DESCRIPTION   "The Low Water Mark for Ip table size. Set to 90%
                       of the table size, can be over-written."
        DEFVAL       { 0 }
        ::= { rcTlsUniIpServiceEntry 17 }

-- Tls Uni Ip Service  STATS TABLE

rcTlsUniIpServiceStatsTable OBJECT-TYPE
        SYNTAX        SEQUENCE OF RcTlsUniIpServiceStatsEntry
        MAX-ACCESS    not-accessible
        STATUS        current
        DESCRIPTION   "Tls Uni Ip service statistics table. Which is used to represent
			the Customer Ip vlan service statistics for Uni Ip Service"
        ::= { rcTls 18 }
 
rcTlsUniIpServiceStatsEntry OBJECT-TYPE
        SYNTAX        RcTlsUniIpServiceStatsEntry
        MAX-ACCESS    not-accessible
        STATUS        current
        DESCRIPTION   "A Tls Uni Ip Service Statistics table entry. Which is used
                       for customer Ip Vlan"
        INDEX         { rcTlsUniIpServiceStatsAddr,rcTlsUniIpServiceStatsCustIpVlan}
        ::= { rcTlsUniIpServiceStatsTable 1 }
 
RcTlsUniIpServiceStatsEntry ::=
        SEQUENCE { 
 		rcTlsUniIpServiceStatsAddr          			IpAddress,	
                rcTlsUniIpServiceStatsCustIpVlan       			INTEGER, 
                rcTlsUniIpServiceStatsPremRxOctets	       		Counter64,	
       		rcTlsUniIpServiceStatsPremRxDroppedOctets   		Counter64,
		rcTlsUniIpServiceStatsGoldRxOctets			Counter64,	
		rcTlsUniIpServiceStatsGoldRxDroppedOctets   		Counter64,
		rcTlsUniIpServiceStatsSilverRxOctets	      		Counter64,	
		rcTlsUniIpServiceStatsSilverRxDroppedOctets 		Counter64,
		rcTlsUniIpServiceStatsStndRxOctets	      		Counter64,	
		rcTlsUniIpServiceStatsStndRxDroppedOctets   		Counter64,
		rcTlsUniIpServiceStatsPremTxOctets	      		Counter64,	
		rcTlsUniIpServiceStatsGoldTxOctets	      		Counter64,	
		rcTlsUniIpServiceStatsSilverTxOctets	      		Counter64,
		rcTlsUniIpServiceStatsStndTxOctets	      		Counter64,	
		rcTlsUniIpServiceStatsPremTxMcastOctets     		Counter64,	
		rcTlsUniIpServiceStatsGoldTxMcastOctets     		Counter64,	
		rcTlsUniIpServiceStatsSilverTxMcastOctets   		Counter64,
		rcTlsUniIpServiceStatsStndTxMcastOctets     		Counter64,
                rcTlsUniIpServiceStatsClear            			TruthValue,
		rcTlsUniIpServiceStatsPremCongestionDropOctets 		Counter64,
		rcTlsUniIpServiceStatsGoldCongestionDropOctets 		Counter64,
		rcTlsUniIpServiceStatsSilverCongestionDropOctets 	Counter64,	
		rcTlsUniIpServiceStatsStndCongestionDropOctets 		Counter64,	
		rcTlsUniIpServiceStatsPremCirDroppedOctets   		Counter64,
		rcTlsUniIpServiceStatsPremPirDroppedOctets   		Counter64,
		rcTlsUniIpServiceStatsGoldCirDroppedOctets   		Counter64,
		rcTlsUniIpServiceStatsGoldPirDroppedOctets   		Counter64,
		rcTlsUniIpServiceStatsSilverCirDroppedOctets   		Counter64,
		rcTlsUniIpServiceStatsSilverPirDroppedOctets   		Counter64,
		rcTlsUniIpServiceStatsStndCirDroppedOctets   		Counter64,
		rcTlsUniIpServiceStatsStndPirDroppedOctets   		Counter64,
		rcTlsUniIpServiceStatsName                   		DisplayString,
		rcTlsUniIpServiceStatsPremTxDroppedOctets	       	Counter64,	
		rcTlsUniIpServiceStatsGoldTxDroppedOctets	       	Counter64,	
		rcTlsUniIpServiceStatsSilverTxDroppedOctets	       	Counter64,
		rcTlsUniIpServiceStatsStndTxDroppedOctets	       	Counter64,	
		rcTlsUniIpServiceStatsPremTxCongestionDropOctets   	Counter64,
		rcTlsUniIpServiceStatsGoldTxCongestionDropOctets   	Counter64,
		rcTlsUniIpServiceStatsSilverTxCongestionDropOctets 	Counter64,	
		rcTlsUniIpServiceStatsStndTxCongestionDropOctets   	Counter64,	
		rcTlsUniIpServiceStatsPremTxCirDroppedOctets       	Counter64,
		rcTlsUniIpServiceStatsPremTxPirDroppedOctets       	Counter64,
		rcTlsUniIpServiceStatsGoldTxCirDroppedOctets       	Counter64,
		rcTlsUniIpServiceStatsGoldTxPirDroppedOctets       	Counter64,
		rcTlsUniIpServiceStatsSilverTxCirDroppedOctets     	Counter64,
		rcTlsUniIpServiceStatsSilverTxPirDroppedOctets     	Counter64,
		rcTlsUniIpServiceStatsStndTxCirDroppedOctets       	Counter64,
		rcTlsUniIpServiceStatsStndTxPirDroppedOctets       	Counter64,
		rcTlsUniIpServiceStatsRxMcastTotalOctets           	Counter64,
		rcTlsUniIpServiceStatsTxMcastTotalOctets           	Counter64,
		rcTlsUniIpServiceStatsPremRxMcastDroppedOctets          Counter64,
		rcTlsUniIpServiceStatsGoldRxMcastDroppedOctets          Counter64,
		rcTlsUniIpServiceStatsSilverRxMcastDroppedOctets        Counter64,
		rcTlsUniIpServiceStatsStndRxMcastDroppedOctets          Counter64
      }

rcTlsUniIpServiceStatsAddr OBJECT-TYPE
        SYNTAX        IpAddress
        MAX-ACCESS    not-accessible
        STATUS        current
        DESCRIPTION   "Tls Uni Ip Service Uni Address"
        ::= { rcTlsUniIpServiceStatsEntry 1}

rcTlsUniIpServiceStatsCustIpVlan OBJECT-TYPE
        SYNTAX        INTEGER (1..4096)
        MAX-ACCESS    not-accessible
        STATUS        current
        DESCRIPTION   "Customer IP Vlan for UNI IP Vlan mapping"
        ::= { rcTlsUniIpServiceStatsEntry 2 }
 
rcTlsUniIpServiceStatsPremRxOctets	OBJECT-TYPE
        SYNTAX        Counter64
        MAX-ACCESS    read-only
        STATUS        current
        DESCRIPTION  "Number of Premium ServiceStats Octets received from This Customer Ip Service."
        ::= { rcTlsUniIpServiceStatsEntry 3 } 

rcTlsUniIpServiceStatsPremRxDroppedOctets	OBJECT-TYPE
        SYNTAX        Counter64
        MAX-ACCESS    read-only
        STATUS        current
        DESCRIPTION  "Number of Premium ServiceStats Octets dropped from This Customer Ip Service."
        ::= { rcTlsUniIpServiceStatsEntry 4 } 
       
rcTlsUniIpServiceStatsGoldRxOctets	OBJECT-TYPE
        SYNTAX        Counter64
        MAX-ACCESS    read-only
        STATUS        current
        DESCRIPTION  "Number of Gold ServiceStats Octets received from This Customer Ip Service."
        ::= { rcTlsUniIpServiceStatsEntry 5 } 

rcTlsUniIpServiceStatsGoldRxDroppedOctets	OBJECT-TYPE
        SYNTAX        Counter64
        MAX-ACCESS    read-only
        STATUS        current
        DESCRIPTION  "Number of Gold ServiceStats Octets dropped from This Customer Ip Service."
        ::= { rcTlsUniIpServiceStatsEntry 6 } 
       
rcTlsUniIpServiceStatsSilverRxOctets	OBJECT-TYPE
        SYNTAX        Counter64
        MAX-ACCESS    read-only
        STATUS        current
        DESCRIPTION  "Number of Silver ServiceStats Octets received from This Customer Ip Service."
        ::= { rcTlsUniIpServiceStatsEntry 7 } 

rcTlsUniIpServiceStatsSilverRxDroppedOctets	OBJECT-TYPE
        SYNTAX        Counter64
        MAX-ACCESS    read-only
        STATUS        current
        DESCRIPTION  "Number of Silver ServiceStats Octets dropped from This Customer Ip Service."
        ::= { rcTlsUniIpServiceStatsEntry 8 } 
       
rcTlsUniIpServiceStatsStndRxOctets	OBJECT-TYPE
        SYNTAX        Counter64
        MAX-ACCESS    read-only
        STATUS        current
        DESCRIPTION  "Number of Standard (Best Effort) ServiceStats Octets received from This Customer Ip Service."
        ::= { rcTlsUniIpServiceStatsEntry 9 } 

rcTlsUniIpServiceStatsStndRxDroppedOctets	OBJECT-TYPE
        SYNTAX        Counter64
        MAX-ACCESS    read-only
        STATUS        current
        DESCRIPTION  "Number of Standard(BestEffort) ServiceStats Octets dropped from this Customer Ip Service."
        ::= { rcTlsUniIpServiceStatsEntry 10 } 
       
rcTlsUniIpServiceStatsPremTxOctets	OBJECT-TYPE
        SYNTAX        Counter64
        MAX-ACCESS    read-only
        STATUS        current
        DESCRIPTION  "Number of Premium ServiceStats Octets sent to his Customer Ip Service."
        ::= { rcTlsUniIpServiceStatsEntry 11 } 

rcTlsUniIpServiceStatsGoldTxOctets	OBJECT-TYPE
        SYNTAX        Counter64
        MAX-ACCESS    read-only
        STATUS        current
        DESCRIPTION  "Number of Gold ServiceStats Octets sent to his Customer Ip Service."
        ::= { rcTlsUniIpServiceStatsEntry 12 } 

rcTlsUniIpServiceStatsSilverTxOctets	OBJECT-TYPE
        SYNTAX        Counter64
        MAX-ACCESS    read-only
        STATUS        current
        DESCRIPTION  "Number of Silver ServiceStats Octets sent to his Customer Ip Service."
        ::= { rcTlsUniIpServiceStatsEntry 13 } 

rcTlsUniIpServiceStatsStndTxOctets	OBJECT-TYPE
        SYNTAX        Counter64
        MAX-ACCESS    read-only
        STATUS        current
        DESCRIPTION  "Number of Standard ServiceStats Octets sent to his Customer Ip Service."
        ::= { rcTlsUniIpServiceStatsEntry 14 } 
		

rcTlsUniIpServiceStatsPremTxMcastOctets	OBJECT-TYPE
        SYNTAX        Counter64
        MAX-ACCESS    read-only
        STATUS        current
        DESCRIPTION  "Number of Premium ServiceStats Multicast sent to his Customer Ip Service."
        ::= { rcTlsUniIpServiceStatsEntry 15 } 

rcTlsUniIpServiceStatsGoldTxMcastOctets	OBJECT-TYPE
        SYNTAX        Counter64
        MAX-ACCESS    read-only
        STATUS        current
        DESCRIPTION  "Number of GoldServiceStats Multicast sent to his Customer Ip Service."
        ::= { rcTlsUniIpServiceStatsEntry 16 } 
		
rcTlsUniIpServiceStatsSilverTxMcastOctets	OBJECT-TYPE
        SYNTAX        Counter64
        MAX-ACCESS    read-only
        STATUS        current
        DESCRIPTION  "Number of SilverServiceStats Multicast sent to his Customer Ip Service."
        ::= { rcTlsUniIpServiceStatsEntry 17 } 

rcTlsUniIpServiceStatsStndTxMcastOctets	OBJECT-TYPE
        SYNTAX        Counter64
        MAX-ACCESS    read-only
        STATUS        current 
        DESCRIPTION  "Number of Premium ServiceStats Multicast sent to his Customer Ip Service."
        ::= { rcTlsUniIpServiceStatsEntry 18     } 

rcTlsUniIpServiceStatsClear      OBJECT-TYPE
        SYNTAX        TruthValue
        MAX-ACCESS    read-write
        STATUS        current
        DESCRIPTION   "Clear statistic."
        ::= { rcTlsUniIpServiceStatsEntry 19 }

rcTlsUniIpServiceStatsPremCongestionDropOctets	OBJECT-TYPE
        SYNTAX        Counter64
        MAX-ACCESS    read-only
        STATUS        current
        DESCRIPTION  "Number of Prem ServiceStats Octets congestion drop"
        ::= { rcTlsUniIpServiceStatsEntry 20 } 
       
rcTlsUniIpServiceStatsGoldCongestionDropOctets	OBJECT-TYPE
        SYNTAX        Counter64
        MAX-ACCESS    read-only
        STATUS        current
        DESCRIPTION  "Number of Gold ServiceStats Octets congestion drop"
        ::= { rcTlsUniIpServiceStatsEntry 21 } 

rcTlsUniIpServiceStatsSilverCongestionDropOctets	OBJECT-TYPE
        SYNTAX        Counter64
        MAX-ACCESS    read-only
        STATUS        current
        DESCRIPTION  "Number of Silver ServiceStats Octets congestion drop"
        ::= { rcTlsUniIpServiceStatsEntry 22 } 

rcTlsUniIpServiceStatsStndCongestionDropOctets	OBJECT-TYPE
        SYNTAX        Counter64
        MAX-ACCESS    read-only
        STATUS        current
        DESCRIPTION  "Number of Standard ServiceStats Octets congestion drop"
        ::= { rcTlsUniIpServiceStatsEntry 23 }

rcTlsUniIpServiceStatsPremCirDroppedOctets	OBJECT-TYPE
        SYNTAX        Counter64
        MAX-ACCESS    read-only
        STATUS        current
        DESCRIPTION  "Number of Prem ServiceStats Octets CIR drop"
        ::= { rcTlsUniIpServiceStatsEntry 24 }

rcTlsUniIpServiceStatsPremPirDroppedOctets	OBJECT-TYPE
        SYNTAX        Counter64
        MAX-ACCESS    read-only
        STATUS        current
        DESCRIPTION  "Number of Prem ServiceStats Octets PIR drop"
        ::= { rcTlsUniIpServiceStatsEntry 25 }
  
rcTlsUniIpServiceStatsGoldCirDroppedOctets	OBJECT-TYPE
        SYNTAX        Counter64
        MAX-ACCESS    read-only
        STATUS        current
        DESCRIPTION  "Number of Gold ServiceStats Octets CIR drop"
        ::= { rcTlsUniIpServiceStatsEntry 26 }

rcTlsUniIpServiceStatsGoldPirDroppedOctets	OBJECT-TYPE
        SYNTAX        Counter64
        MAX-ACCESS    read-only
        STATUS        current
        DESCRIPTION  "Number of Gold ServiceStats Octets PIR drop"
        ::= { rcTlsUniIpServiceStatsEntry 27 }

rcTlsUniIpServiceStatsSilverCirDroppedOctets	OBJECT-TYPE
        SYNTAX        Counter64
        MAX-ACCESS    read-only
        STATUS        current
        DESCRIPTION  "Number of Silver ServiceStats Octets CIR drop"
        ::= { rcTlsUniIpServiceStatsEntry 28 }

rcTlsUniIpServiceStatsSilverPirDroppedOctets	OBJECT-TYPE
        SYNTAX        Counter64
        MAX-ACCESS    read-only
        STATUS        current
        DESCRIPTION  "Number of Silver ServiceStats Octets PIR drop"
        ::= { rcTlsUniIpServiceStatsEntry 29 }

rcTlsUniIpServiceStatsStndCirDroppedOctets	OBJECT-TYPE
        SYNTAX        Counter64
        MAX-ACCESS    read-only
        STATUS        current
        DESCRIPTION  "Number of Standard ServiceStats Octets CIR drop"
        ::= { rcTlsUniIpServiceStatsEntry 30 }  

rcTlsUniIpServiceStatsStndPirDroppedOctets	OBJECT-TYPE
        SYNTAX        Counter64
        MAX-ACCESS    read-only
        STATUS        current
        DESCRIPTION  "Number of Standard ServiceStats Octets PIR drop"
        ::= { rcTlsUniIpServiceStatsEntry 31 } 
 
rcTlsUniIpServiceStatsName OBJECT-TYPE
        SYNTAX        DisplayString (SIZE (0..30)) 
        MAX-ACCESS    read-only
        STATUS        current
        DESCRIPTION   "Name of UNI IP Service Vlan Entry. By default, It is 
		       VLAN-<uni id>-<cust ip vlan>"
        ::= { rcTlsUniIpServiceStatsEntry 32 }

rcTlsUniIpServiceStatsPremTxDroppedOctets	OBJECT-TYPE
        SYNTAX        Counter64
        MAX-ACCESS    read-only
        STATUS        current
        DESCRIPTION  "Tx Number of Premium ServiceStats Octets dropped from This Customer Ip Service."
        ::= { rcTlsUniIpServiceStatsEntry 33 } 

rcTlsUniIpServiceStatsGoldTxDroppedOctets	OBJECT-TYPE
        SYNTAX        Counter64
        MAX-ACCESS    read-only
        STATUS        current
        DESCRIPTION  "Tx Number of Gold ServiceStats Octets dropped from This Customer Ip Service."
        ::= { rcTlsUniIpServiceStatsEntry 34 } 
       
rcTlsUniIpServiceStatsSilverTxDroppedOctets	OBJECT-TYPE
        SYNTAX        Counter64
        MAX-ACCESS    read-only
        STATUS        current
        DESCRIPTION  "Tx Number of Silver ServiceStats Octets dropped from This Customer Ip Service."
        ::= { rcTlsUniIpServiceStatsEntry 35 } 
       
rcTlsUniIpServiceStatsStndTxDroppedOctets	OBJECT-TYPE
        SYNTAX        Counter64
        MAX-ACCESS    read-only
        STATUS        current
        DESCRIPTION  "Tx Number of Standard(BestEffort) ServiceStats Octets dropped from this Customer Ip Service."
        ::= { rcTlsUniIpServiceStatsEntry 36 } 

rcTlsUniIpServiceStatsPremTxCongestionDropOctets	OBJECT-TYPE
        SYNTAX        Counter64
        MAX-ACCESS    read-only
        STATUS        current
        DESCRIPTION  "Tx Number of Prem ServiceStats Octets congestion drop"
        ::= { rcTlsUniIpServiceStatsEntry 37 } 
       
rcTlsUniIpServiceStatsGoldTxCongestionDropOctets	OBJECT-TYPE
        SYNTAX        Counter64
        MAX-ACCESS    read-only
        STATUS        current
        DESCRIPTION  "Tx Number of Gold ServiceStats Octets congestion drop"
        ::= { rcTlsUniIpServiceStatsEntry 38 } 

rcTlsUniIpServiceStatsSilverTxCongestionDropOctets	OBJECT-TYPE
        SYNTAX        Counter64
        MAX-ACCESS    read-only
        STATUS        current
        DESCRIPTION  "Tx Number of Silver ServiceStats Octets congestion drop"
        ::= { rcTlsUniIpServiceStatsEntry 39 } 

rcTlsUniIpServiceStatsStndTxCongestionDropOctets	OBJECT-TYPE
        SYNTAX        Counter64
        MAX-ACCESS    read-only
        STATUS        current
        DESCRIPTION  "Tx Number of Standard ServiceStats Octets congestion drop"
        ::= { rcTlsUniIpServiceStatsEntry 40 }

rcTlsUniIpServiceStatsPremTxCirDroppedOctets	OBJECT-TYPE
        SYNTAX        Counter64
        MAX-ACCESS    read-only
        STATUS        current
        DESCRIPTION  "Tx Number of Prem ServiceStats Octets CIR drop"
        ::= { rcTlsUniIpServiceStatsEntry 41 }

rcTlsUniIpServiceStatsPremTxPirDroppedOctets	OBJECT-TYPE
        SYNTAX        Counter64
        MAX-ACCESS    read-only
        STATUS        current
        DESCRIPTION  "Tx Number of Prem ServiceStats Octets PIR drop"
        ::= { rcTlsUniIpServiceStatsEntry 42 }
  
rcTlsUniIpServiceStatsGoldTxCirDroppedOctets	OBJECT-TYPE
        SYNTAX        Counter64
        MAX-ACCESS    read-only
        STATUS        current
        DESCRIPTION  "Tx Number of Gold ServiceStats Octets CIR drop"
        ::= { rcTlsUniIpServiceStatsEntry 43 }

rcTlsUniIpServiceStatsGoldTxPirDroppedOctets	OBJECT-TYPE
        SYNTAX        Counter64
        MAX-ACCESS    read-only
        STATUS        current
        DESCRIPTION  "Tx Number of Gold ServiceStats Octets PIR drop"
        ::= { rcTlsUniIpServiceStatsEntry 44 }

rcTlsUniIpServiceStatsSilverTxCirDroppedOctets	OBJECT-TYPE
        SYNTAX        Counter64
        MAX-ACCESS    read-only
        STATUS        current
        DESCRIPTION  "Tx Number of Silver ServiceStats Octets CIR drop"
        ::= { rcTlsUniIpServiceStatsEntry 45 }

rcTlsUniIpServiceStatsSilverTxPirDroppedOctets	OBJECT-TYPE
        SYNTAX        Counter64
        MAX-ACCESS    read-only
        STATUS        current
        DESCRIPTION  "Tx Number of Silver ServiceStats Octets PIR drop"
        ::= { rcTlsUniIpServiceStatsEntry 46 }

rcTlsUniIpServiceStatsStndTxCirDroppedOctets	OBJECT-TYPE
        SYNTAX        Counter64
        MAX-ACCESS    read-only
        STATUS        current
        DESCRIPTION  "Tx Number of Standard ServiceStats Octets CIR drop"
        ::= { rcTlsUniIpServiceStatsEntry 47 }  

rcTlsUniIpServiceStatsStndTxPirDroppedOctets	OBJECT-TYPE
        SYNTAX        Counter64
        MAX-ACCESS    read-only
        STATUS        current
        DESCRIPTION  "TX Number of Standard ServiceStats Octets PIR drop"
        ::= { rcTlsUniIpServiceStatsEntry 48 }
 
rcTlsUniIpServiceStatsRxMcastTotalOctets	OBJECT-TYPE
        SYNTAX        Counter64
        MAX-ACCESS    read-only
        STATUS        current
        DESCRIPTION  "Rx Total Number of Mcast Octets"
        ::= { rcTlsUniIpServiceStatsEntry 49 }
 
rcTlsUniIpServiceStatsTxMcastTotalOctets	OBJECT-TYPE
        SYNTAX        Counter64
        MAX-ACCESS    read-only
        STATUS        current
        DESCRIPTION  "TX total Number of Mcast Octets"
        ::= { rcTlsUniIpServiceStatsEntry 50 } 

rcTlsUniIpServiceStatsPremRxMcastDroppedOctets	OBJECT-TYPE
        SYNTAX        Counter64
        MAX-ACCESS    read-only
        STATUS        current
        DESCRIPTION  "Number of Premium Service Rx Mcast Octets dropped from 
		      This Customer Ip Service."
        ::= { rcTlsUniIpServiceStatsEntry 51 } 

rcTlsUniIpServiceStatsGoldRxMcastDroppedOctets	OBJECT-TYPE
        SYNTAX        Counter64
        MAX-ACCESS    read-only
        STATUS        current
        DESCRIPTION  "Number of Gold Service Rx Mcast Octets dropped from 
		      This Customer Ip Service."
        ::= { rcTlsUniIpServiceStatsEntry 52 } 

rcTlsUniIpServiceStatsSilverRxMcastDroppedOctets	OBJECT-TYPE
        SYNTAX        Counter64
        MAX-ACCESS    read-only
        STATUS        current
        DESCRIPTION  "Number of Silver Service Rx Mcast Octets dropped from 
		      This Customer Ip Service."
        ::= { rcTlsUniIpServiceStatsEntry 53 } 
                            
rcTlsUniIpServiceStatsStndRxMcastDroppedOctets	OBJECT-TYPE
        SYNTAX        Counter64
        MAX-ACCESS    read-only
        STATUS        current
        DESCRIPTION  "Number of Standard Service Rx Mcast Octets dropped from 
		      This Customer Ip Service."
        ::= { rcTlsUniIpServiceStatsEntry 54 } 
     
-- Rate Policer Profile Table 

-- The default values represent a best effort class of service, no CIR
-- and a minimal (64Kbps) PIR

-- The sum of the 3 CIRs must be less than or equal to the PIR

rcCosProfileTable OBJECT-TYPE
        SYNTAX        SEQUENCE OF RcCosProfileEntry
        MAX-ACCESS    not-accessible
        STATUS        current
        DESCRIPTION   "A list of CoS Profiles. A Rate Policer is used
                       to configure the rate policers (CIR & PIR) for
                       up to four classes of service for a UNI end-point."
        ::= { rcCos 1 }
 
rcCosProfileEntry OBJECT-TYPE
        SYNTAX        RcCosProfileEntry
        MAX-ACCESS    not-accessible
        STATUS        current
        DESCRIPTION   "A CoS Profile Table Entry."
        INDEX         { rcCosProfileTblIndex  }
        ::= { rcCosProfileTable 1 }
 
RcCosProfileEntry ::=
        SEQUENCE {
                rcCosProfileTblIndex              INTEGER,
                rcCosProfileName                  DisplayString,
                rcCosProfilePremiumCirUnits       INTEGER,
                rcCosProfilePremiumCir            INTEGER,
                rcCosProfileGoldCirUnits          INTEGER,
                rcCosProfileGoldCir               INTEGER,
                rcCosProfileSilverCirUnits        INTEGER,
                rcCosProfileSilverCir             INTEGER,
                rcCosProfileStandardPirUnits      INTEGER,
                rcCosProfileStandardPir           INTEGER,
                rcCosProfileRowStatus             RowStatus,
		rcCosProfilePremiumPirUsage       EnableValue,
		rcCosProfileGoldPirUsage          EnableValue,
	  	rcCosProfileSilverPirUsage        EnableValue,
		rcCosProfilePremiumTBMaxSize      INTEGER,
		rcCosProfilePremiumTBMaxCtl 	  INTEGER,
		rcCosProfileGoldTBMaxSize         INTEGER,
		rcCosProfileGoldTBMaxCtl          INTEGER,
		rcCosProfileSilverTBMaxSize       INTEGER,
		rcCosProfileSilverTBMaxCtl        INTEGER,
		rcCosProfileStandardTBMaxSize     INTEGER,
		rcCosProfileStandardTBMaxCtl      INTEGER,
		rcCosProfileMcastLimitUnits	  INTEGER,
		rcCosProfileMcastLimitRate	  INTEGER,	
		rcCosProfileMcastLimitUsage	  EnableValue,
		rcCosProfileMcastLimitTBMaxCtl    INTEGER,
		rcCosProfileMcastLimitTBMaxSize   INTEGER  
       }

rcCosProfileTblIndex OBJECT-TYPE
        SYNTAX        INTEGER (1..2000)
        MAX-ACCESS    read-only
        STATUS        current
        DESCRIPTION   "The value of this object uniquely identifies an
                       instance of a rcCosProfileEntry."
        ::= { rcCosProfileEntry 1 }
 
rcCosProfileName OBJECT-TYPE
        SYNTAX        DisplayString (SIZE (1..20)) 
        MAX-ACCESS    read-write
        STATUS        current
        DESCRIPTION   "A plain text name describing this rcCosProfile."
        ::= { rcCosProfileEntry 2 }
 
rcCosProfilePremiumCirUnits OBJECT-TYPE
        SYNTAX        INTEGER { 
                          unitsOf64Kbps (1), 
                          unitsOf1Mbps (2) 
                       }
        MAX-ACCESS    read-write
        STATUS        current
        DESCRIPTION   "Indicates whether the rcCosProfilePremiumCir value
                       is measured in units of 64Kbps or 1Mbps."  
        DEFVAL { 1 }
        ::= { rcCosProfileEntry 3 }
 
rcCosProfilePremiumCir OBJECT-TYPE
        SYNTAX        INTEGER (0..1000)
        MAX-ACCESS    read-write
        STATUS        current
        DESCRIPTION   "The value of this object indicates the CIR rate
                       for traffic that has been classified as Premium,
                       a NNSC classification that is analogous to DSCP
                       EF, ToS Critical, or 802.1p user priority 6. This
                       attribute reflects a guaranteed data rate. Traffic
                       in excess of this data rate is discarded.
                       If rcCosProfilePremiumCirUnits is set to 1, this
                       value may not exceed 15."
        DEFVAL { 0 }
        ::= { rcCosProfileEntry 4 }
 
rcCosProfileGoldCirUnits OBJECT-TYPE
        SYNTAX        INTEGER { 
                          unitsOf64Kbps (1), 
                          unitsOf1Mbps (2) 
                       }
        MAX-ACCESS    read-write
        STATUS        current
        DESCRIPTION   "Indicates whether the rcCosProfileGoldCir value
                       is measured in units of 64Kbps or 1Mbps."  
        DEFVAL { 1 }
        ::= { rcCosProfileEntry 5 }
 
rcCosProfileGoldCir OBJECT-TYPE
        SYNTAX        INTEGER (0..1000)
        MAX-ACCESS    read-write
        STATUS        current
        DESCRIPTION   "The value of this object indicates the CIR rate
                       for traffic that has been classified as Gold,
                       a NNSC classification that is analogous to DSCP
                       AF3, ToS Flash, or 802.1p user priority 4. This
                       attribute reflects a guaranteed data rate. Traffic
                       in excess of this data rate is marked yellow.
                       If rcCosProfileGoldCirUnits is set to 1, this
                       value may not exceed 15."
        DEFVAL { 0 }
        ::= { rcCosProfileEntry 6 }
 
rcCosProfileSilverCirUnits OBJECT-TYPE
        SYNTAX        INTEGER { 
                          unitsOf64Kbps (1), 
                         unitsOf1Mbps (2) 
                       }
        MAX-ACCESS    read-write
        STATUS        current
        DESCRIPTION   "Indicates whether the rcCosProfileSilverCir value
                       is measured in units of 64Kbps or 1Mbps."  
        DEFVAL { 1 }
        ::= { rcCosProfileEntry 7 }
 
rcCosProfileSilverCir OBJECT-TYPE
        SYNTAX        INTEGER (0..1000)
        MAX-ACCESS    read-write
        STATUS        current
        DESCRIPTION   "The value of this object indicates the CIR rate
                       for traffic that has been classified as Silver,
                       a NNSC classification that is analogous to DSCP
                       AF2, ToS Immediate, or 802.1p user priority 3. This
                       attribute reflects a guaranteed data rate. Traffic
                       in excess of this data rate is marked yellow.
                       If rcCosProfileSilverCirUnits is set to 1, this
                       value may not exceed 15."
        DEFVAL { 0 }
        ::= { rcCosProfileEntry 8 }
 
rcCosProfileStandardPirUnits OBJECT-TYPE
        SYNTAX        INTEGER { 
                          unitsOf64Kbps (1), 
                          unitsOf1Mbps (2) 
                       }
        MAX-ACCESS    read-write
        STATUS        current
        DESCRIPTION   "Indicates whether the rcCosProfileStandardPir value
                       is measured in units of 64Kbps or 1Mbps."  
        DEFVAL { 1 }
        ::= { rcCosProfileEntry 9 }
 
rcCosProfileStandardPir OBJECT-TYPE
        SYNTAX        INTEGER (1..1000)
        MAX-ACCESS    read-write
        STATUS        current
        DESCRIPTION   "The value of this object indicates the PIR rate
                       for traffic that has been classified as Standard
                       traffic. This attribute reflects a best effort
                       peak data rate. If rcCosProfileStandardPirUnits
                       is set to 1, this value may not exceed 4.
                       Traffic that has been colored yellow as a result
                       of exceeding a Gold or Silver CIR and exceeds this
                       data rate is discarded. Any traffic classified as
                       Standard, a NNSC classification that is analogous
                       to DSCP Standard, ToS Routine, or 802.1p user
                       priority 0, that exceeds this data rate will be
                       discarded. Traffic that has been classified as
                       Premium, and traffic hat has been classified as
                       Gold or Silver that has not exceeded their CIR,
                       will not be discarded if the data rate exceeds
                       this PIR. That traffic may, however, force this
                       PIR to a value less than or equal than zero."
        DEFVAL { 15 }
        ::= { rcCosProfileEntry 10 }

rcCosProfileRowStatus OBJECT-TYPE
        SYNTAX        RowStatus
        MAX-ACCESS    read-write
        STATUS        current
        DESCRIPTION   "Uses for controlling the creation and
                       deletion of this row."
        ::= { rcCosProfileEntry 11 }


rcCosProfilePremiumPirUsage OBJECT-TYPE
        SYNTAX        EnableValue
        MAX-ACCESS    read-write
        STATUS        current
        DESCRIPTION   "Administratively enable or disable Premium PIR usage."
	DEFVAL        { enable }
        ::= { rcCosProfileEntry 12 }

rcCosProfileGoldPirUsage OBJECT-TYPE
        SYNTAX        EnableValue
        MAX-ACCESS    read-write
        STATUS        current
        DESCRIPTION   "Administratively enable or disable Gold PIR usage."
	DEFVAL        { enable }
        ::= { rcCosProfileEntry 13 }

rcCosProfileSilverPirUsage OBJECT-TYPE
        SYNTAX        EnableValue
        MAX-ACCESS    read-write
        STATUS        current
        DESCRIPTION   "Administratively enable or disable Silver PIR usage."
	DEFVAL        { enable }
        ::= { rcCosProfileEntry 14 }

rcCosProfilePremiumTBMaxSize   OBJECT-TYPE
        SYNTAX        INTEGER (1..8000) 
        MAX-ACCESS    read-write
        STATUS        current
        DESCRIPTION   "Specifies the Max. Token Bucket size limit for 
		       the Premium bucket, in kilobytes"  
        DEFVAL { 1 }
        ::= { rcCosProfileEntry 15 }

rcCosProfilePremiumTBMaxCtl  OBJECT-TYPE
        SYNTAX        INTEGER { 
                          automatic (1), 
                          manual (2) 
                       }
        MAX-ACCESS    read-write
        STATUS        current
        DESCRIPTION   "Specifies whether the Max. Token Bucket size attribute 
		       rcCosProfilePremiumTBMaxSize is being used to control 
		       the Premium bucket or not. automatic -- does not 
		       use it. manual -- uses it"  
        DEFVAL { automatic }
	::= { rcCosProfileEntry 16 }

rcCosProfileGoldTBMaxSize  OBJECT-TYPE
        SYNTAX        INTEGER (1..8000) 
        MAX-ACCESS    read-write
        STATUS        current
        DESCRIPTION   "Specifies the Max. Token Bucket size limit for 
		       the Gold bucket, in kilobytes"  
        DEFVAL { 1 }
        ::= { rcCosProfileEntry 17 }

rcCosProfileGoldTBMaxCtl  OBJECT-TYPE
        SYNTAX        INTEGER { 
                          automatic (1), 
                          manual (2) 
                       }
        MAX-ACCESS    read-write
        STATUS        current
        DESCRIPTION   "Specifies whether the Max. Token Bucket size attribute 
		       rcCosProfileGoldTBMaxSize is being used to control 
		       the Gold bucket or not. automatic -- does not 
		       use it. manual -- uses it"  
        DEFVAL { automatic }
	::= { rcCosProfileEntry 18 }

rcCosProfileSilverTBMaxSize  OBJECT-TYPE
        SYNTAX        INTEGER (1..8000) 
        MAX-ACCESS    read-write
        STATUS        current
        DESCRIPTION   "Specifies the Max. Token Bucket size limit for 
		       the Silver bucket, in kilobytes"  
        DEFVAL { 1 }
        ::= { rcCosProfileEntry 19 }

rcCosProfileSilverTBMaxCtl  OBJECT-TYPE
        SYNTAX        INTEGER { 
                          automatic (1), 
                          manual (2) 
                       }
        MAX-ACCESS    read-write
        STATUS        current
        DESCRIPTION   "Specifies whether the Max. Token Bucket size attribute 
		       rcCosProfileSilverTBMaxSize is being used to control 
		       the Silver bucket or not. automatic -- does not 
		       use it. manual -- uses it"  
        DEFVAL { automatic }
	::= { rcCosProfileEntry 20 }

rcCosProfileStandardTBMaxSize  OBJECT-TYPE
        SYNTAX        INTEGER (1..8000) 
        MAX-ACCESS    read-write
        STATUS        current
        DESCRIPTION   "Specifies the Max. Token Bucket size limit for 
		       the Standard bucket, in kilobytes"  
        DEFVAL { 1 }
        ::= { rcCosProfileEntry 21 }

rcCosProfileStandardTBMaxCtl  OBJECT-TYPE
        SYNTAX        INTEGER { 
                          automatic (1), 
                          manual (2) 
                       }
        MAX-ACCESS    read-write
        STATUS        current
        DESCRIPTION   "Specifies whether the Max. Token Bucket size attribute 
		       rcCosProfileStandardTBMaxSize is being used to control 
		       the Standard bucket or not. automatic -- does not 
		       use it. manual -- uses it"  
        DEFVAL { automatic }
	::= { rcCosProfileEntry 22 }
rcCosProfileMcastLimitUnits OBJECT-TYPE
        SYNTAX        INTEGER { 
                          unitsOf64Kbps (1), 
                          unitsOf1Mbps (2) 
                       }
        MAX-ACCESS    read-create
        STATUS        current
        DESCRIPTION   "Indicates whether the rcCosProfileMcastLimitRate
		       value is measured in units of 64Kbps or 1Mbps."  
        DEFVAL { unitsOf64Kbps }
        ::= { rcCosProfileEntry 24 }

rcCosProfileMcastLimitRate OBJECT-TYPE
        SYNTAX        INTEGER (0..1000)
        MAX-ACCESS    read-create
        STATUS        current
        DESCRIPTION   "The value of this object indicates the rate
                       for traffic that has been classified as Mcast.
	               This attribute reflects a maximum data rate.
		       Traffic in excess of this data rate is discarded.
                       If rcCosProfileMcastLimitUnits is set to 1, this
                       value may not exceed 15."
        DEFVAL { 15 }
        ::= { rcCosProfileEntry 25 }

rcCosProfileMcastLimitUsage OBJECT-TYPE
        SYNTAX        EnableValue
        MAX-ACCESS    read-create
        STATUS        current
        DESCRIPTION   "Administratively enable or disable Macast 
		       rate usage."
	DEFVAL { disable }
        ::= { rcCosProfileEntry 26 }

rcCosProfileMcastLimitTBMaxCtl  OBJECT-TYPE
        SYNTAX        INTEGER { 
                          automatic (1), 
                          manual (2) 
                       }
        MAX-ACCESS    read-create
        STATUS        current
        DESCRIPTION   "Specifies whether the Max. Token Bucket size
		       attribute rcCosProfileMcastLimitTBMaxSize can 
		       be modified by the user or is set internally.
		       automatic -- set internally, manual -- modifiable"  
        DEFVAL { automatic }
	::= { rcCosProfileEntry 27 }

rcCosProfileMcastLimitTBMaxSize  OBJECT-TYPE
        SYNTAX        INTEGER (1..8000) 
        MAX-ACCESS    read-create
        STATUS        current
        DESCRIPTION   "Specifies the Max. Token Bucket size limit for 
		       the Mcast bucket, in kilobytes"  
        DEFVAL { 1 }
        ::= { rcCosProfileEntry 28 }

-- rcCosProfileTableSize

rcCosProfileTableSize OBJECT-TYPE
        SYNTAX        Integer32
        MAX-ACCESS    read-only
        STATUS        current
        DESCRIPTION   "Used to indicate the number of entries in the
                       rcCosProfileTable"
        ::= { rcCos 2 }

-- BAN RING Table 

rcBanRingTable OBJECT-TYPE
        SYNTAX        SEQUENCE OF RcBanRingEntry
        MAX-ACCESS    not-accessible
        STATUS        current
        DESCRIPTION   ""
        ::= { rcBanRing 1 }
 
rcBanRingEntry OBJECT-TYPE
        SYNTAX        RcBanRingEntry
        MAX-ACCESS    not-accessible
        STATUS        current
        DESCRIPTION   "BAN ring table entry."
        INDEX         { rcBanRingId }
        ::= { rcBanRingTable 1 }
 
RcBanRingEntry ::=
        SEQUENCE {
                rcBanRingId                    INTEGER,
                rcBanRingPrimaryPort           InterfaceIndex,
                rcBanRingSecondaryPort         InterfaceIndex,
                rcBanRingAdminState            EnableValue,
                rcBanRingTxTimer               Integer32,
                rcBanRingOperState             INTEGER,
                rcBanRingName                  DisplayString,
                rcBanRingDiscoverInterval      INTEGER,
                rcBanRingRowStatus             RowStatus,
                rcBanRingNumVlanIds            Integer32,
                rcBanRingVlanIds               IdList,
		rcBanRingRrpHello              EnableValue,
                rcBanRingRrpHelloInterval      INTEGER,
		rcBanRingClearRrpStats         TruthValue,
		rcBanRingClearRdpStats         TruthValue,
		rcBanRingNumOfUni              Integer32
       }

rcBanRingId OBJECT-TYPE
        SYNTAX        INTEGER (1..254)
        MAX-ACCESS    read-only
        STATUS        current
        DESCRIPTION   "BAN Ring ID."
        ::= { rcBanRingEntry 1 }
 
rcBanRingPrimaryPort OBJECT-TYPE
        SYNTAX        InterfaceIndex
        MAX-ACCESS    read-write
        STATUS        current
        DESCRIPTION   "BAN Ring primaray port number."
        ::= { rcBanRingEntry 2 }
 
rcBanRingSecondaryPort OBJECT-TYPE
        SYNTAX        InterfaceIndex
        MAX-ACCESS    read-write
        STATUS        current
        DESCRIPTION   "BAN Ring secondary port number."
        ::= { rcBanRingEntry 3 }
 
rcBanRingAdminState OBJECT-TYPE
        SYNTAX        EnableValue
        MAX-ACCESS    read-write
        STATUS        current
        DESCRIPTION   "Administratively enable or disable a BAN Ring."
	DEFVAL        { disable }
        ::= { rcBanRingEntry 4 }

rcBanRingTxTimer OBJECT-TYPE
        SYNTAX        Integer32
        MAX-ACCESS    read-write
        STATUS        current
        DESCRIPTION   "BAN Ring TX timer value."
        ::= { rcBanRingEntry 5 }
 
rcBanRingOperState OBJECT-TYPE
        SYNTAX        INTEGER { 
			  down(0),
                          normal(1), 
                          cut(2), 
                          recover(3) 
                       }
        MAX-ACCESS    read-only
        STATUS        current
        DESCRIPTION   "BAN Ring operation status."
        ::= { rcBanRingEntry 6 }

rcBanRingName OBJECT-TYPE
        SYNTAX        DisplayString (SIZE (0..32)) 
        MAX-ACCESS    read-write
        STATUS        current
        DESCRIPTION   "Modification of this field is allowed only
                       when the admin state is disabled."
        ::= { rcBanRingEntry 7 }

rcBanRingDiscoverInterval OBJECT-TYPE
        SYNTAX          INTEGER (1..255)
        UNITS           "seconds"
        MAX-ACCESS      read-write
        STATUS          current
        DESCRIPTION     "The time interval between discovery messages that are
                         generated to check for ring module existence."
        DEFVAL          { 30 }
        ::= { rcBanRingEntry 8 }

rcBanRingRowStatus OBJECT-TYPE
        SYNTAX        RowStatus
        MAX-ACCESS    read-write
        STATUS        current
        DESCRIPTION   "Uses for controlling the creation and
                       deletion of this row."
        ::= { rcBanRingEntry 9 }

rcBanRingNumVlanIds OBJECT-TYPE
        SYNTAX        	Integer32
        MAX-ACCESS      read-only
        STATUS        	current
        DESCRIPTION   	"Used to indicate the number of VLAN IDs that
                      	are stored in the rcBanRingVlanIds variable."
        ::= { rcBanRingEntry 10 }

rcBanRingVlanIds OBJECT-TYPE
        SYNTAX        	IdList (SIZE (4096))
        MAX-ACCESS      read-write
        STATUS        	current
        DESCRIPTION   	"An array used to identify which VLANs this Ring 
                      	is associated with.  Each VLAN ID is stored as a 
		      	two octet value. The first octet in the pair holds
                      	bits 15-8 of the VLAN ID, while the second octet
                      	holds bits 7-0 of the VLAN ID."
        ::= { rcBanRingEntry 11 }

rcBanRingRrpHello OBJECT-TYPE
        SYNTAX        EnableValue
        MAX-ACCESS    read-write
        STATUS        current
        DESCRIPTION   "RRP hello enable or disable a BAN Ring."
	DEFVAL        { disable }
        ::= { rcBanRingEntry 12 }

rcBanRingRrpHelloInterval OBJECT-TYPE
        SYNTAX          INTEGER (1000..60000)
        UNITS           "milliseconds"
        MAX-ACCESS      read-write
        STATUS          current
        DESCRIPTION     "The time interval between hello messages that are
                         generated to the ESU."
        DEFVAL          { 1000 }
        ::= { rcBanRingEntry 13 }

rcBanRingClearRrpStats   OBJECT-TYPE
        SYNTAX          TruthValue
        MAX-ACCESS      read-write
        STATUS          current
        DESCRIPTION     "To clear the RRP sending/receiving and missing 
			 hello message counter"
        DEFVAL          { false }
        ::= { rcBanRingEntry 14 }

rcBanRingClearRdpStats   OBJECT-TYPE
        SYNTAX          TruthValue
        MAX-ACCESS      read-write
        STATUS          current
        DESCRIPTION     "To clear the RDP sending/receiving 
			 message counter"
        DEFVAL          { false }
        ::= { rcBanRingEntry 15 }

rcBanRingNumOfUni OBJECT-TYPE
        SYNTAX        	Integer32
        MAX-ACCESS      read-only
        STATUS        	current
        DESCRIPTION   	"Used to indicate the number of UNIs this ring
                      	is assigned to"
        ::= { rcBanRingEntry 16 }

-- RBS TOPOLOGY Table 

rcBanRingTopoTable OBJECT-TYPE

        SYNTAX        SEQUENCE OF RcBanRingTopoEntry
        MAX-ACCESS    not-accessible
        STATUS        current
        DESCRIPTION   ""
        ::= { rcBanRing 2 }
 
rcBanRingTopoEntry OBJECT-TYPE
        SYNTAX        RcBanRingTopoEntry
        MAX-ACCESS    not-accessible
        STATUS        current
        DESCRIPTION   "BAN ring topology entry."
        INDEX         { rcBanRingTopoRingId,rcBanRingTopoRbsId }
        ::= { rcBanRingTopoTable 1 }
 
RcBanRingTopoEntry ::=
        SEQUENCE {
                rcBanRingTopoRingId                INTEGER,
                rcBanRingTopoRbsId                 INTEGER,
                rcBanRingTopoRbsMac                MacAddress,
                rcBanRingTopoRbsIp                 IpAddress,
                rcBanRingTopoRbsState              INTEGER,
                rcBanRingTopoRbsPortMask           Integer32,
                rcBanRingTopoRbsPortState          Integer32,
		rcBanRingTopoRbsPosition           Integer32,
		rcBanRingTopoRingBreakType         INTEGER,
		rcBanRingTopoRingName              DisplayString
       }

rcBanRingTopoRingId OBJECT-TYPE
        SYNTAX        INTEGER (1..255)
        MAX-ACCESS    read-only
        STATUS        current
        DESCRIPTION   "BAN Ring ID."
        ::= { rcBanRingTopoEntry 1 }
 
rcBanRingTopoRbsId OBJECT-TYPE
        SYNTAX        INTEGER (1..24)
        MAX-ACCESS    read-only
        STATUS        current

        DESCRIPTION   "BAN Ring RBS ID."
        ::= { rcBanRingTopoEntry 2 }
 
rcBanRingTopoRbsMac OBJECT-TYPE
        SYNTAX        MacAddress
        MAX-ACCESS    read-only
        STATUS        current
        DESCRIPTION   "BAN Ring RBS Mac address."
        ::= { rcBanRingTopoEntry 3 }
 
rcBanRingTopoRbsIp OBJECT-TYPE
        SYNTAX        IpAddress
        MAX-ACCESS    read-only
        STATUS        current
        DESCRIPTION   "BAN Ring RBS Ip address."
        ::= { rcBanRingTopoEntry 4 }
 
rcBanRingTopoRbsState OBJECT-TYPE
        SYNTAX        INTEGER { 
                          up(1), 
                          down(2) 
                       }
        MAX-ACCESS    read-only
        STATUS        current
        DESCRIPTION   "BAN Ring RBS operation status."
        ::= { rcBanRingTopoEntry 5 }

rcBanRingTopoRbsPortMask OBJECT-TYPE
        SYNTAX        Integer32
        MAX-ACCESS    read-only
        STATUS        current
        DESCRIPTION   "BAN Ring RBS ports configured mask. Bit Set representation,
		       From less significant bit to the most significant bit.
		       Less significant bit 0 represents to the first port, Less 
		       significant bit 1 represents second port on module. 
		       So on so for ... 
		       Bit clear (0) means port is not configured, 
		       Bit Set(1) means port is configured "
        ::= { rcBanRingTopoEntry 6 }
 
rcBanRingTopoRbsPortState OBJECT-TYPE
        SYNTAX        Integer32
        MAX-ACCESS    read-only
        STATUS        current
        DESCRIPTION   "BAN Ring RBS port state mask. Bit Set representation,
		       From less significant bit to the most significant bit.
		       Less significant bit 0 represents to the first port, Less 
		       significant bit 1 represents second port switch. 
		       So on so for ... 
		       Bit clear (0) means state down, Bit Set(1) means state up"
        ::= { rcBanRingTopoEntry 7 }

rcBanRingTopoRbsPosition  OBJECT-TYPE
        SYNTAX        Integer32
        MAX-ACCESS    read-only
        STATUS        current
        DESCRIPTION   "Postion of the RBS switch in the BAN ring"
        ::= { rcBanRingTopoEntry 8 }       

rcBanRingTopoRingBreakType  OBJECT-TYPE
        SYNTAX        INTEGER {
			normalRing (1),
			primaryHalf(2),
			secondaryHalf(3)
			}
        MAX-ACCESS    read-only
        STATUS        current
        DESCRIPTION   "Represent the RBS switch ring status, `normalRing (1) means ring is 
		       not broken. 'primaryHalf'(2) means ring is broken and this switch is 
		       on the primary half broken ring. 'secondaryHalf'(3) means ring is 
		       broken and this switch is on secondary half ring"
        ::= { rcBanRingTopoEntry 9 }       

rcBanRingTopoRingName OBJECT-TYPE
        SYNTAX        DisplayString (SIZE (1..32)) 
        MAX-ACCESS    read-only
        STATUS        current
        DESCRIPTION   "Ring Name"
        ::= { rcBanRingTopoEntry 10 }

-- Standalone RBS Table 

rcBanRingSaRbsTable OBJECT-TYPE

        SYNTAX        SEQUENCE OF RcBanRingSaRbsEntry
        MAX-ACCESS    not-accessible
        STATUS        current
        DESCRIPTION   ""
        ::= { rcBanRing 3 }
 
rcBanRingSaRbsEntry OBJECT-TYPE
        SYNTAX        RcBanRingSaRbsEntry
        MAX-ACCESS    not-accessible
        STATUS        current
        DESCRIPTION   "BAN ring table entry."
        INDEX         { rcBanRingSaRbsBanPort }
        ::= { rcBanRingSaRbsTable 1 }
 
RcBanRingSaRbsEntry ::=
        SEQUENCE {
                rcBanRingSaRbsBanPort               InterfaceIndex,
                rcBanRingSaRbsAdminState            EnableValue,
                rcBanRingSaRbsTxTimer               Integer32,
                rcBanRingSaRbsOperState             INTEGER,
                rcBanRingSaRbsDiscoverInterval      INTEGER,
                rcBanRingSaRbsRowStatus             RowStatus
          }

rcBanRingSaRbsBanPort OBJECT-TYPE
        SYNTAX        InterfaceIndex (64..687)
        MAX-ACCESS    not-accessible
        STATUS        current
        DESCRIPTION   "Standalone RBS BAN port number."
        ::= { rcBanRingSaRbsEntry 1 }
 
rcBanRingSaRbsAdminState OBJECT-TYPE
        SYNTAX        EnableValue
        MAX-ACCESS    read-create
        STATUS        current
        DESCRIPTION   "Administratively enable or disable a Standalone RBS."
	DEFVAL        { disable }
        ::= { rcBanRingSaRbsEntry 2 }

rcBanRingSaRbsTxTimer OBJECT-TYPE
        SYNTAX        Integer32
        MAX-ACCESS    read-write
        STATUS        current
        DESCRIPTION   "Standalone RBS TX timer value."
        ::= { rcBanRingSaRbsEntry 3 }
 
rcBanRingSaRbsOperState OBJECT-TYPE
        SYNTAX        INTEGER {
			  down(0), 
                          normal(1), 
                          cut(2), 
                          recover(3) 
                       }
        MAX-ACCESS    read-only
        STATUS        current
        DESCRIPTION   "Standalone RBS operation status."
        ::= { rcBanRingSaRbsEntry 4 }

rcBanRingSaRbsDiscoverInterval OBJECT-TYPE
        SYNTAX          INTEGER (1..255)
        UNITS           "seconds"
        MAX-ACCESS      read-create
        STATUS          current
        DESCRIPTION     "The time interval between discovery messages that are
                         generated to check for Standalone RBS module existence."
        DEFVAL          { 30 }
        ::= { rcBanRingSaRbsEntry 5 }

rcBanRingSaRbsRowStatus OBJECT-TYPE
        SYNTAX        RowStatus
        MAX-ACCESS    read-create
        STATUS        current
        DESCRIPTION   "Uses for controlling the creation and
                       deletion of this row."
        ::= { rcBanRingSaRbsEntry 6 }

-- Ban Ring Dual-homing Ring

rcBanDhRingTable OBJECT-TYPE

        SYNTAX        SEQUENCE OF RcBanDhRingEntry
        MAX-ACCESS    not-accessible
        STATUS        current
        DESCRIPTION   ""
        ::= { rcBanRing 4 }
 
rcBanDhRingEntry OBJECT-TYPE
        SYNTAX        RcBanDhRingEntry
        MAX-ACCESS    not-accessible
        STATUS        current
        DESCRIPTION   "BAN Dual Home ring table entry."
        INDEX         { rcBanDhRingId }
        ::= { rcBanDhRingTable 1 }

RcBanDhRingEntry ::=
        SEQUENCE {
                rcBanDhRingId                    INTEGER,
                rcBanDhRingBanPortType           INTEGER,
                rcBanDhRingPort                  InterfaceIndex,
                rcBanDhRingPartnerPortMac        MacAddress,
		rcBanDhRingIbtPort               InterfaceIndex,
                rcBanDhRingIbtMlt                INTEGER,
                rcBanDhRingIbtVid                INTEGER,
                rcBanDhRingAdminState            EnableValue,
                rcBanDhRingTxTimer               Integer32,
                rcBanDhRingOperState             INTEGER,
                rcBanDhRingName                  DisplayString,
                rcBanDhRingDiscoverInterval      INTEGER,
                rcBanDhRingRowStatus             RowStatus,
                rcBanDhRingNumVlanIds            Integer32,
                rcBanDhRingVlanIds               IdList,
		rcBanDhRingRrpHello              EnableValue,
                rcBanDhRingRrpHelloInterval      INTEGER,
		rcBanDhRingClearRrpStats         TruthValue,
		rcBanDhRingClearRdpStats         TruthValue,
		rcBanDhRingNumOfUni              Integer32
       }

rcBanDhRingId OBJECT-TYPE
        SYNTAX        INTEGER (1..254)
        MAX-ACCESS    not-accessible
        STATUS        current
        DESCRIPTION   "BAN Dual Home Ring ID."
        ::= { rcBanDhRingEntry 1 }

rcBanDhRingBanPortType  OBJECT-TYPE
        SYNTAX          INTEGER {
            primary(1),
            secondary(2)
            }
        MAX-ACCESS      read-create
        STATUS          current
        DESCRIPTION     "Primary/Secondary BAN port type"
        DEFVAL          { primary }
        ::= { rcBanDhRingEntry 2 }

rcBanDhRingPort OBJECT-TYPE
        SYNTAX        InterfaceIndex
        MAX-ACCESS    read-create
        STATUS        current
        DESCRIPTION   "BAN  Dual Home Ring primaray port number."
        ::= { rcBanDhRingEntry 3 }
 
rcBanDhRingPartnerPortMac OBJECT-TYPE
        SYNTAX        MacAddress
        MAX-ACCESS    read-create
        STATUS        current
        DESCRIPTION   "BAN  Dual Home Ring Partner/other port MAC address."
        ::= { rcBanDhRingEntry 4 }

rcBanDhRingIbtPort OBJECT-TYPE
        SYNTAX        InterfaceIndex
        MAX-ACCESS    read-create
        STATUS        current
        DESCRIPTION   "Single link Inter BAN Trunk port number."
        ::= { rcBanDhRingEntry 5 }

rcBanDhRingIbtMlt OBJECT-TYPE
        SYNTAX        INTEGER (0..32)
        MAX-ACCESS    read-create
        STATUS        current
        DESCRIPTION   "Multi-link Inter BAN Trunk MLT interface ID"
        ::= { rcBanDhRingEntry 6 }
 
rcBanDhRingIbtVid OBJECT-TYPE
        SYNTAX        INTEGER (0..4094) 
        MAX-ACCESS    read-create
        STATUS        current
        DESCRIPTION   "BAN Dual Home Ring IBT port VID number."
        ::= { rcBanDhRingEntry 7 }

rcBanDhRingAdminState OBJECT-TYPE
        SYNTAX        EnableValue
        MAX-ACCESS    read-create
        STATUS        current
        DESCRIPTION   "Administratively enable or disable a BAN Dual Home Ring."
	DEFVAL        { disable }
        ::= { rcBanDhRingEntry 8 }

rcBanDhRingTxTimer OBJECT-TYPE
        SYNTAX        Integer32
        MAX-ACCESS    read-create
        STATUS        current
        DESCRIPTION   "BAN Dual Home Ring TX timer value."
        ::= { rcBanDhRingEntry 9 }
 
rcBanDhRingOperState OBJECT-TYPE
        SYNTAX        INTEGER { 
			  down(0),
                          normal(1), 
                          cut(2), 
                          recover(3) 
                       }
        MAX-ACCESS    read-only
        STATUS        current
        DESCRIPTION   "BAN Dual Home Ring operation status."
        ::= { rcBanDhRingEntry 10 }

rcBanDhRingName OBJECT-TYPE
        SYNTAX        DisplayString (SIZE (0..32)) 
        MAX-ACCESS    read-create
        STATUS        current
        DESCRIPTION   "Modification of this field is allowed only
                       when the admin state is disabled."
        ::= { rcBanDhRingEntry 11 }

rcBanDhRingDiscoverInterval OBJECT-TYPE
        SYNTAX          INTEGER (1..255)
        UNITS           "seconds"
        MAX-ACCESS      read-create
        STATUS          current
        DESCRIPTION     "The time interval between discovery messages that are
                         generated to check for ring module existence."
        DEFVAL          { 30 }
        ::= { rcBanDhRingEntry 12 }

rcBanDhRingRowStatus OBJECT-TYPE
        SYNTAX        RowStatus
        MAX-ACCESS    read-create
        STATUS        current
        DESCRIPTION   "Uses for controlling the creation and
                       deletion of this row."
        ::= { rcBanDhRingEntry 13 }

rcBanDhRingNumVlanIds OBJECT-TYPE
        SYNTAX        	Integer32
        MAX-ACCESS      read-only
        STATUS        	current
        DESCRIPTION   	"Used to indicate the number of VLAN IDs that
                      	are stored in the rcBanRingVlanIds variable."
        ::= { rcBanDhRingEntry 14 }

rcBanDhRingVlanIds OBJECT-TYPE
        SYNTAX        	IdList (SIZE (4096))
        MAX-ACCESS      read-create
        STATUS        	current
        DESCRIPTION   	"An array used to identify which VLANs this Ring 
                      	is associated with.  Each VLAN ID is stored as a 
		      	two octet value. The first octet in the pair holds
                      	bits 15-8 of the VLAN ID, while the second octet
                      	holds bits 7-0 of the VLAN ID."
        ::= { rcBanDhRingEntry 15 }

rcBanDhRingRrpHello OBJECT-TYPE
        SYNTAX        EnableValue
        MAX-ACCESS    read-create
        STATUS        current
        DESCRIPTION   "RRP hello enable or disable a BAN Ring."
	DEFVAL        { disable }
        ::= { rcBanDhRingEntry 16 }

rcBanDhRingRrpHelloInterval OBJECT-TYPE
        SYNTAX          INTEGER (1000..60000)
        UNITS           "milliseconds"
        MAX-ACCESS      read-create
        STATUS          current
        DESCRIPTION     "The time interval between hello messages that are
                         generated to the ESU."
        DEFVAL          { 1000 }
        ::= { rcBanDhRingEntry 17 }

rcBanDhRingClearRrpStats   OBJECT-TYPE
        SYNTAX          TruthValue
        MAX-ACCESS      read-write
        STATUS          current
        DESCRIPTION     "To clear the RRP sending/receiving and missing 
			 hello message counter"
	DEFVAL          { false }
        ::= { rcBanDhRingEntry 18 }

rcBanDhRingClearRdpStats   OBJECT-TYPE
        SYNTAX          TruthValue
        MAX-ACCESS      read-write
        STATUS          current
        DESCRIPTION     "To clear the RDP sending/receiving message counter"
	DEFVAL          { false }
        ::= { rcBanDhRingEntry 19 }

rcBanDhRingNumOfUni OBJECT-TYPE
        SYNTAX        	Integer32
        MAX-ACCESS      read-only
        STATUS        	current
        DESCRIPTION   	"Used to indicate the number of UNIs this ring
                      	is assigned to"
        ::= { rcBanDhRingEntry 20 } 


-- rcBanRingStatsTable 

rcBanRingStatsTable OBJECT-TYPE

        SYNTAX        SEQUENCE OF RcBanRingStatsEntry
        MAX-ACCESS    not-accessible
        STATUS        current
        DESCRIPTION   "Ban Ring stats table"
        ::= { rcBanRing 5 }
 
rcBanRingStatsEntry OBJECT-TYPE
        SYNTAX        RcBanRingStatsEntry
        MAX-ACCESS    not-accessible
        STATUS        current
        DESCRIPTION   "BAN ring table entry. Contain RRP and Rdp Message
                      sending/receiving and missing counter"
        INDEX         { rcBanRingStatsId }
        ::= { rcBanRingStatsTable 1 }
 
RcBanRingStatsEntry ::= 
        SEQUENCE {
                rcBanRingStatsId                            INTEGER,
                rcBanRingStatsRingOperState                 INTEGER,
                rcBanRingStatsRingName                      DisplayString,
                rcBanRingStatsPrimaryPortTxRrpHello         Counter32,
                rcBanRingStatsPrimaryPortRxRrpHello         Counter32,
                rcBanRingStatsSecondaryPortTxRrpHello       Counter32,  
                rcBanRingStatsSecondaryPortRxRrpHello       Counter32,
                rcBanRingStatsPrimaryPortMissingRrpHello    Counter32,
                rcBanRingStatsSecondaryPortMissingRrpHello  Counter32,
                rcBanRingStatsPrimaryPortTxRdp              Counter32,     
                rcBanRingStatsPrimaryPortRxRdp              Counter32,
                rcBanRingStatsSecondaryPortTxRdp            Counter32,     
                rcBanRingStatsSecondaryPortRxRdp            Counter32
       }

rcBanRingStatsId      OBJECT-TYPE
        SYNTAX        INTEGER (1..254)
        MAX-ACCESS    not-accessible
        STATUS        current
        DESCRIPTION   "BAN Ring ID."
        ::= { rcBanRingStatsEntry 1 }

rcBanRingStatsRingOperState    OBJECT-TYPE
        SYNTAX        INTEGER { 
			  down(0),
                          normal(1), 
                          cut(2), 
                          recover(3) 
                       }
        MAX-ACCESS    read-only
        STATUS        current
        DESCRIPTION   "BAN Ring operation status."
        ::= { rcBanRingStatsEntry 2 }

rcBanRingStatsRingName   OBJECT-TYPE
        SYNTAX        DisplayString (SIZE (0..32)) 
        MAX-ACCESS    read-only
        STATUS        current
        DESCRIPTION   "Name fo the Ban ring"
        ::= { rcBanRingStatsEntry 3 }


rcBanRingStatsPrimaryPortTxRrpHello  OBJECT-TYPE
        SYNTAX         Counter32
        MAX-ACCESS     read-only
        STATUS         current
        DESCRIPTION    "The total Number of RRP Hello messages are 
                       transmitted by primary port"
        ::= { rcBanRingStatsEntry 4 }
                                            
rcBanRingStatsPrimaryPortRxRrpHello  OBJECT-TYPE
        SYNTAX         Counter32
        MAX-ACCESS     read-only
        STATUS         current
        DESCRIPTION    "The total Number of RRP Hello messages are 
                       received on primary port. Every RRP hello message
                       is transmitted by Primary port, is expected to be 
                       responsed by a Connected Port (ESU Port). The
                       respose is a receiving count"
        ::= { rcBanRingStatsEntry 5 }
                          
rcBanRingStatsSecondaryPortTxRrpHello   OBJECT-TYPE 
        SYNTAX         Counter32
        MAX-ACCESS     read-only
        STATUS         current
        DESCRIPTION    "The total Number of RRP Hello messages are 
                       transmitted by Seondary port"
        ::= { rcBanRingStatsEntry 6 }            
                                            
rcBanRingStatsSecondaryPortRxRrpHello   OBJECT-TYPE    
        SYNTAX         Counter32
        MAX-ACCESS     read-only
        STATUS         current
        DESCRIPTION    "The total Number of RRP Hello messages are 
                       received on Secondary port. Every RRP hello message
                       is transmitted by Secondary port, is expected to be 
                       responsed by a Connected Port (ESU Port). The
                       respose is a receiving count"
        ::= { rcBanRingStatsEntry 7 }

rcBanRingStatsPrimaryPortMissingRrpHello  OBJECT-TYPE
        SYNTAX         Counter32
        MAX-ACCESS     read-only
        STATUS         current
        DESCRIPTION    "The total Number of RRP Hello messages responses
                       are missing on Primary port. Each RRP hello
                       message is transmitted by Primary port, 
                       is expected to be responded by a Connected Port
                       (ESU Port). Otherwise, it is a missing count"
        ::= { rcBanRingStatsEntry 8 }                                            
rcBanRingStatsSecondaryPortMissingRrpHello  OBJECT-TYPE
        SYNTAX         Counter32
        MAX-ACCESS     read-only
        STATUS         current
        DESCRIPTION    "The total Number of RRP Hello messages responses
                       are missing on Secondary port. Each RRP hello
                       message is transmitted by Secondary port, 
                       is expected to be respondsed by a Connected Port
                       (ESU Port). Otherwise, it is a missing count"
        ::= { rcBanRingStatsEntry 9 }
                     
rcBanRingStatsPrimaryPortTxRdp   OBJECT-TYPE
        SYNTAX         Counter32
        MAX-ACCESS     read-only
        STATUS         current
        DESCRIPTION    "The total Number of RDP messages are transmitted 
                       by Primary Port." 
        ::= { rcBanRingStatsEntry 10 }

rcBanRingStatsPrimaryPortRxRdp     OBJECT-TYPE
        SYNTAX         Counter32
        MAX-ACCESS     read-only
        STATUS         current
        DESCRIPTION    "The total Number of RDP messages are received 
                       on Primary Port. No RDP Message received on
                       Primary Port if rcBanRingStatsRingOperState is 
                       'normal'."
        ::= { rcBanRingStatsEntry 11 }

rcBanRingStatsSecondaryPortTxRdp   OBJECT-TYPE        
        SYNTAX         Counter32
        MAX-ACCESS     read-only
        STATUS         current
        DESCRIPTION    "The total Number of RDP messages are transmitted 
                       by Secondary Port when rcBanRingStatsRingOperState
                       is in 'cut'. No RDP Tx when it is 'normal'" 
        ::= { rcBanRingStatsEntry 12 }

rcBanRingStatsSecondaryPortRxRdp  OBJECT-TYPE  
       SYNTAX         Counter32
        MAX-ACCESS     read-only
        STATUS         current
        DESCRIPTION    "The total Number of RDP messages received 
                       on Secondary Port." 
        ::= { rcBanRingStatsEntry 13 }

-- rcBanDhRingStatsTable 
rcBanDhRingStatsTable OBJECT-TYPE

        SYNTAX        SEQUENCE OF RcBanDhRingStatsEntry
        MAX-ACCESS    not-accessible
        STATUS        current
        DESCRIPTION   "Ban Ring stats table"
        ::= { rcBanRing 6  }

rcBanDhRingStatsEntry OBJECT-TYPE
        SYNTAX        RcBanDhRingStatsEntry
        MAX-ACCESS    not-accessible
        STATUS        current
        DESCRIPTION   "BAN ring table entry. Contain RRP and Rdp Message
                      sending/receiving and missing counter"
        INDEX         { rcBanDhRingStatsId }
        ::= { rcBanDhRingStatsTable 1 }

RcBanDhRingStatsEntry ::=
        SEQUENCE {
                rcBanDhRingStatsId                         INTEGER,
                rcBanDhRingStatsRingOperState              INTEGER,
                rcBanDhRingStatsRingName                   DisplayString,
                rcBanDhRingStatsRingPortTxRrpHello         Counter32,
                rcBanDhRingStatsRingPortRxRrpHello         Counter32,
                rcBanDhRingStatsIbtPortTxRrpHello          Counter32,
                rcBanDhRingStatsIbtPortRxRrpHello          Counter32,
                rcBanDhRingStatsRingPortMissingRrpHello    Counter32,
                rcBanDhRingStatsIbtPortMissingRrpHello     Counter32,
                rcBanDhRingStatsRingPortTxRdp              Counter32,
                rcBanDhRingStatsRingPortRxRdp              Counter32,
                rcBanDhRingStatsIbtPortRxRdp               Counter32

       }

rcBanDhRingStatsId      OBJECT-TYPE
        SYNTAX        INTEGER (1..254)
        MAX-ACCESS    not-accessible
        STATUS        current
        DESCRIPTION   "BAN Ring ID."
        ::= { rcBanDhRingStatsEntry 1 }

rcBanDhRingStatsRingOperState    OBJECT-TYPE
        SYNTAX        INTEGER {
                          down(0),
                          normal(1),
                          cut(2),
                          recover(3)
                       }
        MAX-ACCESS    read-only
        STATUS        current
        DESCRIPTION   "BAN Ring operation status."
        ::= { rcBanDhRingStatsEntry 2 }

rcBanDhRingStatsRingName   OBJECT-TYPE
        SYNTAX        DisplayString (SIZE (0..32))
        MAX-ACCESS    read-only
        STATUS        current
        DESCRIPTION   "Name fo the Ban ring"
        ::= { rcBanDhRingStatsEntry 3 }


rcBanDhRingStatsRingPortTxRrpHello  OBJECT-TYPE
        SYNTAX         Counter32
        MAX-ACCESS     read-only
        STATUS         current
        DESCRIPTION    "The total Number of RRP Hello messages are
                       transmitted by primary port"
        ::= { rcBanDhRingStatsEntry 4 }

rcBanDhRingStatsRingPortRxRrpHello  OBJECT-TYPE
        SYNTAX         Counter32
        MAX-ACCESS     read-only
        STATUS         current
        DESCRIPTION    "The total Number of RRP Hello messages are
                       received on primary port. Every RRP hello message
                       is transmitted by Ring port, is expected to be
                       responsed by a Connected Port (ESU Port). The
                       respose is a receiving count"
        ::= { rcBanDhRingStatsEntry 5 }

rcBanDhRingStatsIbtPortTxRrpHello   OBJECT-TYPE
        SYNTAX         Counter32
        MAX-ACCESS     read-only
        STATUS         current
        DESCRIPTION    "The total Number of RRP Hello messages are
                       transmitted by Seondary port"
        ::= { rcBanDhRingStatsEntry 6 }

rcBanDhRingStatsIbtPortRxRrpHello   OBJECT-TYPE
        SYNTAX         Counter32
        MAX-ACCESS     read-only
        STATUS         current
        DESCRIPTION    "The total Number of RRP Hello messages are
                       received on Ibt port. Every RRP hello message
                       is transmitted by Ibt port, is expected to be
                       responsed by a Connected Port (ESU Port). The
                       respose is a receiving count"
        ::= { rcBanDhRingStatsEntry 7 }

rcBanDhRingStatsRingPortMissingRrpHello  OBJECT-TYPE
        SYNTAX         Counter32
        MAX-ACCESS     read-only
        STATUS         current
        DESCRIPTION    "The total Number of RRP Hello messages responses
                       are missing on Ring port. Each RRP hello
                       message is transmitted by Ring port,
                       is expected to be responded by a Connected Port
                       (ESU Port). Otherwise, it is a missing count"
        ::= { rcBanDhRingStatsEntry 8 }

rcBanDhRingStatsIbtPortMissingRrpHello  OBJECT-TYPE
        SYNTAX         Counter32
        MAX-ACCESS     read-only
        STATUS         current
        DESCRIPTION    "The total Number of RRP Hello messages responses
                       are missing on Ibt port. Each RRP hello
                       message is transmitted by Ibt port,
                       is expected to be respondsed by a Connected Port
                       (ESU Port). Otherwise, it is a missing count"
        ::= { rcBanDhRingStatsEntry 9 }

rcBanDhRingStatsRingPortTxRdp   OBJECT-TYPE
        SYNTAX         Counter32
        MAX-ACCESS     read-only
        STATUS         current
        DESCRIPTION    "The total Number of RDP messages are transmitted
                       by Ring Port."
        ::= { rcBanDhRingStatsEntry 10 }

rcBanDhRingStatsRingPortRxRdp     OBJECT-TYPE
        SYNTAX         Counter32
        MAX-ACCESS     read-only
        STATUS         current
        DESCRIPTION    "The total Number of RDP messages are received
                       on Ring Port."
        ::= { rcBanDhRingStatsEntry 11 }

rcBanDhRingStatsIbtPortRxRdp  OBJECT-TYPE
       SYNTAX         Counter32
        MAX-ACCESS     read-only
        STATUS         current
        DESCRIPTION    "The total Number of RDP messages received
                       on Ibt Port."
        ::= { rcBanDhRingStatsEntry 12 }

-- TD Connectivity
--

rcTlsTest		OBJECT IDENTIFIER ::= { rcTdc 1 }

rcTlsTestTdc      OBJECT IDENTIFIER ::= { rcTlsTest 1 }

--
-- rcTlsTestTdc - TD Connectivity Test
--
rcTlsTestTdcTable  OBJECT-TYPE
        SYNTAX          SEQUENCE OF RcTlsTestTdcEntry
        MAX-ACCESS      not-accessible
        STATUS          current
        DESCRIPTION     "Provisioning information for all TD Connectivity
                        tests and each tests' results."
        ::= { rcTlsTestTdc 1 }

rcTlsTestTdcEntry  OBJECT-TYPE
        SYNTAX          RcTlsTestTdcEntry
        MAX-ACCESS      not-accessible
        STATUS          current
        DESCRIPTION     "Provisioning information for a particular TD
                        Connectivity test and the test results."
        INDEX           { rcTlsTestTdcTestId }
        ::= { rcTlsTestTdcTable 1 }

RcTlsTestTdcEntry ::=
        SEQUENCE {
                rcTlsTestTdcTestId        INTEGER,
                rcTlsTestTdcTDI           INTEGER,
                rcTlsTestTdcSrcPortNum    Integer32,
                rcTlsTestTdcDstPortNum    Integer32,
                rcTlsTestTdcSrcPortIP     IpAddress,
                rcTlsTestTdcDstPortIP     IpAddress,
                rcTlsTestTdcPktPriority   INTEGER,
                rcTlsTestTdcPktTimeout    INTEGER,
                rcTlsTestTdcProtocol      INTEGER,
                rcTlsTestTdcTestType      INTEGER,
                rcTlsTestTdcTimeTrace     INTEGER,
                rcTlsTestTdcPriority      TruthValue,
                rcTlsTestTdcPktsSent        Integer32,
                rcTlsTestTdcPktsReceived    Integer32,
                rcTlsTestTdcRttBroadcast    Integer32,
                rcTlsTestTdcRttUnicast      Integer32,
                rcTlsTestTdcPriOpePkt       OCTET STRING,
                rcTlsTestTdcTestDate        OCTET STRING,
                rcTlsTestTdcTestTime        OCTET STRING,
                rcTlsTestTdcTraceInfo       TruthValue,
                rcTlsTestTdcRowStatus       RowStatus,
                rcTlsTestTdcAction          INTEGER,
                rcTlsTestTdcResult          INTEGER,
                rcTlsTestTdcErrorMask       BITS,
                rcTlsTestTdcName          DisplayString,
                rcTlsTestTdcMulticastCnt  INTEGER,
                rcTlsTestTdcUnicastCnt    INTEGER,
                rcTlsTestTdcRepeatCnt     INTEGER,
                rcTlsTestTdcPeriodicRate  INTEGER,
                rcTlsTestTdcPeriodicCount INTEGER,
                rcTlsTestTdcHistoryCnt    INTEGER,
                rcTlsTestTdcRttThreshold  INTEGER,
                rcTlsTestTdcSnmpTrapControl TruthValue,
                rcTlsTestTdcRttBroadcastMin Integer32,
                rcTlsTestTdcRttBroadcastMax Integer32,
                rcTlsTestTdcRttBroadcastAvg Integer32,
                rcTlsTestTdcRttUnicastMin   Integer32,
                rcTlsTestTdcRttUnicastMax   Integer32,
                rcTlsTestTdcRttUnicastAvg   Integer32,
                rcTlsTestTdcHopCountMin     Integer32,
                rcTlsTestTdcHopCountMax     Integer32,
                rcTlsTestTdcHopCountAvg     Integer32,
                rcTlsTestTdcClearHistoryAction INTEGER,
                rcTlsTestTdcScheduled       TruthValue,
                rcTlsTestTdcCurrentPeriodicCount Integer32,
	        rcTlsTestTdcQtag            INTEGER
                }

rcTlsTestTdcTestId  OBJECT-TYPE
        SYNTAX          INTEGER (1..9999)
        MAX-ACCESS      read-only
        STATUS          current
        DESCRIPTION     "The unique TDC test ID for this entry."
        ::= { rcTlsTestTdcEntry 1 }

rcTlsTestTdcTDI  OBJECT-TYPE
        SYNTAX          INTEGER (1..16777215)
        MAX-ACCESS      read-write
        STATUS          current
        DESCRIPTION     "The customer TD on which this test is executed."
        ::= { rcTlsTestTdcEntry 2 }

rcTlsTestTdcSrcPortNum  OBJECT-TYPE
        SYNTAX          Integer32
        MAX-ACCESS      read-write
        STATUS          current
        DESCRIPTION     "An index value that uniquely identifies the TLS
                        interface (UNI port) at the source of the test."
        ::= { rcTlsTestTdcEntry 3 }

rcTlsTestTdcDstPortNum  OBJECT-TYPE
        SYNTAX          Integer32
        MAX-ACCESS      read-write
        STATUS          current
        DESCRIPTION     "An index value that uniquely identifies the
                        destination TLS interface (LAN port)."
        ::= { rcTlsTestTdcEntry 4 }

rcTlsTestTdcSrcPortIP  OBJECT-TYPE
        SYNTAX          IpAddress
        MAX-ACCESS      read-write
        STATUS          current
        DESCRIPTION     "The IP address of the source port or CPU."
        ::= { rcTlsTestTdcEntry 5 }

rcTlsTestTdcDstPortIP  OBJECT-TYPE
        SYNTAX          IpAddress
        MAX-ACCESS      read-write
        STATUS          current
        DESCRIPTION     "The IP address of the destination port or CPU."
        ::= { rcTlsTestTdcEntry 6 }

rcTlsTestTdcPktPriority  OBJECT-TYPE
        SYNTAX          INTEGER (0..7)
        MAX-ACCESS      read-write
        STATUS          current
        DESCRIPTION     "Optional 802.1 network priority to be used for
                        this test. If not specified by the user, the port
                        default priority is assumed."
        ::= { rcTlsTestTdcEntry 7 }

rcTlsTestTdcPktTimeout  OBJECT-TYPE
        SYNTAX          INTEGER (1..120)
        MAX-ACCESS      read-write
        STATUS          current
        DESCRIPTION     "Optional timeout period for the TDC test in seconds.
                        If not specified, a default value of 10 seconds will
                        be used."
        DEFVAL          { 10 }
        ::= { rcTlsTestTdcEntry 8 }

rcTlsTestTdcProtocol  OBJECT-TYPE
        SYNTAX          INTEGER {
                                  l2(1), -- tls/l2
                                  oel2(2),  -- oel2
                                  l2forcedOel2(3)  -- l2 port to send oel2
                        }
        MAX-ACCESS      read-write
        STATUS          current
        DESCRIPTION     "The protocol to use for the TDC test. If not
                        specified by the user, the mode (protocol) of the
                        source UNI port will be assumed."
        ::= { rcTlsTestTdcEntry 9 }

rcTlsTestTdcTestType  OBJECT-TYPE
        SYNTAX          INTEGER {
                                broadcastandunicast(1), -- both (tlsl2)
                                broadcast(2),  -- broadcast only (tlsl2)
                                unicast(3),  -- unicast only
                                multicastandunicast(4),  -- both (oel2)
                                multicast(5)  -- multicast only (oel2)
                        }
        MAX-ACCESS      read-write
        STATUS          current
        DESCRIPTION     "Optional target address of the TDC test. For tlsl2
                        protocol, the options are broadcast and unicast,
                        broadcast only and unicast only. For oel2 protocol,
                        the options are multicast and unicast, multicast only
                        and unicast only. By default, tlsl2 tests use broadcast
                        and unicast while oel2 tests use multicast and uni-cast."
        ::= { rcTlsTestTdcEntry 10 }

rcTlsTestTdcTimeTrace OBJECT-TYPE
        SYNTAX          INTEGER {
                                  none(1), -- basic test
                                  time(2),  -- time info test
                                  trace(3)  -- trace info test
                        }
        MAX-ACCESS      read-write
        STATUS          current
        DESCRIPTION     "Optional data associated with the TDC test. The
                        basic test validates the provisioning associated with
                        the source ports, destination ports and TDs configured
                        in the test. The time test collects the round-trip-time
                        of the packet between source and destination. The trace
                        test collects the IP address, machine adress and port
                        information for nodes along the source to destination
                        path (and back again). If not specified, the basic test
                        is assumed."
        DEFVAL          { 1 }
        ::= { rcTlsTestTdcEntry 11 }

rcTlsTestTdcPriority  OBJECT-TYPE
        SYNTAX          TruthValue
        MAX-ACCESS      read-only
        STATUS          current
        DESCRIPTION     "Boolean value indicating whether the user
                        specified the packet priority or not."
        ::= { rcTlsTestTdcEntry 12 }

rcTlsTestTdcPktsSent  OBJECT-TYPE
        SYNTAX          Integer32
        MAX-ACCESS      read-only
        STATUS          current
        DESCRIPTION     "The number of test packets sent."
        ::= { rcTlsTestTdcEntry 13 }

rcTlsTestTdcPktsReceived  OBJECT-TYPE
        SYNTAX          Integer32
        MAX-ACCESS      read-only
        STATUS          current
        DESCRIPTION     "The number of test packets received."
        ::= { rcTlsTestTdcEntry 14 }

rcTlsTestTdcRttBroadcast  OBJECT-TYPE
        SYNTAX          Integer32
        MAX-ACCESS      read-only
        STATUS          current
        DESCRIPTION     "The round-trip-time of the last broadcast test
                        packet in microseconds."
        ::= { rcTlsTestTdcEntry 15 }

rcTlsTestTdcRttUnicast  OBJECT-TYPE
        SYNTAX          Integer32
        MAX-ACCESS      read-only
        STATUS          current
        DESCRIPTION     "The round-trip-time of the last unicast test
                        packet in microseconds."
        ::= { rcTlsTestTdcEntry 16 }

rcTlsTestTdcPriOpePkt  OBJECT-TYPE
        SYNTAX          OCTET STRING (SIZE (8))
        MAX-ACCESS      read-only
        STATUS          current
        DESCRIPTION     "The OPE network priority. (ie. Customer priority
                        mapped into an OPE priority. Same as tlsTDPriority-Map.)"
        ::= { rcTlsTestTdcEntry 17 }

rcTlsTestTdcTestDate  OBJECT-TYPE
        SYNTAX          OCTET STRING (SIZE (6))
        MAX-ACCESS      read-only
        STATUS          current
        DESCRIPTION     "The local date stamp for the test (DD/MM)."
        ::= { rcTlsTestTdcEntry 18 }

rcTlsTestTdcTestTime  OBJECT-TYPE
        SYNTAX          OCTET STRING (SIZE (9))
        MAX-ACCESS      read-only
        STATUS          current
        DESCRIPTION     "The local time-of-day stamp for the test (HH:MM:SS)."
        ::= { rcTlsTestTdcEntry 19 }

rcTlsTestTdcTraceInfo  OBJECT-TYPE
        SYNTAX          TruthValue
        MAX-ACCESS      read-only
        STATUS          current
        DESCRIPTION     "Boolean value indicating whether the trace info
                        exists for this entry."
        ::= { rcTlsTestTdcEntry 20 }

rcTlsTestTdcRowStatus  OBJECT-TYPE
        SYNTAX          RowStatus
        MAX-ACCESS      read-write
        STATUS          current
        DESCRIPTION     "Used to create/delete an entry in this table"
        ::= { rcTlsTestTdcEntry 21 }

rcTlsTestTdcAction  OBJECT-TYPE
        SYNTAX          INTEGER {
                                none(1), -- no action taken
                                start(2), -- run the specified TDC test one time
                                startPeriodic(3), -- start the specified TDC test for periodic execution
                                abort (4), -- abort the execution of the cur-rent test
                                abortPeriodic(5) -- abort future executions of test (does not halt current test)
        }
        MAX-ACCESS      read-write
        STATUS          current
        DESCRIPTION     "This action controls test execution:  start will exe-cute the test one time; 
			startPeriodic will begin periodic execution of a test;
                        abort termi-nates the test if it is currently executing;
                        abortPeriodic will cancel future executions of a peri-odic test 
			(will not halt a current test).
                        No test results are collected for an aborted test.  
			abort and abortPeriodic have no affect
                        if a test is not running."
        DEFVAL          { none }
        ::= { rcTlsTestTdcEntry 22 }

rcTlsTestTdcResult  OBJECT-TYPE
        SYNTAX          INTEGER {
                                 none(1), -- none of these
                                 inProgress(2), -- action still in progress
                                 success(3), -- action successful
                                 fail(4) -- action failed
                        }
        MAX-ACCESS      read-only
        STATUS          current
        DESCRIPTION     "Result from the last TDC action"
        DEFVAL          { none }
        ::= { rcTlsTestTdcEntry 23 }


rcTlsTestTdcErrorMask  OBJECT-TYPE
        SYNTAX          BITS {
                          unused0(0),
                          bit1(1),
                          bit2(2),
                          bit3(3),
                          bit4(4),
                          bit5(5),
                          bit6(6),
                          bit7(7),
                          bit8(8),
                          bit9(9),
                          bit10(10),
                          bit11(11),
                          bit12(12),
                          bit13(13),
                          bit14(14),
                          bit15(15),
                          bit16(16),
                          bit17(17),
                          bit18(18),
                          bit19(19),
                          bit20(20),
                          bit21(21),
                          bit22(22),
                          unused23(23),
                          unused24(24),
                          unused25(25),
                          unused26(26),
                          unused27(27),
                          unused28(28),
                          unused29(29),
                          unused30(30),
                          unused31(31),
                          unused32(32),
                          bit33(33),
                          bit34(34),
                          bit35(35),
                          bit36(36),
                          bit37(37),
                          bit38(38),
                          bit39(39),
                          bit40(40),
                          bit41(41),
                          bit42(42),
                          bit43(43),
                          bit44(44),
                          bit45(45),
                          bit46(46),
                          bit47(47),
                          bit48(48),
                          bit49(49),
                              bit50(50)
                        }
        MAX-ACCESS      read-only
        STATUS          current
        DESCRIPTION     "The error mask associated with the TDC test. Each bit
                        in the mask represents a specific error. The errors
                        from least significant bit to highest significant bit
                        are:
                        bit  1 - TD nonexistent on destination port
                        bit  2 - TD disabled on destination port
                        bit  3 - TD not assigned to destination port
                        bit  4 - TD filtered on destination NNI port
                        bit  5 - destination port is NNI
                        bit  6 - destination port is craft
                        bit  7 - destination FDB test failed
                        bit  8 - destination administrative state down
                        bit  9 - destination operational state down
                        bit 10 - destination port connectivity mismatch error
                        bit 11 - destination port type mismatch
                        bit 12 - destination port mode mismatch error
                        bit 13 - destination MIB query failed
                        bit 14 - destination system error
                        bit 15 - invalid destination port
                        bit 16 - destination port is CPU
                        bit 17 - destination port mode mismatch warning
                        bit 18 - destination port connectivity mismatch warning
                        bit 19 - default priority used on destination
                        bit 20 - IP not assigned on destination oel2 port
                        bit 21 - static entry exists on destination port
                        bit 22 - destination FDB table full warning
                        bit 33 - TD nonexistent on source port
                        bit 34 - TD not assigned to source port
                        bit 35 - source FDB test failed
                        bit 36 - source administrative state down
                        bit 37 - source operational state down
                        bit 38 - source system error
                        bit 39 - no response
                        bit 40 - could not get trace information
                        bit 41 - could not get time information
                        bit 42 - source MIB query failed
                        bit 43 - TD disabled on source port
                        bit 44 - invalid source port
                        bit 45 - all ports down on the source node
                        bit 46 - unknown error
                        bit 47 - source FDB test failed
                        bit 48 - static entry exists on source port
                        bit 49 - no FDB entry for destination MAC, unicast aborted
                        bit 50 \226 RTT threshold exceeded"
        ::= { rcTlsTestTdcEntry 24 }


rcTlsTestTdcName  OBJECT-TYPE
        SYNTAX          DisplayString(SIZE (0 .. 20))
        MAX-ACCESS      read-write
        STATUS          current
        DESCRIPTION     "An optional user-defined name for this test.  A TDC
                        test name must be unique for each test."
        ::= { rcTlsTestTdcEntry 25 }

rcTlsTestTdcMulticastCnt  OBJECT-TYPE
        SYNTAX          INTEGER (0 .. 100)
        MAX-ACCESS      read-write
        STATUS          current
        DESCRIPTION     "The number of multicast messages sent with each test.
                        A value of zero(0) means the test will look at the FDB
                        for a valid entry, and if one exists a multicast packet
                        will not be sent."
        DEFVAL          { 1 }
        ::= { rcTlsTestTdcEntry 26 }

rcTlsTestTdcUnicastCnt  OBJECT-TYPE
        SYNTAX          INTEGER (0 .. 100)
        MAX-ACCESS      read-write
        STATUS          current
        DESCRIPTION     "The number of unicast messages sent with each test."
        DEFVAL          { 1 }
        ::= { rcTlsTestTdcEntry 27 }

rcTlsTestTdcRepeatCnt  OBJECT-TYPE
        SYNTAX          INTEGER (1 .. 100)
        MAX-ACCESS      read-write
        STATUS          current
        DESCRIPTION     "The number of times a message sequence is executed per
                        test."
        DEFVAL          { 1 }
        ::= { rcTlsTestTdcEntry 28 }


rcTlsTestTdcPeriodicRate  OBJECT-TYPE
        SYNTAX          INTEGER (1..1440)  -- time in minutes
        MAX-ACCESS      read-write
        STATUS          current
        DESCRIPTION     "Used to set a periodic test rate.  The time is
                        in minutes.  The time period ranges from once-a-minute (1) to once-a-day (1440).  A time
                        of zero will cause an error indication if a periodic test is initiated.
                        The test will run at the set rate up to the number of times 
			set via rcTlsTestTdcPeriodicCount.
                        This value can not be changed if a test is currently running periodically.
                        Periodic testing can be halted via rcTlsTestTdcPeriodic-Control."
        DEFVAL          { 1 }
        ::= { rcTlsTestTdcEntry 29 }

rcTlsTestTdcPeriodicCount  OBJECT-TYPE
        SYNTAX          INTEGER (0 .. 1440)
        MAX-ACCESS      read-write
        STATUS          current
        DESCRIPTION     "This object allows the user to place a limit on the number of times 
			 a test running periodically shall run.
                        - 0 : Run indefinitely at the periodic rate set via rcTlsTestTdcPeriodicRate.
                        -  1 .. 1440 : Run this number of times at the periodic rate set via 
			   rcTlsTestTdcPeriodicRate.
                        The maximum allowable value of 1440 allows the user to run at the maximum 
			periodic rate of once-per-minute for a 24-hour period.
                        Beware of the maximum number of samples which may be saved via the 

			TDC history table if you wish to save all the results of a peri-odic TDC test.
                        This value cannot be changed if a test is currently running periodically.  
			Periodic testing can be halted via rcTlsTestTdcPeriodic-Control."
        DEFVAL          { 0 }
        ::= { rcTlsTestTdcEntry 30 }

rcTlsTestTdcHistoryCnt  OBJECT-TYPE
        SYNTAX          INTEGER (1 .. 9999)
        MAX-ACCESS      read-write
        STATUS          current
        DESCRIPTION     "The number of results to be saved for a given TDC test.  The 
			 maximum number of results which may be saved by a given device is
			 obtainable via rcTlsTestTdcHistoryMax.
                         The total amount of storage allocated for all tests cannot exceed 
			 rcTlsTestTdcHistoryMax."
        DEFVAL          { 1 }
        ::= { rcTlsTestTdcEntry 31 }

rcTlsTestTdcRttThreshold  OBJECT-TYPE
        SYNTAX          INTEGER (0 .. 10000)
        MAX-ACCESS      read-write
        STATUS          current
        DESCRIPTION     "The number of milliseconds allowed for a message to
                        make a round trip journey. Exceeding this threshold can
                        cause the generation of an SNMP rcTlsTestTdcTestFailure
                        event, but will not affect continued execution of the
                        test.  A value of 0 indicates the threshold is
                        disabled."
        DEFVAL          { 0 }
        ::= { rcTlsTestTdcEntry 32 }

rcTlsTestTdcSnmpTrapControl  OBJECT-TYPE
        SYNTAX          TruthValue
        MAX-ACCESS      read-write
        STATUS          current
        DESCRIPTION     "Enable or disable the generation of the
                        rcTlsTestTdcTestFailure SNMP trap for this test."
        DEFVAL          { false }
        ::= { rcTlsTestTdcEntry 33 }

rcTlsTestTdcRttBroadcastMin  OBJECT-TYPE
        SYNTAX          Integer32
        MAX-ACCESS      read-only
        STATUS          current
        DESCRIPTION     "The minimum round-trip-time, in microseconds,
                        required by a broadcast test packet over for all
                        executions of this test."
        ::= { rcTlsTestTdcEntry 34 }

rcTlsTestTdcRttBroadcastMax  OBJECT-TYPE
        SYNTAX          Integer32
        MAX-ACCESS      read-only
        STATUS          current
        DESCRIPTION     "The maximum round-trip-time, in microseconds,
                        required by a broadcast test packet for all
                        executions of this test."
        ::= { rcTlsTestTdcEntry 35 }

rcTlsTestTdcRttBroadcastAvg  OBJECT-TYPE
        SYNTAX          Integer32
        MAX-ACCESS      read-only
        STATUS          current
        DESCRIPTION     "The average round-trip-time for a broadcast test
                        packet in microseconds for all executions of this test."
        ::= { rcTlsTestTdcEntry 36 }

rcTlsTestTdcRttUnicastMin  OBJECT-TYPE
        SYNTAX          Integer32
        MAX-ACCESS      read-only
        STATUS          current
        DESCRIPTION     " The minimum round-trip-time, in microseconds,
                        required by a unicast test packet for all
                        executions of this test."
        ::= { rcTlsTestTdcEntry 37 }

rcTlsTestTdcRttUnicastMax  OBJECT-TYPE
        SYNTAX          Integer32
        MAX-ACCESS      read-only
        STATUS          current
        DESCRIPTION     " The maximum round-trip-time, in microseconds,
                        required by a unicast test packet for all
                        executions of this test."
        ::= { rcTlsTestTdcEntry 38 }

rcTlsTestTdcRttUnicastAvg  OBJECT-TYPE
        SYNTAX          Integer32
        MAX-ACCESS      read-only
        STATUS          current
        DESCRIPTION     "The average round-trip-time for a unicast test
                        packet in microseconds for all executions of this test."
        ::= { rcTlsTestTdcEntry 39 }

rcTlsTestTdcHopCountMin  OBJECT-TYPE
        SYNTAX          Integer32
        MAX-ACCESS      read-only
        STATUS          current
        DESCRIPTION     "The minimum hop count for all executions of this test."
        ::= { rcTlsTestTdcEntry 40 }

rcTlsTestTdcHopCountMax  OBJECT-TYPE
        SYNTAX          Integer32
        MAX-ACCESS      read-only
        STATUS          current
        DESCRIPTION     "The maximum hop count for all executions of this test."
        ::= { rcTlsTestTdcEntry 41 }

rcTlsTestTdcHopCountAvg  OBJECT-TYPE
        SYNTAX          Integer32
        MAX-ACCESS      read-only
        STATUS          current
        DESCRIPTION     "The average hop count all executions of this test."
        ::= { rcTlsTestTdcEntry 42 }

rcTlsTestTdcClearHistoryAction OBJECT-TYPE
        SYNTAX          INTEGER {
                                  none(1), -- none of these
                                  clear(2) -- clear history for this test
        }
        MAX-ACCESS      read-write
        STATUS          current
        DESCRIPTION     "The clear option removes all stored test results for
                        this test including the most recent test result.  The clear option has no
                        affect if there are no stored results. A query of this object shall return none(1)."
        DEFVAL          { none }
        ::= { rcTlsTestTdcEntry 43 }

rcTlsTestTdcScheduled  OBJECT-TYPE
        SYNTAX          TruthValue
        MAX-ACCESS      read-only
        STATUS          current
        DESCRIPTION     "Indicates whether this test is currently scheduled to execute in periodic mode.
                        A TRUE response indicates the test is scheduled to run at some future time, and will
                        execute as scheduled unless manually aborted."
        ::= { rcTlsTestTdcEntry 44 }

rcTlsTestTdcCurrentPeriodicCount  OBJECT-TYPE
        SYNTAX          Integer32
        MAX-ACCESS      read-only
        STATUS          current
        DESCRIPTION     "This object returns the current value of the periodic counter.  If the value had been
                        set greater than zero and the test is currently running periodically, then this object
                        is decremented each time the the test runs until a value of zero is reached."
        ::= { rcTlsTestTdcEntry 45 }

rcTlsTestTdcQtag  OBJECT-TYPE
        SYNTAX        INTEGER (0..4096) 
        MAX-ACCESS    read-write
        STATUS        current
        DESCRIPTION   "TDC test Qtag, it is 0 by default. It means the first 
	               Qtag of the Tls Endpoint"
	DEFVAL        { 0 }
        ::= {rcTlsTestTdcEntry 46  }

--
-- Trace Information related to the TDC Test.
-- If rcTlsTestTdcTraceInfo == True, the trace info for the rcTlsTestTdcTestId
-- can be found in this table
--
rcTlsTestTdcTraceTable  OBJECT-TYPE
        SYNTAX          SEQUENCE OF RcTlsTestTdcTraceEntry
        MAX-ACCESS      not-accessible
        STATUS          current
        DESCRIPTION     "Trace information for a TD Connectivity test."
        ::= { rcTlsTestTdc 2}

rcTlsTestTdcTraceEntry  OBJECT-TYPE
        SYNTAX          RcTlsTestTdcTraceEntry
        MAX-ACCESS      not-accessible
        STATUS          current
        DESCRIPTION     "Trace information for the last TD Connectivity test
                        that had the trace functionality enabled."
        INDEX           { rcTlsTestTraceTestId,
                          rcTlsTestTraceTraceType,
                          rcTlsTestTraceTraceSeq }
        ::= { rcTlsTestTdcTraceTable 1 }

RcTlsTestTdcTraceEntry ::=
        SEQUENCE {
                -- index
                rcTlsTestTraceTestId              INTEGER,
                rcTlsTestTraceTraceType           INTEGER,
                rcTlsTestTraceTraceSeq            Integer32,

                -- node info
                rcTlsTestTraceNodeEthAddr         MacAddress,
                rcTlsTestTraceNodeIPAddr          IpAddress,
                rcTlsTestTracePortOut             Integer32,
                rcTlsTestTracePortIn              Integer32
                }

rcTlsTestTraceTestId  OBJECT-TYPE
        SYNTAX          INTEGER (1..9999)
        MAX-ACCESS      read-only
        STATUS          current
        DESCRIPTION     "The unique TDC test ID to which these results
                        correspond."
        ::= { rcTlsTestTdcTraceEntry 1 }

rcTlsTestTraceTraceType  OBJECT-TYPE
        SYNTAX          INTEGER {
                                broadcast(1),
                                multicast(2),
                                unicast(3)
                        }
        MAX-ACCESS      read-only
        STATUS          current
        DESCRIPTION     "Type of TDC test packet for which these results
                        apply."
        ::= { rcTlsTestTdcTraceEntry 2 }

rcTlsTestTraceTraceSeq  OBJECT-TYPE
        SYNTAX          Integer32 (-2147483648..2147483647)
        MAX-ACCESS      read-only
        STATUS          current
        DESCRIPTION     "The trace sequence number associated with this
                        entry."
        ::= { rcTlsTestTdcTraceEntry 3 }

rcTlsTestTraceNodeEthAddr  OBJECT-TYPE
        SYNTAX          MacAddress
        MAX-ACCESS      read-only
        STATUS          current
        DESCRIPTION     "The MAC address of the node by which this sequence
                        entry was generated."
        ::= { rcTlsTestTdcTraceEntry 4 }

rcTlsTestTraceNodeIPAddr  OBJECT-TYPE
        SYNTAX          IpAddress
        MAX-ACCESS      read-only
        STATUS          current
        DESCRIPTION     "The IP address of the node by which this sequence
                        entry was generated."
        ::= { rcTlsTestTdcTraceEntry 5 }

rcTlsTestTracePortOut  OBJECT-TYPE
        SYNTAX          Integer32
        MAX-ACCESS      read-only
        STATUS          current
        DESCRIPTION     "The port number on which this node sent the outbound
                        test packet."
        ::= { rcTlsTestTdcTraceEntry 6 }

rcTlsTestTracePortIn  OBJECT-TYPE
        SYNTAX          Integer32
        MAX-ACCESS      read-only
        STATUS          current
        DESCRIPTION     "The port number on which this node received the
                        inbound test packet."
        ::= { rcTlsTestTdcTraceEntry 7 }

--
-- History Information related to the TDC Test History.
--
rcTlsTestTdcHistoryTable  OBJECT-TYPE
        SYNTAX          SEQUENCE OF RcTlsTestTdcHistoryEntry
        MAX-ACCESS      not-accessible
        STATUS          current
        DESCRIPTION     "History for a TD Connectivity test."
        ::= { rcTlsTestTdc 3}

rcTlsTestTdcHistoryEntry  OBJECT-TYPE
        SYNTAX          RcTlsTestTdcHistoryEntry
        MAX-ACCESS      not-accessible
        STATUS          current
        DESCRIPTION     "History information for the TD Connectivity tests."
        INDEX           { rcTlsTestTdcHistoryTestHId,
                          rcTlsTestTdcHistoryId }
        ::= { rcTlsTestTdcHistoryTable 1 }

RcTlsTestTdcHistoryEntry ::=
        SEQUENCE {
                -- index
                rcTlsTestTdcHistoryTestHId       INTEGER,
                rcTlsTestTdcHistoryId     INTEGER,

                -- history data
                rcTlsTestTdcHistoryPktsSent         Integer32,
                rcTlsTestTdcHistoryPktsReceived     Integer32,
                rcTlsTestTdcHistoryRttBroadcastMin  Integer32,
                rcTlsTestTdcHistoryRttBroadcastMax  Integer32,
                rcTlsTestTdcHistoryRttBroadcastAvg  Integer32,
                rcTlsTestTdcHistoryRttUnicastMin    Integer32,
                rcTlsTestTdcHistoryRttUnicastMax    Integer32,
                rcTlsTestTdcHistoryRttUnicastAvg    Integer32,
                rcTlsTestTdcHistoryRttAvg           Integer32,
                rcTlsTestTdcHistoryHopCountMin      Integer32,
                rcTlsTestTdcHistoryHopCountMax      Integer32,
                rcTlsTestTdcHistoryHopCountAvg      Integer32,
                rcTlsTestTdcHistoryTestDateandTime  DateAndTime,
                rcTlsTestTdcHistoryTimeStamp        TimeStamp,
                rcTlsTestTdcHistoryResult           INTEGER,
                rcTlsTestTdcHistoryErrorMask        BITS
                }

rcTlsTestTdcHistoryTestHId  OBJECT-TYPE
        SYNTAX          INTEGER (1..9999)
        MAX-ACCESS      not-accessible
        STATUS          current
        DESCRIPTION     "The unique TDC test ID for this entry."
        ::= { rcTlsTestTdcHistoryEntry 1 }

rcTlsTestTdcHistoryId  OBJECT-TYPE
        SYNTAX          INTEGER (1 .. 9999)
        MAX-ACCESS      not-accessible
        STATUS          current
        DESCRIPTION     "The history id for this entry.  The device will save up to rcTlsTestTdcHistoryCnt
                        entries per test.  Test results are stored in the next available row, and if more than
                        rcTlsTestTdcHistoryCnt are present the oldest stored re-sult will be removed.
                        Once the maximum row id is reached the index will wrap-around."
        ::= { rcTlsTestTdcHistoryEntry 2 }

rcTlsTestTdcHistoryPktsSent  OBJECT-TYPE
        SYNTAX          Integer32
        MAX-ACCESS      read-only
        STATUS          current
        DESCRIPTION     "The number of packets sent during this test."
        ::= { rcTlsTestTdcHistoryEntry 3 }

rcTlsTestTdcHistoryPktsReceived  OBJECT-TYPE
        SYNTAX          Integer32
        MAX-ACCESS      read-only
        STATUS          current
        DESCRIPTION     "The number of packets received during this test."
        ::= { rcTlsTestTdcHistoryEntry 4 }

rcTlsTestTdcHistoryRttBroadcastMin  OBJECT-TYPE
        SYNTAX          Integer32
        MAX-ACCESS      read-only
        STATUS          current
        DESCRIPTION     "The average broadcast RTT during this test."
        ::= { rcTlsTestTdcHistoryEntry 5 }

rcTlsTestTdcHistoryRttBroadcastMax  OBJECT-TYPE
        SYNTAX          Integer32
        MAX-ACCESS      read-only
        STATUS          current
        DESCRIPTION     "The average broadcast RTT during this test."
        ::= { rcTlsTestTdcHistoryEntry 6 }

rcTlsTestTdcHistoryRttBroadcastAvg  OBJECT-TYPE
        SYNTAX          Integer32
        MAX-ACCESS      read-only
        STATUS          current
        DESCRIPTION     "The average broadcast RTT during this test."
        ::= { rcTlsTestTdcHistoryEntry 7 }

rcTlsTestTdcHistoryRttUnicastMin  OBJECT-TYPE
        SYNTAX          Integer32
        MAX-ACCESS      read-only
        STATUS          current
        DESCRIPTION     "The average unicast RTT during this test."
        ::= { rcTlsTestTdcHistoryEntry 8 }

rcTlsTestTdcHistoryRttUnicastMax  OBJECT-TYPE
        SYNTAX          Integer32
        MAX-ACCESS      read-only
        STATUS          current
        DESCRIPTION     "The average unicast RTT during this test."
        ::= { rcTlsTestTdcHistoryEntry 9 }

rcTlsTestTdcHistoryRttUnicastAvg  OBJECT-TYPE
        SYNTAX          Integer32
        MAX-ACCESS      read-only
        STATUS          current
        DESCRIPTION     "The average unicast RTT during this test."
        ::= { rcTlsTestTdcHistoryEntry 10 }

rcTlsTestTdcHistoryRttAvg  OBJECT-TYPE
        SYNTAX          Integer32
        MAX-ACCESS      read-only
        STATUS          current
        DESCRIPTION     "The average RTT during this test."
        ::= { rcTlsTestTdcHistoryEntry 11 }

rcTlsTestTdcHistoryHopCountMin  OBJECT-TYPE
        SYNTAX          Integer32
        MAX-ACCESS      read-only
        STATUS          current
        DESCRIPTION     "The minimum hop count during this test.  May be
                        invalid if test trace is disabled."
        ::= { rcTlsTestTdcHistoryEntry 12 }

rcTlsTestTdcHistoryHopCountMax  OBJECT-TYPE
        SYNTAX          Integer32
        MAX-ACCESS      read-only
        STATUS          current
        DESCRIPTION     "The maximum hop count during this test.  May be
                        invalid if test trace is disabled."
        ::= { rcTlsTestTdcHistoryEntry 13 }

rcTlsTestTdcHistoryHopCountAvg  OBJECT-TYPE
        SYNTAX          Integer32
        MAX-ACCESS      read-only
        STATUS          current
        DESCRIPTION     "The average hop count during this test.  May be
                        invalid if test trace is disabled."
        ::= { rcTlsTestTdcHistoryEntry 14 }

rcTlsTestTdcHistoryTestDateandTime  OBJECT-TYPE
        SYNTAX          DateAndTime
        MAX-ACCESS      read-only
        STATUS          current
        DESCRIPTION     "The date the test was run."
        ::= { rcTlsTestTdcHistoryEntry 15 }


rcTlsTestTdcHistoryTimeStamp  OBJECT-TYPE
        SYNTAX          TimeStamp
        MAX-ACCESS      read-only
        STATUS          current
        DESCRIPTION     "The value of sysUpTime at which the test began
                        execution."
        ::= { rcTlsTestTdcHistoryEntry 16 }


rcTlsTestTdcHistoryResult  OBJECT-TYPE
        SYNTAX          INTEGER {
                                 none(1), -- none of these
                                 success(3), -- action successful
                                 fail(4) -- action failed
                        }
        MAX-ACCESS      read-only
        STATUS          current
        DESCRIPTION     "Result from the TDC action"
        DEFVAL          { none }
        ::= { rcTlsTestTdcHistoryEntry 17 }

rcTlsTestTdcHistoryErrorMask  OBJECT-TYPE
        SYNTAX          BITS {
                          unused0(0),
                          bit1(1),
                          bit2(2),
                          bit3(3),
                          bit4(4),
                          bit5(5),
                          bit6(6),
                          bit7(7),
                          bit8(8),
                          bit9(9),
                          bit10(10),
                          bit11(11),
                          bit12(12),
                          bit13(13),
                          bit14(14),
                          bit15(15),
                          bit16(16),
                          bit17(17),
                          bit18(18),
                          bit19(19),
                          bit20(20),
                          bit21(21),
                          bit22(22),
                          unused23(23),
                          unused24(24),
                          unused25(25),
                          unused26(26),
                          unused27(27),
                          unused28(28),
                          unused29(29),
                          unused30(30),
                          unused31(31),
                          unused32(32),
                          bit33(33),
                          bit34(34),
                          bit35(35),
                          bit36(36),
                          bit37(37),
                          bit38(38),
                          bit39(39),
                          bit40(40),
                          bit41(41),
                          bit42(42),
                          bit43(43),
                          bit44(44),
                          bit45(45),
                          bit46(46),
                          bit47(47),
                          bit48(48),
                          bit49(49),
                          bit50(50)
                        }
        MAX-ACCESS      read-only
        STATUS          current
        DESCRIPTION     "The error mask associated with the TDC test. Each bit
                        in the mask represents a specific error. The errors
                        from least significant bit to highest significant bit
                        are:
                        bit  1 - TD nonexistent on destination port
                        bit  2 - TD disabled on destination port
                        bit  3 - TD not assigned to destination port
                        bit  4 - TD filtered on destination NNI port
                        bit  5 - destination port is NNI
                        bit  6 - destination port is craft
                        bit  7 - destination FDB test failed
                        bit  8 - destination administrative state down
                        bit  9 - destination operational state down
                        bit 10 - destination port connectivity mismatch error
                        bit 11 - destination port type mismatch
                        bit 12 - destination port mode mismatch error
                        bit 13 - destination MIB query failed
                        bit 14 - destination system error
                        bit 15 - invalid destination port
                        bit 16 - destination port is CPU
                        bit 17 - destination port mode mismatch warning
                        bit 18 - destination port connectivity mismatch warning
                        bit 19 - default priority used on destination
                        bit 20 - IP not assigned on destination oel2 port
                        bit 21 - static entry exists on destination port
                        bit 22 - destination FDB table full warning
                        bit 33 - TD nonexistent on source port
                        bit 34 - TD not assigned to source port
                        bit 35 - source FDB test failed
                        bit 36 - source administrative state down
                        bit 37 - source operational state down
                        bit 38 - source system error
                        bit 39 - no response
                        bit 40 - could not get trace information
                        bit 41 - could not get time information
                        bit 42 - source MIB query failed
                        bit 43 - TD disabled on source port
                        bit 44 - invalid source port
                        bit 45 - all ports down on the source node
                        bit 46 - unknown error
                        bit 47 - source FDB test failed
                        bit 48 - static entry exists on source port
                        bit 49 - no FDB entry for destination MAC, unicast aborted
                        bit 50 \226 RTT threshold exceeded"
        ::= { rcTlsTestTdcHistoryEntry 18 }


rcTlsTestTdcHistoryMax  OBJECT-TYPE
        SYNTAX          INTEGER (1..9999)
        MAX-ACCESS      read-only
        STATUS          obsolete
        DESCRIPTION     "The maximum amount of test history storage available on this device."
        ::= { rcTlsTestTdc 4}

rcTlsTestTdcHistoryRemaining  OBJECT-TYPE
        SYNTAX          INTEGER (1..9999)
        MAX-ACCESS      read-only
        STATUS          obsolete
        DESCRIPTION     "The amount of test history storage remaining unused
                        on this device."
        ::= { rcTlsTestTdc 5}

-- Tdc test result trap type
rcTlsTdcTestResultIndication   OBJECT-TYPE
        SYNTAX        INTEGER {
                tdcTestPass(1),
                tdcTestFail(2)
                  }
        MAX-ACCESS    read-only
        STATUS        current
        DESCRIPTION  " The Tdc Test has passed or failed "
        ::= { rcTlsTestTdc 6 }

rcTlsTdcTestRttExceedIndication   OBJECT-TYPE
        SYNTAX        INTEGER {
                tdcTestRttOK(1),
                tdcTestRttExceed(2)
                  }
        MAX-ACCESS    read-only
        STATUS        current
        DESCRIPTION  " The Tdc Test RTT has exceeded the preset threshold or not"
        ::= { rcTlsTestTdc 7 }

END
