RBT-MIB DEFINITIONS ::= BEGIN

IMPORTS
    MODULE-IDENTITY, enterprises FROM SNMPv2-SMI;

rbt MODULE-IDENTITY
    LAST-UPDATED        "200909230000Z"
    ORGANIZATION        "Riverbed Technology, Inc."
    CONTACT-INFO
       "   Riverbed Technical Support
           support@riverbed.com"
    DESCRIPTION         "Riverbed Technology MIB"
    REVISION            "200909230000Z"
    DESCRIPTION         "Updated contact information"
    ::= { enterprises 17163 }

products OBJECT IDENTIFIER
    ::= { rbt 1 }

END
