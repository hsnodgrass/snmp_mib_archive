------------------------------------------------------------------
--                                                              --
-- Tandem SNMP Trap Multiplexer MIB definitions.                --
--                                                              --
------------------------------------------------------------------


SNMP-TMUX-MIB DEFINITIONS ::= BEGIN

   IMPORTS
           enterprises, Gauge, Counter
               FROM RFC1155-SMI
           OBJECT-TYPE
               FROM RFC-1212
           TRAP-TYPE
               FROM RFC-1215
           DisplayString
               FROM RFC1213-MIB;

   --  TMUX-MIB

   tandem               OBJECT IDENTIFIER ::= { enterprises 169 }

   nonstopsystems       OBJECT IDENTIFIER ::= { tandem 3 }

   ztmx                 OBJECT IDENTIFIER ::= { nonstopsystems 185 }

   -- groups in TMX-MIB

   ztmxPDUStatistics    OBJECT IDENTIFIER ::= { ztmx 1 }

   ztmxProcess          OBJECT IDENTIFIER ::= { ztmx 2 }

   ztmxSpecial          OBJECT IDENTIFIER ::= { ztmx 3 }

   ------------------------------------------------------------------
   --                                                              --
   -- ztmxPDUStatistics: the PDU statistics group                  --
   --                                                              --
   ------------------------------------------------------------------

   ztmxUdpStatsCurrTime OBJECT-TYPE
      SYNTAX DisplayString
      ACCESS read-only
      STATUS mandatory
      DESCRIPTION
         "String showing the current time."
      ::= { ztmxPDUStatistics 1 }

   ztmxUdpInDatagrams   OBJECT-TYPE
      SYNTAX Counter
      ACCESS read-only
      STATUS mandatory
      DESCRIPTION
         "The total number of UPD datagrams delivered to the TMUX
         process."
      ::= { ztmxPDUStatistics 2 }

   ztmxInDecodeErrors   OBJECT-TYPE
      SYNTAX Counter
      ACCESS read-only
      STATUS mandatory
      DESCRIPTION
         "The total number of UPD datagrams delivered to the TMUX
         process that could not be interpreted as SNMP V.1 PDUs."
      ::= { ztmxPDUStatistics 3 }

   ztmxInGetPdus  OBJECT-TYPE
      SYNTAX Counter
      ACCESS read-only
      STATUS mandatory
      DESCRIPTION
         "The total number of Get PDUs received by the TMUX
         process.  These are probably strayed PDUs as the TMUX
         process is bound to the TRAP port."
      ::= { ztmxPDUStatistics 4 }

   ztmxInGetNextPdus OBJECT-TYPE
      SYNTAX Counter
      ACCESS read-only
      STATUS mandatory
      DESCRIPTION
         "The total number of GetNext PDUs received by the TMUX
         process.  These are probably strayed PDUs as the TMUX
         process is bound to the TRAP port."
      ::= { ztmxPDUStatistics 5 }

   ztmxInSetPdus  OBJECT-TYPE
      SYNTAX Counter
      ACCESS read-only
      STATUS mandatory
      DESCRIPTION
         "The total number of Set PDUs received by the TMUX
         process.  These are probably strayed PDUs as the TMUX
         process is bound to the TRAP port."
      ::= { ztmxPDUStatistics 6 }

   ztmxInGetResponsePdus   OBJECT-TYPE
      SYNTAX Counter
      ACCESS read-only
      STATUS mandatory
      DESCRIPTION
         "The total number of GetResponse PDUs received by the TMUX
         process.  These are probably strayed PDUs as the TMUX
         process is bound to the TRAP port."
      ::= { ztmxPDUStatistics 7 }

   ztmxInTrapPdus OBJECT-TYPE
      SYNTAX Counter
      ACCESS read-only
      STATUS mandatory
      DESCRIPTION
         "The total number of Trap PDUs received by the TMUX
         process."
      ::= { ztmxPDUStatistics 8 }

   ------------------------------------------------------------------
   -- The Trap Statistic Group                                     --
   ------------------------------------------------------------------

   ztmxTrapStatistics   OBJECT IDENTIFIER ::= { ztmxPDUStatistics 9 }

   ztmxTrapStatsCurrTime   OBJECT-TYPE
      SYNTAX DisplayString
      ACCESS read-only
      STATUS mandatory
      DESCRIPTION
         "String showing the current time."
      ::= { ztmxTrapStatistics 1 }

   ztmxInColdStartTraps OBJECT-TYPE
      SYNTAX Counter
      ACCESS read-only
      STATUS mandatory
      DESCRIPTION
         "The total number of Trap PDUs received by the TMUX process
         that report reinitiation but the configuration of the sender
         may change."
      ::= { ztmxTrapStatistics 2 }

   ztmxInWarmStartTraps OBJECT-TYPE
      SYNTAX Counter
      ACCESS read-only
      STATUS mandatory
      DESCRIPTION
         "The total number of Trap PDUs received by the TMUX process
         that report reinitiation but the configuration of the sender
         will not change."
      ::= { ztmxTrapStatistics 3 }

   ztmxInLinkDownTraps  OBJECT-TYPE
      SYNTAX Counter
      ACCESS read-only
      STATUS mandatory
      DESCRIPTION
         "The total number of Trap PDUs received by the TMUX process
         that report a failure in one of the agent's links."
      ::= { ztmxTrapStatistics 4 }

   ztmxInLinkUpTraps OBJECT-TYPE
      SYNTAX Counter
      ACCESS read-only
      STATUS mandatory
      DESCRIPTION
         "The total number of Trap PDUs received by the TMUX process
         that report one of the links has come up."
      ::= { ztmxTrapStatistics 5 }

   ztmxInAuthFailTraps  OBJECT-TYPE
      SYNTAX Counter
      ACCESS read-only
      STATUS mandatory
      DESCRIPTION
         "The total number of Trap PDUs received by the TMUX process
         that report improper authentication."
      ::= { ztmxTrapStatistics 6 }

   ztmxInEgpNeighborLossTraps OBJECT-TYPE
      SYNTAX Counter
      ACCESS read-only
      STATUS mandatory
      DESCRIPTION
         "The total number of Trap PDUs received by the TMUX process
         that report an exterior gateway protocol neighbor is lost."
      ::= { ztmxTrapStatistics 7 }

   ztmxInEnterpriseSpecificTraps OBJECT-TYPE
      SYNTAX Counter
      ACCESS read-only
      STATUS mandatory
      DESCRIPTION
         "The total number of Trap PDUs received by the TMUX process
         that report an enterprise specific event."
      ::= { ztmxTrapStatistics 8 }

   ------------------------------------------------------------------
   --                                                              --
   -- ztmxSaProcess: the Subagent Process group                    --
   --                                                              --
   ------------------------------------------------------------------

   ztmxProcCurrTime  OBJECT-TYPE
      SYNTAX DisplayString
      ACCESS read-only
      STATUS mandatory
      DESCRIPTION
         "String showing the current time."
      ::= { ztmxProcess 1 }

   ztmxProcVersion   OBJECT-TYPE
      SYNTAX DisplayString
      ACCESS read-only
      STATUS mandatory
      DESCRIPTION
         "String showing the version of the subagent."
      ::= { ztmxProcess 2 }

   ztmxProcName   OBJECT-TYPE
      SYNTAX DisplayString
      ACCESS read-only
      STATUS mandatory
      DESCRIPTION
         "String showing the process name."
      ::= { ztmxProcess 3 }

   ztmxProcPaid   OBJECT-TYPE
      SYNTAX DisplayString
      ACCESS read-only
      STATUS mandatory
      DESCRIPTION
         "String showing the process access id ('group.user')."
      ::= { ztmxProcess 4 }

   ztmxProcPrimPID   OBJECT-TYPE
      SYNTAX DisplayString
      ACCESS read-only
      STATUS mandatory
      DESCRIPTION
         "String showing the primary process PID ('CPU,PIN')."
      ::= { ztmxProcess 5 }

   ztmxProcBkupPID   OBJECT-TYPE
      SYNTAX DisplayString
      ACCESS read-only
      STATUS mandatory
      DESCRIPTION
         "String showing the backup process PID ('CPU,PIN')."
      ::= { ztmxProcess 6 }

   ztmxProcCreatTime OBJECT-TYPE
      SYNTAX DisplayString
      ACCESS read-only
      STATUS mandatory
      DESCRIPTION
         "String showing the process creation time."
      ::= { ztmxProcess 7 }

   ztmxProcCpuTime   OBJECT-TYPE
      SYNTAX DisplayString
      ACCESS read-only
      STATUS mandatory
      DESCRIPTION
         "Process CPU time."
      ::= { ztmxProcess 8 }

   ztmxProcPri OBJECT-TYPE
      SYNTAX INTEGER
      ACCESS read-write
      STATUS mandatory
      DESCRIPTION
         "Intitial process priority. Valid range 1-199"
      ::= { ztmxProcess 9 }

   ztmxProcHomeTerm  OBJECT-TYPE
      SYNTAX DisplayString
      ACCESS read-only
      STATUS mandatory
      DESCRIPTION
         "String showing the process home terminal name."
      ::= { ztmxProcess 10 }

   ztmxProcHeapInitial  OBJECT-TYPE
      SYNTAX Gauge
      ACCESS read-only
      STATUS mandatory
      DESCRIPTION
         "Intial heap size (in Bytes)."
      ::= { ztmxProcess 11 }

   ztmxProcHeapCurrent  OBJECT-TYPE
      SYNTAX Gauge
      ACCESS read-only
      STATUS mandatory
      DESCRIPTION
         "Current heap size (in Bytes)."
      ::= { ztmxProcess 12 }

   ztmxProcEmsCollector OBJECT-TYPE
      SYNTAX DisplayString
      ACCESS read-only
      STATUS mandatory
      DESCRIPTION
         "String showing the name of the EMS collector process the TMUX
         process is writing the translated EMS events to."
      ::= { ztmxProcess 13 }

   ztmxProcAgent  OBJECT-TYPE
      SYNTAX DisplayString
      ACCESS read-only
      STATUS mandatory
      DESCRIPTION
         "String showing the name of the agent process the TMUX
         process is interfacing with."
      ::= { ztmxProcess 14 }

   ztmxProcAgentSessionStatus OBJECT-TYPE
      SYNTAX  INTEGER {   open(1),
                          close(2) }
      ACCESS read-only
      STATUS mandatory
      DESCRIPTION
         "The status of the session between the TMUX process and
         the agent.  If state is not 'open' the TMUX process
         was not able to establish communication with the agent."
      ::= { ztmxProcess 15 }

   ztmxProcUdpPort   OBJECT-TYPE
      SYNTAX  INTEGER
      ACCESS read-only
      STATUS mandatory
      DESCRIPTION
         "UDP Port number the TMUX process binds to to receive TRAP
         PDUs."
      ::= { ztmxProcess 16 }

   ztmxProcTcpIpProcess OBJECT-TYPE
      SYNTAX DisplayString
      ACCESS read-only
      STATUS mandatory
      DESCRIPTION
         "String showing the name(s) of the TCP/IP process the TMUX
         process is receiving TRAP PDUs from."
      ::= { ztmxProcess 17 }

   ztmxSwitchToBackupNow   OBJECT-TYPE
      SYNTAX INTEGER { autoProcessPairControl(0),
                       forceBackupTakeover(1) }
      ACCESS read-write
      STATUS mandatory
      DESCRIPTION
         "If set to forceBackupTakeover, the backup process will take over
         and a new backup is created."
      ::= { ztmxProcess 18 }

   ztmxProcProgramFileName OBJECT-TYPE
      SYNTAX DisplayString
      ACCESS read-only
      STATUS mandatory
      DESCRIPTION
         "String showing the proram file name of the TMUX process."
      ::= { ztmxProcess 19 }

   ztmxProcEmsWriteTotal   OBJECT-TYPE
      SYNTAX  Counter
      ACCESS read-only
      STATUS mandatory
      DESCRIPTION
         "Total count of write operations to the EMS collector process.
         Each write operation attempts to send a trap event to the EMS
         collector."
      ::= { ztmxProcess 20 }

   ztmxProcEmsWriteErrors  OBJECT-TYPE
      SYNTAX  Counter
      ACCESS read-only
      STATUS mandatory
      DESCRIPTION
         "Count of write operations to the EMS collector process that
         did not complete normally.  It's likely that the trap event
         that was sent with such operation was not successfully stored
         in the EMS database."
      ::= { ztmxProcess 21 }

END -- SNMP-TMUX-MIB
