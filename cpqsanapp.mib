-- ****************************************************************************
--
--            Compaq Storage Area Networks Management Appliance
--         Management Information Base for SNMP Network Management
--
--
--      Copyright 1992-2001 Compaq Computer Corporation.
--      All Rights Reserved.
--
--      The information in this document is subject to change without notice.
--
--      COMPAQ COMPUTER CORPORATION SHALL NOT BE LIABLE FOR TECHNICAL
--      OR EDITORIAL ERRORS OR OMISSIONS CONATINED HEREIN; NOR FOR INCIDENTAL
--      OR CONSEQUENTIAL DAMAGES RESULTING FROM THE FURNISHING, PERFORMANCE,
--      OR USE OF THIS MATERIAL.
--
--      The Host OS MIB provides operating system information, such as
--      name, version, file system information, software running, and more.
--
--      The Compaq Enterprise number is 232.
--      The ASN.1 prefix to, and including the Compaq Enterprise is:
--           1.3.6.1.4.1.232
--
-- ****************************************************************************


CPQSANAPP-MIB DEFINITIONS ::= BEGIN

IMPORTS

OBJECT-TYPE FROM RFC-1212
TRAP-TYPE FROM RFC-1215
enterprises FROM RFC1155-SMI
DisplayString FROM RFC1213-MIB;

compaq           OBJECT IDENTIFIER ::= { enterprises 232 }
cpqSanAppliance  OBJECT IDENTIFIER ::= { compaq 151 }
resourceMonitor  OBJECT IDENTIFIER ::= { cpqSanAppliance 11 }

swSystemName  OBJECT-TYPE
	SYNTAX 	DisplayString (SIZE(255))
	ACCESS	read-write
	STATUS	mandatory
	DESCRIPTION
	"Fabric Element Name"
	::= { resourceMonitor 1 }

swSystemType  OBJECT-TYPE
	SYNTAX 	INTEGER {
		hsg80 (1),
		switch (2),
		appliance (3)
	}
	ACCESS	read-write
	STATUS	mandatory
	DESCRIPTION
	"Element Type Index"
	::= { resourceMonitor 2 }

swEventName  OBJECT-TYPE
	SYNTAX 	DisplayString (SIZE(255))
	ACCESS	read-write
	STATUS	mandatory
	DESCRIPTION
	"Event Name"
	::= { resourceMonitor 3 }

swFailure  OBJECT-TYPE
	SYNTAX 	DisplayString (SIZE(255))
	ACCESS	read-write
	STATUS	mandatory
	DESCRIPTION
	"Failure Description"
	::= { resourceMonitor 4 }

swSequence  OBJECT-TYPE
	SYNTAX 	INTEGER
	ACCESS	read-write
	STATUS	mandatory
	DESCRIPTION
	"Sequence Number"
	::= { resourceMonitor 5 }

swFailureTrap  TRAP-TYPE
	ENTERPRISE resourceMonitor
	VARIABLES {swSystemName, swSystemType, swEventName, swFailure, swSequence}
	DESCRIPTION
	"Failure event detected"

      --#TYPE "Failure Event"
      --#SUMMARY "Failure event detected - element %d of Type %d sent notification %d %d."
      --#ARGUMENTS {1, 2, 3, 4}
      --#SEVERITY MAJOR
      --#TIMEINDEX 99

	::= 1

swWarningTrap  TRAP-TYPE
	ENTERPRISE resourceMonitor
	VARIABLES {swSystemName, swSystemType, swEventName, swFailure, swSequence}
	DESCRIPTION
	"Warning event detected"

      --#TYPE "Warning Event"
      --#SUMMARY "Warning event detected - element %d of Type %d sent notification %d %d."
      --#ARGUMENTS {1, 2, 3, 4}
      --#SEVERITY MINOR
      --#TIMEINDEX 99

	::= 2

swInformationTrap  TRAP-TYPE
	ENTERPRISE resourceMonitor
	VARIABLES {swSystemName, swSystemType, swEventName, swFailure, swSequence}
	DESCRIPTION
	"Information event detected"

      --#TYPE "Information Event"
      --#SUMMARY "Information event detected - element %d of Type %d sent notification %d %d."
      --#ARGUMENTS {1, 2, 3, 4}
      --#SEVERITY INFORMATIONAL
      --#TIMEINDEX 99

	::= 4

END
