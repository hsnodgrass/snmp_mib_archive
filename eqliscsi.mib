-- Mib files packaged on  Thu Feb 25 14:37:59 EST 2010 for Storage Array Firmware V4.3.5 (R115269)

EQLISCSI-MIB DEFINITIONS  ::= BEGIN

   IMPORTS
   MODULE-IDENTITY, OBJECT-TYPE, OBJECT-IDENTITY, NOTIFICATION-TYPE,
   Counter32, enterprises, Integer32, Counter64, Gauge32, Unsigned32,
   TimeTicks, Opaque, experimental
   FROM SNMPv2-SMI

   TruthValue, DisplayString
   FROM  SNMPv2-TC

	iscsiSessionStatsEntry
	FROM ISCSI-MIB

    equalLogic
            FROM EQUALLOGIC-SMI
   MODULE-COMPLIANCE, OBJECT-GROUP, NOTIFICATION-GROUP
   FROM SNMPv2-CONF

   ;

eqliscsiExtModule MODULE-IDENTITY
	LAST-UPDATED "201002251937Z"
    ORGANIZATION  "EqualLogic Inc."
    CONTACT-INFO
        "Contact: Customer Support
         Postal:  EqualLogic Inc
                  9 Townsend st., Nashua, NH 03063           
         Tel:     +1 603-579-9762             
         E-mail:  support@equallogic.com
         WEB:     www.equallogic.com"

    DESCRIPTION
        "Equallogic Inc augmented ISCSI MIB module."

    REVISION "200206260000Z" -- November 19, 2002
    DESCRIPTION
        "Equallogic Inc  augmented ISCSI MIB module
         
		 Copyright (c) 2002-2004 by EqualLogic, Inc.

         All rights reserved.  This software may not be copied, disclosed,
         transferred, or used except in accordance with a license granted
         by EqualLogic, Inc.  This software embodies proprietary information
         and trade secrets of EqualLogic, Inc.
        "
    ::= { enterprises equalLogic(12740) 11 }

eqliscsiExtObjects OBJECT IDENTIFIER ::= { eqliscsiExtModule 1 }

----------------------------------------------------------------------

-- Session Stats Table

eqliscsiSessionStatsTable OBJECT-TYPE
    SYNTAX        SEQUENCE OF EqlIscsiSessionStatsEntry
    MAX-ACCESS    not-accessible
    STATUS        current
    DESCRIPTION
        "A Dynamic list of general iSCSI traffic counters for each of the
     sessions present on the system."
::= { eqliscsiExtObjects 1 }

eqliscsiSessionStatsEntry OBJECT-TYPE
    SYNTAX        EqlIscsiSessionStatsEntry
    MAX-ACCESS    not-accessible
    STATUS        current
    DESCRIPTION
        "An entry (row) containing general iSCSI traffic counters
     for a particular session."
    AUGMENTS { iscsiSessionStatsEntry }
::= { eqliscsiSessionStatsTable 1 }

EqlIscsiSessionStatsEntry ::= SEQUENCE {
   eqliscsiSsnErrorCount         Counter32,
   eqliscsiSsnTimeUp             TimeTicks,
	eqliscsiSsnTotalDataTrnsfrd	Counter32,
	eqliscsiNodeUuid			      OCTET STRING,
	eqliscsiSsnTotalDataTrnsfrd64	Counter64,
   eqliscsiSsnMembers            Opaque,
   eqliscsiSsnRouteStats         Opaque,
   eqliscsiSsnLoadValue          Unsigned32
}


eqliscsiSsnErrorCount OBJECT-TYPE
    SYNTAX        Counter32
    MAX-ACCESS    read-only
    STATUS        current
    DESCRIPTION
        "The number of errors encountered since this session was established"
::= { eqliscsiSessionStatsEntry 1 }

eqliscsiSsnTimeUp OBJECT-TYPE
    SYNTAX        TimeTicks
    MAX-ACCESS    read-only
    STATUS        current
    DESCRIPTION
        "The time in ticks that has elapsed since this session was first 
         established with the iSCSI target"
::= { eqliscsiSessionStatsEntry 2 }

eqliscsiSsnTotalDataTrnsfrd OBJECT-TYPE
    SYNTAX        Counter32
    UNITS         "KB"
    MAX-ACCESS    read-only
    STATUS        deprecated
    DESCRIPTION
        "The amount of data transfered for this session in Kilobytes.
         This number is determined by the sum of the inbound and outbound
         traffic counters."
::= { eqliscsiSessionStatsEntry 3 }

eqliscsiNodeUuid OBJECT-TYPE
    SYNTAX         OCTET STRING (SIZE (16))
    MAX-ACCESS    read-only
    STATUS        current
    DESCRIPTION
        "The UUID of the iscs"
::= { eqliscsiSessionStatsEntry 4 }

eqliscsiSsnTotalDataTrnsfrd64 OBJECT-TYPE
    SYNTAX        Counter64
    UNITS         "KB"
    MAX-ACCESS    read-only
    STATUS        deprecated
    DESCRIPTION
        "The amount of data transfered for this session in Kilobytes.
         This number is determined by the sum of the inbound and outbound
         traffic counters."
::= { eqliscsiSessionStatsEntry 5 }


eqliscsiSsnMembers OBJECT-TYPE
    SYNTAX      Opaque (SIZE (64))
    MAX-ACCESS  read-only
    STATUS      current
    DESCRIPTION "List of eligible member id's.  This is sizeof(uint32_t) * VOLUME_MAX_PSS_COUNT defined in MgmtPDU.h"
   ::= { eqliscsiSessionStatsEntry 6 }


eqliscsiSsnRouteStats OBJECT-TYPE
    SYNTAX      Opaque (SIZE (64))
    MAX-ACCESS  read-only
    STATUS      current
    DESCRIPTION "Array of the percentage of traffic being routed to each member.  This is a 1 to 1 relationship to the
                 Members array.  This is sizeof(uint32_t) * VOLUME_MAX_PSS_COUNT defined in MgmtPDU.h"
   ::= { eqliscsiSessionStatsEntry 7 }

eqliscsiSsnLoadValue OBJECT-TYPE
    SYNTAX      Unsigned32 (0..100)
    MAX-ACCESS  read-only
    STATUS      current
    DESCRIPTION "Calculated value of how busy this connection is.  0 is 100% busy, 100 is 0% busy"
    DEFVAL      {0}
   ::= { eqliscsiSessionStatsEntry 8 }


--------------------------------------------------------------------------------------

END
