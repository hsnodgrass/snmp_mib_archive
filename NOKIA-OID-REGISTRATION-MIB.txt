-- SMI Network Management Private Enterprise Codes:                            
-- 
-- Prefix: iso.org.dod.internet.private.enterprise (1.3.6.1.4.1)
--
-- Enterprise oids in 
-- ftp://ftp.isi.edu/in-notes/iana/assignments/enterprise-numbers
-- Version history
-- 30.01.1997 01 MJS Added products 8, 9 and 10. Mikko J. Salminen
-- 03.02.1997 02 MJS Name for product 9 finalized. Mikko J. Salminen
-- 05.03.1997 03 MJS nokiaDataComm changed to nokia according to permission from IANA.
--                   nokiaManufacturing branch added
--                   smd added, Mikko J. Salminen
-- 13.06.1997 04 MKi Added product 11 for SNMP Proxy for HDSL Modem Pool (A. Halonen).
--                   Contact persons being responsible for subtree added.
-- 13.06.1997 05 MKi atmVoiceDataMux to use value {nokiaProducts 20} instead of 
--                   {nokiaProducts 10} because of a mistake in object registration.
-- 14.08.1997 06 MKi nokiaTesting added { nokia 6 }. Below this branch subtrees for 
--                   testing purposes can be allocated. Commercial implementations 
--                   must not use these OIDs.
--                   nawe (Nokia Artus Wireless E-mail) added { nokiaProducts 12 }.
-- 07.10.1997 07 MKi Added nms10mfTesting branch (A. Reen)
-- 08.10.1997 08 MKi Added stTropez product branch (Neuendorff Keith (NTC/Dallas))
-- 10.10.1997 09 MKi nms10mfTesting renamed nms10Testing (A. Reen)
-- 28.10.1997 10 MKi subtree for NMS/300 MIBs added. Name of dynaModemMIB corrected.
-- 05.12.1997 11 MKi subtree for IAN2 added. 
-- 21.01.1998 12 MKi subtree for NTC Common MIB added.
-- 01.04.1998 13 MKi subtree for IAN2 testing added.
-- 27.04.1998 14 MKi subtree for ntM10, etIfRel1 and etIfRel2 added.
-- 28.04.1998 15 MKi ntM10 renamed to ntm10 as requested by J. Torkkel.
-- 27.05.1998 16 MKi ian2 renamed to ian as requested by D. Caskie.
-- 10.07.1998 17 MKi subtree for IPRG products added.
-- 03.08.1998 18 MKi subtree for BBAN added.
-- 14.08.1998 19 MKi iprgProducts renamed to ipsoProducts, begin - end clauses added.
-- 27.08.1998 20 MKi subtree for NAMP added.
-- 09.09.1998 21 MKi subtree for ggsn and nms10 products added, mpdTesting added.
-- 02.05.1999 22 MKi subtree for wirelessAccessPoint added.
-- 14.07.1999 23 MKi subtree for wireless LAN client added.
-- 03.08.1999 24 AKL subtree for ELS added.
-- 26.08.1999 25 AKL subtree for accessServer added.
-- 13.10.1999 26 AKL subtree for CG provisionally reserved and subtrees for 
--               SGSN and  Access Zone Controller (product and testing 
--               subtrees) reserved.
-- 15.10.1999 27 AKL subtree for WAP Server reserved.
-- 18.19.1999 28 AKL subtree for Nokia S30 reserved.
-- 01.12.1999 29 AKL subtree for ipTelephony reserved.
-- 18.01.2000 30 AKL subtree for MAX reserved.
-- 25.01.2000 31 AKL subtree for TWISS reserved.
-- 17.03.2000 32 AKL subtree for Nokia RFC Extensions reserved.
-- 17.08.2000 33 HBo subtree for ost and nhcTesting reserved.
-- 25.08.2000 34 HBo subtree for nsg (Nokia Service Gateway) and nsgTesting reserved.
-- 13.09.2000 35 HBo subtree for nokiaVPN reserved.
-- 04.10.2000 36 HBo subtrees for mmsc and nokiaLoopmaster reserved
-- 31.10.2000 37 HBo subtrees for nokiaSSL and nokiaAlchemyOS reserved
-- 07.11.2000 38 HBo subtrees for ipTrunk and nals (Nokia Artuse Location Server)
--                   reserved
-- 04.12.2000 39 HBo subtrees nokiaSnmpInterface and nawg (Nokia Artuse WAP Gateway)
--                   reserved
-- 05.02.2001 40 HBo subtrees for nokiaPKI, asg (Access Service Gateway),
--                   nap (Nokia Artuse Profile Directory) and mPlatform reserved
-- 15.03.2001 41 HBo subtrees for netAct4BB, nwr (Nokia Wireless Router)
--                   and nwrTesting reserved
-- 27.03.2001 42 HBo subtrees for ossLDAP reserved
--                   (OID subtree for OSS for the purposes of LDAP directory schema)
-- 03.05.2001 43 HBo subtree for dx200IptGateway reserved
-- 18.06.2001 44 HBo subtree for downloadServer reserved
-- 16.07.2001 45 HBo subtree for mPES (Mobile Position Enabling Server) reserved
-- 01.08.2001 46 HBo subtree for microWaveRadioProducts reserved
-- 02.08.2001 47 HBo subtree for app(lication)Gateway reserved
-- 22.08.2001 48 HBo subtree for pts (Personal Trusted Service) reserved
-- 30.10.2001 49 HBo subtree for nawp (Nokia Artuse Wireless Proxy) reserved
-- 26.11.2001 50 HBo subtree for flexiServerLDAP reserved
-- 27.11.2001 51 HBo subtrees for noiFaultManagment ...,
--                                noiConfigurationManagement...,
--                            and noiPerformanceManagement... reserved
-- 09.01.2002 52 HBo subtrees for noiFaultManagment ...,
--                                noiConfigurationManagement...,
--                            and noiPerformanceManagement... removed
--                   now they are defined in NOKIA-NE3S-REGISTRATION-MIB
-- 08.13.2002 53 Rupa subtrees for NIC TLS Gateway

NOKIA-OID-REGISTRATION-MIB DEFINITIONS ::= BEGIN

IMPORTS
    enterprises
        FROM RFC1155-SMI;


nokia                 OBJECT IDENTIFIER ::= { enterprises 94 }

nokiaProducts         OBJECT IDENTIFIER ::= { nokia 1 }
nokiaVars             OBJECT IDENTIFIER ::= { nokia 2 }
nokiaInterfaceModules OBJECT IDENTIFIER ::= { nokia 3 }
     -- nokiaDataComm 4 is reserved, nobody knows where (MJS)
nokiaManufacturing    OBJECT IDENTIFIER ::= { nokia 5 }
nokiaTesting          OBJECT IDENTIFIER ::= { nokia 6 }
nokiaSnmpInterface    OBJECT IDENTIFIER ::= { nokia 7 }

-- Vars section

nokiaSystem      OBJECT IDENTIFIER ::= { nokiaVars 1 }
nokiaInterface   OBJECT IDENTIFIER ::= { nokiaVars 2 }
nokiaDot1d       OBJECT IDENTIFIER ::= { nokiaVars 3 }
nokiaDot3        OBJECT IDENTIFIER ::= { nokiaVars 4 }
nokiaVirtualPort OBJECT IDENTIFIER ::= { nokiaVars 5 }
nokiaIpRouting   OBJECT IDENTIFIER ::= { nokiaVars 6 }
nokiaSnmp        OBJECT IDENTIFIER ::= { nokiaVars 7 }

dot3Rptr         OBJECT IDENTIFIER ::= { nokiaDot3 1 }

nokiaIp           OBJECT IDENTIFIER ::= { nokiaIpRouting 1 }
nokiaIcmp         OBJECT IDENTIFIER ::= { nokiaIpRouting 2 }
nokiaUdp          OBJECT IDENTIFIER ::= { nokiaIpRouting 3 }
nokiaRip          OBJECT IDENTIFIER ::= { nokiaIpRouting 4 }
nokiaArp          OBJECT IDENTIFIER ::= { nokiaIpRouting 5 }

-- Product Section

-- The product section contains the different product's
-- object identifiers.  Each product has a unique object
-- identifier allocated from this section which is referenced
-- by the sysObjectID variable from RFC1213.

-- Types of products

localBridge       OBJECT IDENTIFIER ::= { nokiaProducts 1 }
remoteBridge      OBJECT IDENTIFIER ::= { nokiaProducts 2 }
frameRelayBridge  OBJECT IDENTIFIER ::= { nokiaProducts 3 }
frameRelayBrouter OBJECT IDENTIFIER ::= { nokiaProducts 4 }
hubFamily         OBJECT IDENTIFIER ::= { nokiaProducts 5 }
lanGateway        OBJECT IDENTIFIER ::= { nokiaProducts 6 }
localBrouter      OBJECT IDENTIFIER ::= { nokiaProducts 7 }
accessManager     OBJECT IDENTIFIER ::= { nokiaProducts 8 }  -- L. Seppanen
nmsProxy          OBJECT IDENTIFIER ::= { nokiaProducts 9 }  -- M. Voipio
     -- { nokiaProducts 10 }  is not available, because it was initially reserved 
     -- for atmVoiceDataMux but the real implementation used value 20.
dynaModemMIB      OBJECT IDENTIFIER ::= { nokiaProducts 11 } -- A. Halonen
nawe              OBJECT IDENTIFIER ::= { nokiaProducts 12 } -- J. Soitinaho, nawe =
                                                             -- Nokia Artus Wireless E-mail
stTropez          OBJECT IDENTIFIER ::= { nokiaProducts 13 } -- Nancy Martinez, Dallas
nms300            OBJECT IDENTIFIER ::= { nokiaProducts 14 } 
ian               OBJECT IDENTIFIER ::= { nokiaProducts 15 } -- Dorna Caskie, Boston
ntcCommon         OBJECT IDENTIFIER ::= { nokiaProducts 16 } -- Mika Kiikkila
ntm10             OBJECT IDENTIFIER ::= { nokiaProducts 17 } -- Jari Torkkel
etIfRel1          OBJECT IDENTIFIER ::= { nokiaProducts 18 } -- Jari Torkkel
etIfRel2          OBJECT IDENTIFIER ::= { nokiaProducts 19 } -- Jari Torkkel
atmVoiceDataMux   OBJECT IDENTIFIER ::= { nokiaProducts 20 } -- H. Helokunnas
ipsoProducts      OBJECT IDENTIFIER ::= { nokiaProducts 21 } -- Dan Myers
bban              OBJECT IDENTIFIER ::= { nokiaProducts 22 } -- Andreas Terstegge, DPD
namp              OBJECT IDENTIFIER ::= { nokiaProducts 23 } -- J. Soitinaho
ggsn              OBJECT IDENTIFIER ::= { nokiaProducts 24 } -- Timo Holopainen
nms10             OBJECT IDENTIFIER ::= { nokiaProducts 25 } -- A. Reen
wirelessAccessPoint  OBJECT IDENTIFIER ::= {nokiaProducts 26 } -- Simon Black
wirelessLANclient OBJECT IDENTIFIER ::= { nokiaProducts 27 } -- Simon Black
els               OBJECT IDENTIFIER ::= { nokiaProducts 28 } -- Mimmi Lai, els =
							     -- Entry Level System
accessServer      OBJECT IDENTIFIER ::= { nokiaProducts 29 } -- Pekka Valipirtti
cg                OBJECT IDENTIFIER ::= { nokiaProducts 30 } -- Jussi Sorvali (protem)
sgsn              OBJECT IDENTIFIER ::= { nokiaProducts 31 } -- Timo Holopainen       
azc               OBJECT IDENTIFIER ::= { nokiaProducts 32 } -- Pekka Manner
wapServer         OBJECT IDENTIFIER ::= { nokiaProducts 33 } -- Mauno Pasanen
s30               OBJECT IDENTIFIER ::= { nokiaProducts 34 } -- Jari Selenius
ipTelephony       OBJECT IDENTIFIER ::= { nokiaProducts 35 } -- Jian Song
max               OBJECT IDENTIFIER ::= { nokiaProducts 36 } -- Eduardo Fernandez
twiss             OBJECT IDENTIFIER ::= { nokiaProducts 37 } -- Mika Lundstrom
nokiaRFCExtensions OBJECT IDENTIFIER ::= { nokiaProducts 38 } -- Henry Haverinen
ost               OBJECT IDENTIFIER ::= { nokiaProducts 39 } -- Rickard Westman, NHC
nsg               OBJECT IDENTIFIER ::= { nokiaProducts 40 } -- Sajith Mohamed
nokiaVPN          OBJECT IDENTIFIER ::= { nokiaProducts 41 } -- Jonny Larson, Nokia Internet Communications
mmsc              OBJECT IDENTIFIER ::= { nokiaProducts 42 } -- Jouni.M Piirainen
nokiaLoopmaster   OBJECT IDENTIFIER ::= { nokiaProducts 43 } -- Richard S. Walker
nokiaSSL          OBJECT IDENTIFIER ::= { nokiaProducts 44 } -- Brian Baker
nokiaAlchemyOS    OBJECT IDENTIFIER ::= { nokiaProducts 45 } -- Jonny Larson
nals              OBJECT IDENTIFIER ::= { nokiaProducts 46 } -- Weimin Tsai
ipTrunk           OBJECT IDENTIFIER ::= { nokiaProducts 47 } -- Ari Kesti
nawg              OBJECT IDENTIFIER ::= { nokiaProducts 48 } -- Helena Kytomaki
nokiaPKI          OBJECT IDENTIFIER ::= { nokiaProducts 49 } -- Jorrit de Groot
asg               OBJECT IDENTIFIER ::= { nokiaProducts 50 } -- Joerg Rockel
nap               OBJECT IDENTIFIER ::= { nokiaProducts 51 } -- Helena Kytomaki
mPlatform         OBJECT IDENTIFIER ::= { nokiaProducts 52 } -- Nhan H. Trinh
netAct4BB         OBJECT IDENTIFIER ::= { nokiaProducts 53 } -- Jorma Huttunen
nwr               OBJECT IDENTIFIER ::= { nokiaProducts 54 } -- Gyula Kun-Szabo
ossLDAP           OBJECT IDENTIFIER ::= { nokiaProducts 55 } -- Jori Aro
dx200IptGateway   OBJECT IDENTIFIER ::= { nokiaProducts 56 } -- Ari Kesti
downloadServer    OBJECT IDENTIFIER ::= { nokiaProducts 57 } -- Jukka Heiska
mPES              OBJECT IDENTIFIER ::= { nokiaProducts 58 } -- Weimin Tsai
microWaveRadioProducts OBJECT IDENTIFIER ::= { nokiaProducts 59 } -- Andre Wardaschka
appGateway        OBJECT IDENTIFIER ::= { nokiaProducts 60 } -- Stanislav Paltis, Vikas Chawla
pts               OBJECT IDENTIFIER ::= { nokiaProducts 61 } -- Pasi Hamalainen
nawp              OBJECT IDENTIFIER ::= { nokiaProducts 62 } -- Jeff Niemann
flexiServerLDAP   OBJECT IDENTIFIER ::= { nokiaProducts 63 } -- Pasi Raasakka
nokiaTLSGateway   OBJECT IDENTIFIER ::= { nokiaProducts 64 } -- Jonny Larson

-- New products will be added to the end of this list.


-- Types of manufacturing system
-- Jouko Leppaniemi/NMP in charge of this subtree
smd       OBJECT IDENTIFIER ::= { nokiaManufacturing 1 }


-- Testing Section

-- Testing section contains interim object identifiers
-- needed for testing purposes. These OIDs must not be used by 
-- commercial products.

nms300Testing     OBJECT IDENTIFIER ::= { nokiaTesting 1 }  -- M. Voipio
nms10Testing      OBJECT IDENTIFIER ::= { nokiaTesting 2 }  -- A. Reen
ianTesting        OBJECT IDENTIFIER ::= { nokiaTesting 3 }  -- Dorna Caskie, Boston
mpdTesting        OBJECT IDENTIFIER ::= { nokiaTesting 4 }  -- Jouni Pirhonen, MPD/FAS
wirelessAPTesting OBJECT IDENTIFIER ::= { nokiaTesting 5 }  -- Simon Black
azTesting	  OBJECT IDENTIFIER ::= { nokiaTesting 6 }  -- Pekka Manner
nhcTesting	  OBJECT IDENTIFIER ::= { nokiaTesting 7 }  -- Rickard Westman, NHC
nsgTesting	  OBJECT IDENTIFIER ::= { nokiaTesting 8 }  -- Sajith Mohamed
asgTesting        OBJECT IDENTIFIER ::= { nokiaTesting 9 }  -- Joerg Rockel
mPlatformTesting  OBJECT IDENTIFIER ::= { nokiaTesting 10 } -- Nhan H. Trinh
nwrTesting        OBJECT IDENTIFIER ::= { nokiaTesting 11 } -- Gyula Kun-Szabo

END
