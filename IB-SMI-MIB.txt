--
-- Copyright (c) 2004-2005, Infoblox, Inc
-- All rights reserved.

IB-SMI-MIB DEFINITIONS ::= BEGIN

--
-- Imports
--

IMPORTS MODULE-IDENTITY, OBJECT-TYPE, enterprises
		        FROM SNMPv2-SMI 
        TEXTUAL-CONVENTION
		        FROM SNMPv2-TC;

--
-- Module Identity
--        

infoblox MODULE-IDENTITY
         LAST-UPDATED  "200501100000Z"  --  Jan 10, 2005
         ORGANIZATION  "Infoblox"
         CONTACT-INFO  "Infoblox
                        475 Potrero Drive
                        Sunnyvale, CA 94085
                        1-888-463-6259
	                support@infoblox.com"
         DESCRIPTION
           "This is the MIB module for object type definitions
	    that are used throughout the infoblox enterprise MIBs."

         REVISION  "200501100000Z"  --  Jan 10, 2005
         DESCRIPTION   "Added copyright"
                                                                                                
         REVISION  "200405210000Z"  --  May 21, 2004
         DESCRIPTION   "Creation of the MIB file"
                                                                                                
         ::= {  enterprises  7779  }
 
ibSNMP        OBJECT IDENTIFIER ::= { infoblox 3 }  -- oid for SNMP tree
ibProduct     OBJECT IDENTIFIER ::= { ibSNMP 1 }
ibOne         OBJECT IDENTIFIER ::= { ibProduct 1 }
ibTrapOne     OBJECT IDENTIFIER ::= { ibOne 1 }
ibPlatformOne OBJECT IDENTIFIER ::= { ibOne 2 }
ibDNSOne      OBJECT IDENTIFIER ::= { ibOne 3 }
ibDHCPOne     OBJECT IDENTIFIER ::= { ibOne 4 }
ibRADIUSOne   OBJECT IDENTIFIER ::= { ibOne 6 }

IbString ::= TEXTUAL-CONVENTION
   DISPLAY-HINT  "255a"
   STATUS        current
   DESCRIPTION   "A text string with 255 octets"
   SYNTAX        OCTET STRING (SIZE (0..255))

IbNode ::= TEXTUAL-CONVENTION
   STATUS        current
   DESCRIPTION   "A node name string"
   SYNTAX        OCTET STRING (SIZE (0..127))
                                                                                
IbIpAddr ::= TEXTUAL-CONVENTION
   STATUS        current
   DESCRIPTION   "An Ip address in xxx.xxx.xxx.xxx notation"
   SYNTAX        OCTET STRING (SIZE(0..16))

END
