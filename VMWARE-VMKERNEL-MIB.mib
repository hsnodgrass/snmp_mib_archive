-- **********************************************************
-- Copyright 2007 VMware, Inc.  All rights reserved. 
-- 
--  This MIB Module provides definitions vmkernel related
--  management.
--
-- **********************************************************
-- Version 1.0

VMWARE-VMKERNEL-MIB DEFINITIONS ::= BEGIN

IMPORTS
    OBJECT-TYPE
        FROM RFC-1212
   DisplayString 
      FROM RFC1213-MIB
  vmwProductSpecific
        FROM VMWARE-ROOT-MIB
   vmwESX
      FROM VMWARE-PRODUCTS-MIB;


esxVMKernel OBJECT IDENTIFIER ::= { vmwESX 1 }

vmkLoaded OBJECT-TYPE 
   SYNTAX      DisplayString
   ACCESS      read-only
   STATUS      mandatory
   DESCRIPTION
      "Has the vmkernel been loaded? (yes/no)"
   ::= { esxVMKernel 1 }

END
