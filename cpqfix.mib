-- 
-- 
--
-- MIB: CPQFIX
-- --------------------------------------------------------------
-- Description: Used to map variations of RFC1215-MIB and RFC1213-MIB
-- --------------------------------------------------------------
--
        RFC-1215 DEFINITIONS ::= BEGIN
	END

        RFC1215 DEFINITIONS ::= BEGIN
	END

        RFC-1213 DEFINITIONS ::= BEGIN
	END
