-- File: xylo-trpobj.mib
--
--	Bay Networks Private Enterprise Remote Annex MIB
--
--  Copyright 1997 Bay Networks, Inc.  ALL RIGHTS RESERVED.
--
--  ALL RIGHTS RESERVED. Licensed Material - Property of Bay Networks, Inc.
--  This software is made available solely pursuant to the terms of a
--  software license agreement which governs its use.
--  Unauthorized duplication, distribution or sale are strictly prohibited.
--
--  This information is subject to change without notice, and should
--  not be construed as a commitment by Bay Networks, Inc.  Bay Networks, Inc.,
--  assumes no responsibility for any errors that may appear in this
--  document.
--
--  $Id: 
--
-- overview

-- This module defines RAC trap related MIB groups for the Bay Networks
-- RAC product line.

  XYLO-TRAPOBJECTS-MIB DEFINITIONS ::= BEGIN

  IMPORTS
		IpAddress 
			FROM RFC1155-SMI
		DisplayString
			FROM RFC1213-MIB
		OBJECT-TYPE
			FROM RFC-1212
		wanTrapObj, modemTrapObj, callmgmtTrapObj, 
		genericTrapObj, anxTrapHostInfo
			FROM XYLO-MIB-SMI;


--  xylogics		OBJECT IDENTIFIER ::= { enterprises 15 } 
--  racTrap		OBJECT IDENTIFIER ::= { xylogics 100 }
--  racTrapObjects	OBJECT IDENTIFIER ::= { racTrap 1 }
--  wanTrapObj	  	OBJECT IDENTIFIER ::= { racTrapObjects 1 }
--  modemTrapObj	OBJECT IDENTIFIER ::= { racTrapObjects 2 }
--  callmgmtTrapObj	OBJECT IDENTIFIER ::= { racTrapObjects 3 }
--  genericTrapObj      OBJECT IDENTIFIER ::= { racTrapObjects 4 }
--  anxTrapHostInfo	OBJECT IDENTIFIER ::= { annex 10 }


-- WAN trap related object definition.

	wanBpvThreshold OBJECT-TYPE
		SYNTAX	INTEGER (0..65535)
		ACCESS	read-write
		STATUS	mandatory
		DESCRIPTION
			"The threshold which, when met or exceeded,
			triggers the wanBpvThreshTrap to be sent.
                        Setting this object to zero (0) disables the trap.

                        This object corresponds to NA/admin
                        parameter bpv_threshold."
		::= { wanTrapObj 1 }

	wanOofThreshold OBJECT-TYPE
		SYNTAX	INTEGER (0..65535)
		ACCESS	read-write
		STATUS	mandatory
		DESCRIPTION
			"The threshold which, when met of exceeded,
			triggers the wanOofThreshTrap to be sent.
                        Setting this object to zero (0) disables the trap.

                        This object corresponds to NA/admin
                        parameter oof_threshold."
		::= { wanTrapObj 2 }

        wanEsThreshold	OBJECT-TYPE
		SYNTAX	INTEGER (0..65535)
		ACCESS	read-write
		STATUS	mandatory
		DESCRIPTION
			"The threshold which, when met or exceeded,
			triggers the wanEsThreshTrap to be sent.
                        Setting this object to zero (0) disables the trap.
 
                        This object corresponds to NA/admin
                        parameter es_threshold."
		::= { wanTrapObj 3 }

	wanCvThreshold OBJECT-TYPE
		SYNTAX  INTEGER (0..65535)
		ACCESS  read-write
		STATUS  mandatory
		DESCRIPTION
			"The threshold which, when met or exceeded, triggers the
			wanCvThreshtrap to be sent.  Setting this object to zero (0)
                        disables the trap.
 
                        This object corresponds to NA/admin
                        parameter cv_threshold."
		 ::= { wanTrapObj 4 }

	wanEsfThreshold OBJECT-TYPE
		SYNTAX  INTEGER (0..65535)
		ACCESS  read-write
		STATUS  mandatory
		DESCRIPTION
			"The threshold which, when met or exceeded, triggers the
			wanEsfThreshTrap to be sent.  Setting this object to zero (0)
                        disables the trap.
 
                        This object corresponds to NA/admin
                        parameter esf_threshold."
		 ::= { wanTrapObj 5 }
 
	wanSesThreshold OBJECT-TYPE
		SYNTAX  INTEGER (0..65535)
		ACCESS  read-write
		STATUS  mandatory
		DESCRIPTION
			"The threshold which, when met or exceeded, triggers the
			wanSesThreshTrap to be sent.  Setting this object to zero (0)
                        disables the trap.
 
                        This object corresponds to NA/admin
                        parameter ses_threshold."
		 ::= { wanTrapObj 6 }

	wanUasThreshold OBJECT-TYPE
		SYNTAX  INTEGER (0..65535)
		ACCESS  read-write
		STATUS  mandatory
		DESCRIPTION
			"The threshold which, when met or exceeded, triggers the
			wanUasThreshTrap to be sent.  Setting this object to zero (0)
                        disables the trap.
 
                        This object corresponds to NA/admin
                        parameter uas_threshold."
		 ::= { wanTrapObj 7 }

	wanBesThreshold OBJECT-TYPE
		SYNTAX  INTEGER (0..65535)
		ACCESS  read-write
		STATUS  mandatory
		DESCRIPTION
			"The threshold which, when met or exceeded, triggers the
			wanBesThreshTrap to be sent.  Setting this object to zero (0)
                        disables the trap.
 
                        This object corresponds to NA/admin
                        parameter bes_threshold."
		 ::= { wanTrapObj 8 }

	wanLofcThreshold OBJECT-TYPE
		SYNTAX  INTEGER (0..65535)
		ACCESS  read-write
		STATUS  mandatory
		DESCRIPTION
			"The threshold which, when met or exceeded, triggers the
			wanLofcThreshTrap to be sent.  Setting this object to zero (0)
                        disables the trap.
 
                        This object corresponds to NA/admin
                        parameter lofc_threshold."
		 ::= { wanTrapObj 9 }

	wanCssThreshold OBJECT-TYPE
		SYNTAX  INTEGER (0..65535)
		ACCESS  read-write
		STATUS  mandatory
		DESCRIPTION
			"The threshold which, when met or exceeded, triggers the
			wanCssThreshTrap to be sent.  Setting this object to zero (0)
                        disables the trap.
 
                        This object corresponds to NA/admin
                        parameter css_threshold."
		 ::= { wanTrapObj 10 }

	ds0ErrorThreshold OBJECT-TYPE
		SYNTAX  INTEGER (0..65535)
		ACCESS  read-write
		STATUS  mandatory
		DESCRIPTION
			"This object defines the threshold for the number
			of consecutive calls that the ds0 fails to accept
			after which the ds0ErrorTrap is sent to the trap
			host(s).  Setting this object to zero (0) disables
			the trap

			This object corresponds to the na/admin parameter
			ds0_error_threshold."
		 ::= { wanTrapObj 11 }

-- Modem trap related object definition.

  mdmErrorTrapThresh	OBJECT-TYPE
		SYNTAX	INTEGER (0..65535)
		ACCESS	read-write
		STATUS	mandatory
		DESCRIPTION
			"This object defines the threshold for number of
			consecutive calls that the modem fails to accept after
			which the modem is busied out and wanMdmErrorThreshTrap
			is sent to the trap host(s). Setting this object to
			zero, disables the trap. Default is zero (disable).
			This object corresponds to modem_error_threshold
			NA/admin parameter."
		::= { modemTrapObj 1 }

-- Call management trap related object definition.
	callBeginTrapObj	OBJECT-TYPE
		SYNTAX	INTEGER {
				enable(1),
				disable(2)
				}
		ACCESS	read-write
		STATUS	mandatory
		DESCRIPTION
		"This object controls the callBeginTrap trap 
		generation by the RAC. Setting this object to
		disable, the RAC will not generate the callBeginTrap
		trap. Default is disable(2).
		This object corresponds to call_begin_trap NA/admin
		parameter."
		::= { callmgmtTrapObj 1 }
	
	callEndTrapThresh	OBJECT-TYPE
			SYNTAX	INTEGER (0..255)
			ACCESS	read-write
			STATUS	mandatory
			DESCRIPTION
			"This object controls the callEndTrap trap 
			generation by the RAC. Setting this object to
			zero (default) will disable the trap generation.
  			Setting this object to a value other than zero,
                        the RAC will generate the callEndTrap after than
 			many calls has terminated. A call that has failed
			to connect is considered a terminated call with
			appropriate disconnect reason. This object can
			be used by the manager entity to retrieve the
			terminated call information from the call history
			MIB table. Default value is zero.
			This object corresponds to call_end_trap_inc NA/admin
			parameter."
			::= { callmgmtTrapObj 2 }
	
	
	unexpectDisconnectTrapThresh	OBJECT-TYPE
			SYNTAX	INTEGER (0..255)
			ACCESS	read-write
			STATUS	mandatory
			DESCRIPTION
			"This object controls the unexpectDisconnectTrap 
			trap generation by the RAC. Setting this object to
			zero (default) will disable the trap generation.
			Setting this object to a value other than zero,
			the RAC will generate the unexpectDisconnectTrap 
			after that many calls has terminated unexpectedly. 
			A call is considered to have disconnected 
			unexpectedly is the call disconnect reason is:
			protocolError, localHangup, timeoutHDLC, 
			maxLogonTimeout OR if the call is handled by a modem 
			and the modem disconnect reason is : 
			poorSignalQ, failRetrain.
			This object corresponds to unexpected_trap_inc NA/admin
			parameter."
		::= { callmgmtTrapObj 3 }
	
	forcedCallDisconnectTrapThresh	OBJECT-TYPE
			SYNTAX	INTEGER (0..255)
			ACCESS	read-write
			STATUS	mandatory
			DESCRIPTION
			"This object controls the forcedCallDisconnectTrap
			trap generation by the RAC. Setting this object to
			zero (default) will disable the trap generation.
			Setting this object to a value other than zero,
			the RAC will generate the forcedCallDisconnectTrap
			after that many calls has terminated due to timeouts. 
			The RAC has the following timers and setting off either
			of these timers will generate the trap. The timers are:
			cliInactivityTimeout - the amount of time in minutes 
			that the RAC (system) waits before hanging up 
			the call. This is valid if the session is in 
			CLI mode. Not applicable for any other 
			sessions (PPP etc). The value of the timer is 
			determined by the object, gpTimerCliInactivity.
			inactivityTimeout - the amount of time in minutes that
			the RAC waits before hanging up the call. The 
			timer is independent of the mode of the 
			session. The value of the timer is determined 
			by the object, gpTimerInactivityTimer.
			netInactivityTimeout - this is similar to the 
			inactivity timeout.
			This object corresponds to forced_call_inc
			NA/admin parameter."
		::= { callmgmtTrapObj 4 }

-- generic traps. One of a kind trap objects.
	
  diallnkTrpEna OBJECT-TYPE
                SYNTAX INTEGER {
                        enabled(1),
                        disabled(2)
                }
                ACCESS read-write
                STATUS mandatory
                DESCRIPTION
                        "When enabled, SNMP link up/down traps are generated 
			for remote dialin interfaces."
                ::= { genericTrapObj 1 }


-- Trap host information.  The contents of this group determine 
-- which hosts will received the traps generated by the Annex.
-- Up to four trap hosts can be defined by reading the config.annex
-- file during boot.  When adding trap hosts at boot time, the
-- first community name in the known communities table is used
-- for all entries in this table.  The status is set to valid, 
-- and the aging interval is disabled.  A manager may then alter
-- these defaults if desired.  Changes to the trap host table
-- are not saved when the Annex is rebooted.

  
  anxTrapHostMax OBJECT-TYPE
          SYNTAX    INTEGER (0..10)
          ACCESS    read-only
          STATUS    mandatory
          DESCRIPTION
               "The maximum number of rows in the trap host table."
          ::= { anxTrapHostInfo 1 }

  anxTrapHostCurEnt OBJECT-TYPE
          SYNTAX    INTEGER (0..10)
          ACCESS    read-only
          STATUS    mandatory
          DESCRIPTION
               "The current number of rows in the trap host table."
          ::= { anxTrapHostInfo 2 }

  anxTrapHostNext OBJECT-TYPE
          SYNTAX    INTEGER (0..10)
          ACCESS    read-only
          STATUS    mandatory
          DESCRIPTION
               "The index of the next available row to be created 
	       in the trap host table. A value of zero means that 
	       the table is full and no more rows can be added."
          ::= { anxTrapHostInfo 3 }

  anxTrapHostTable OBJECT-TYPE
          SYNTAX    SEQUENCE OF AnxTrapHostEntry
          ACCESS    not-accessible
          STATUS    mandatory
          DESCRIPTION
               "A table of managers which to send traps."
          ::= { anxTrapHostInfo 4 }

  anxTrapHostEntry OBJECT-TYPE
          SYNTAX    AnxTrapHostEntry
          ACCESS    not-accessible
          STATUS    mandatory
          DESCRIPTION
               "A row in the trap host table.  The column 
	       anxTrapHostStatus is used to create and delete rows 
	       in the table.  Creation requires a SET PDU with 
	       objects anxTrapHostStatus, anxTrapHostAddrType,
               anxTrapHostNetAddr, and anxTrapHostCommunity
               for the new row."
          INDEX     { anxTrapHostIndex }
          ::= { anxTrapHostTable 1 }

  AnxTrapHostEntry ::= SEQUENCE {
     anxTrapHostIndex      INTEGER,
     anxTrapHostStatus     INTEGER,
     anxTrapHostAddrType   INTEGER,
     anxTrapHostNetAddr    OCTET STRING,
     anxTrapHostComm       OCTET STRING,
     anxTrapHostAgeTime    INTEGER,
     anxTrapHostPortNumber	   INTEGER,
     anxTrapHostGrouping	INTEGER
     }

  anxTrapHostIndex OBJECT-TYPE
          SYNTAX    INTEGER (1..10)
          ACCESS    read-only
          STATUS    mandatory
          DESCRIPTION
               "The index of the row in the table."
          ::= { anxTrapHostEntry 1 }

  anxTrapHostStatus OBJECT-TYPE
          SYNTAX    INTEGER {
              other(1),
              valid(2),
              ignore(3),
              delete(4),
              create(5)
              }
          ACCESS    read-write
          STATUS    mandatory
          DESCRIPTION
               "This object is used to create and delete rows in 
	       the table and control if they are used. The values
               that can be written are:
		 valid(2)....if the current status is ignore(3),
			     re-enable this entry for sending
			     traps again
                 ignore(3)...don't use this entry to
                             send traps at this time
                 delete(4)...deletes the row
                 create(5)...creates a new row

               If the row exists, then a SET with value of create(5) 
	       returns error 'badValue'. Deleted rows go away
               immediately. The following values can be returned on reads:
                 other(1)....some other case
                 valid(2)....the row exists and is valid
                 ignore(3)...don't use this entry to
                             send traps at this time"
          ::= { anxTrapHostEntry 2 }

  anxTrapHostAddrType OBJECT-TYPE
          SYNTAX    INTEGER {
              ip(1)
              }
          ACCESS    read-write
          STATUS    mandatory
          DESCRIPTION
               "The type of address that is stored in the object 
	       anxTrapHostNetAddr. The value is:
                 ip(1)...IP address"
          ::= { anxTrapHostEntry 3 }

  anxTrapHostNetAddr OBJECT-TYPE
          SYNTAX    OCTET STRING
          ACCESS    read-write
          STATUS    mandatory
          DESCRIPTION
               "The network address (in network order) for SNMP 
	       manager that is to receive the trap."
          ::= { anxTrapHostEntry 4 }

  anxTrapHostComm OBJECT-TYPE
          SYNTAX    OCTET STRING (SIZE(0..20))
          ACCESS    read-write
          STATUS    mandatory
          DESCRIPTION
               "The community string to use when sending a trap
	       to this host."
          ::= { anxTrapHostEntry 5 }

  anxTrapHostAgeTime OBJECT-TYPE
          SYNTAX    INTEGER
          ACCESS    read-write
          STATUS    mandatory
          DESCRIPTION
               "The time interval in seconds used to age entries out 
	       of the trap receiver table. The default value if not 
	       specified will be 0, or infinite,never to be aged out."
          DEFVAL { 0 }
          ::= { anxTrapHostEntry 6 }

  anxTrapHostPortNumber OBJECT-TYPE
          SYNTAX    INTEGER
          ACCESS    read-write
          STATUS    mandatory
          DESCRIPTION
		"The port number to send the trap to. If this is not
		enetered the port will default to 162"
          ::= { anxTrapHostEntry 7 }

  anxTrapHostGrouping OBJECT-TYPE
          SYNTAX    INTEGER (1..65535)
          ACCESS    read-write
          STATUS    mandatory
          DESCRIPTION
		"A bitmask that will associate the trp host entry
		with one or more trap groupings:
		none		0x00000000
		startup		0x00000001
		connection	0x00000002
		wan		0x00000004
		call-accounting	0x00000008
		ospf		0x00000010
		all		0xffffffff"
          ::= { anxTrapHostEntry 8 }

-- Following objects are used by xylogics trap generated by ACP host.
-- They are defined here.

  anxTrapUserName	OBJECT-TYPE
			SYNTAX	DisplayString (SIZE (0..128))
			ACCESS	read-only
			STATUS	mandatory
			DESCRIPTION
				"A string defining the user name under attack."
			::= { anxTrapHostInfo 5 }

  anxTrapPortIndex	OBJECT-TYPE
			SYNTAX	INTEGER
			ACCESS	read-only
			STATUS	mandatory
			DESCRIPTION
				"A unique number from 1 to totalPorts that
			identifies the port under attack."
			::= { anxTrapHostInfo 6 }

  anxTrapPortType	OBJECT-TYPE
			SYNTAX	INTEGER {
					async(1),
					sync(2),
					virtual(3),
					dialout(4),
					ethernet(5),
					rfc(6)
				}
			ACCESS	read-only
			STATUS	mandatory
			DESCRIPTION
				"A enumerated string that identifies the
			port type under attack."
			::= { anxTrapHostInfo 7 }

  anxTrapInetAddr	OBJECT-TYPE
			SYNTAX	IpAddress
			ACCESS	read-only
			STATUS	mandatory
			DESCRIPTION
				"The Internet address of the Annex."
			::= { anxTrapHostInfo 8 }


  anxTrapAttackErrcode	OBJECT-TYPE
			SYNTAX INTEGER {
			maxThreshold(1),
			timeThreshold(2)
			}
		ACCESS read-only
		STATUS mandatory
		DESCRIPTION
			"Error code indicating the threshold reached under
			following circumstances.
			maxThreshold(1) - User has exceeded the threshold
					  for consecutive number of attempts
					  to log-in.
			timeThreshold(2) - User has exceeded the threshold 
					  for number of log-in failure
					  over a pre-defined period."
			::= { anxTrapHostInfo 9 }

  anxTrapAttackErrmsg OBJECT-TYPE
		SYNTAX DisplayString (SIZE (0..128))
		ACCESS read-only
		STATUS mandatory
		DESCRIPTION
			"Error message string."
			::= { anxTrapHostInfo 10 }

  anxTrapDbErrcode	OBJECT-TYPE
			SYNTAX INTEGER {
			read-error(1),
			write-error(2),
			protect-error(3)
			}
		ACCESS read-only
		STATUS mandatory
		DESCRIPTION
			"Error code indicating the type of error occured
			when ERPCD tried to access the database.
		   read-error(1)    - ERPCD cannot read the database
                   write-error(2)   - ERPCD cannot write to the database
                   protect-error(3) - ERPCD detects wrong database protection."
			::= { anxTrapHostInfo 11 }


  anxTrapDbErrmsg OBJECT-TYPE
		SYNTAX DisplayString (SIZE (0..128))
		ACCESS read-only
		STATUS mandatory
		DESCRIPTION
			"Error message string giving details about the
			error when ERPCD tried to access the database."
			::= { anxTrapHostInfo 12 }

  trapModemMsg		OBJECT-TYPE
			SYNTAX	DisplayString (SIZE (0..128))
			ACCESS	read-only
			STATUS	mandatory
			DESCRIPTION
				"This object is send along with the modem 
				busy out trap. This object specifies the 
				modem which is being busied out and the 
				reason for busying out the modem."
			::= { anxTrapHostInfo 13 }

  operImageModemImage  	        OBJECT-TYPE
                        	SYNTAX  DisplayString (SIZE (0..128))
                        	ACCESS  read-only
                        	STATUS  mandatory
                        	DESCRIPTION
                       		"This is a trap indicating the operational 
				image version and the modem image version."  
			::= { anxTrapHostInfo 14 }

  wanVersion		        OBJECT-TYPE
                        	SYNTAX  DisplayString (SIZE (0..128))
                        	ACCESS  read-only
                        	STATUS  mandatory
                        	DESCRIPTION
                       		"This trap indicates that a  wan has come
				 up and also the version string for that wan." 
			::= { anxTrapHostInfo 15 }


  trapAfdMsg		OBJECT-TYPE
			SYNTAX	DisplayString (SIZE (0..128))
			ACCESS	read-only
			STATUS	mandatory
			DESCRIPTION
				"This object is sent along with the 
				afd catastrophic trap. This object specifies
				the wan module which is inoperable"
			::= { anxTrapHostInfo 18 }

END
