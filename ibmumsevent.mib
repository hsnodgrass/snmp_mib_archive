UMSEVENT-MIB DEFINITIONS ::= BEGIN

IMPORTS
   OBJECT-TYPE
      FROM RFC-1212

   TRAP-TYPE
      FROM RFC-1215

   director,ibmpsg, ibmpsgEvent,
   Boolean, Uint8, Sint8, Uint16, Sint16, Uint32,
   Sint32, Uint64, Sint64, Real32, Real64, String, Datetime
      FROM UMS-MIB;


iBMPSGGenericEventBindings OBJECT IDENTIFIER ::= { ibmpsgEvent 1 }

iBMPSGGenericEventIdentifier OBJECT-TYPE
   SYNTAX         String
   ACCESS         read-write
   STATUS         mandatory
   DESCRIPTION    "iBMPSGGenericEventIdentifier"
   REFERENCE      "IBMPSG_GenericEvent.Identifier"
::= { iBMPSGGenericEventBindings 1 }

iBMPSGGenericEventSourceObjectPath OBJECT-TYPE
   SYNTAX         String
   ACCESS         read-write
   STATUS         mandatory
   DESCRIPTION    "iBMPSGGenericEventSourceObjectPath"
   REFERENCE      "IBMPSG_GenericEvent.SourceObjectPath"
::= { iBMPSGGenericEventBindings 2 }

iBMPSGGenericEventTargetObjectPath OBJECT-TYPE
   SYNTAX         String
   ACCESS         read-write
   STATUS         mandatory
   DESCRIPTION    "iBMPSGGenericEventTargetObjectPath"
   REFERENCE      "IBMPSG_GenericEvent.TargetObjectPath"
::= { iBMPSGGenericEventBindings 3 }

iBMPSGGenericEventdescription OBJECT-TYPE
   SYNTAX         String
   ACCESS         read-write
   STATUS         mandatory
   DESCRIPTION    ""
   REFERENCE      "IBMPSG_GenericEvent.description"
::= { iBMPSGGenericEventBindings 4 }

iBMPSGGenericEventSeverity OBJECT-TYPE
   SYNTAX         Uint16
   ACCESS         read-write
   STATUS         mandatory
   DESCRIPTION    "iBMPSGGenericEventdescription"
   REFERENCE      "IBMPSG_GenericEvent.Severity"
::= { iBMPSGGenericEventBindings 5 }

iBMPSGGenericEventTimeStamp OBJECT-TYPE
   SYNTAX         Datetime
   ACCESS         read-write
   STATUS         mandatory
   DESCRIPTION    "iBMPSGGenericEventTimeStamp"
   REFERENCE      "IBMPSG_GenericEvent.TimeStamp"
::= { iBMPSGGenericEventBindings 6 }

iBMPSGGenericEvent TRAP-TYPE
   ENTERPRISE     ibmpsg
   VARIABLES    {
      iBMPSGGenericEventIdentifier,
      iBMPSGGenericEventSourceObjectPath,
      iBMPSGGenericEventTargetObjectPath,
      iBMPSGGenericEventdescription,
      iBMPSGGenericEventSeverity,
      iBMPSGGenericEventTimeStamp
   }
   DESCRIPTION    "Placeholder event"
   REFERENCE      "IBMPSG_GenericEvent"
::= 1


iBMPSGTemperatureEventBindings OBJECT IDENTIFIER ::= { ibmpsgEvent 2 }

iBMPSGTemperatureEventIdentifier OBJECT-TYPE
   SYNTAX         String
   ACCESS         read-write
   STATUS         mandatory
   DESCRIPTION    ""
   REFERENCE      "IBMPSG_TemperatureEvent.Identifier"
::= { iBMPSGTemperatureEventBindings 1 }

iBMPSGTemperatureEventSourceObjectPath OBJECT-TYPE
   SYNTAX         String
   ACCESS         read-write
   STATUS         mandatory
   DESCRIPTION    "iBMPSGTemperatureEventIdentifier"
   REFERENCE      "IBMPSG_TemperatureEvent.SourceObjectPath"
::= { iBMPSGTemperatureEventBindings 2 }

iBMPSGTemperatureEventTargetObjectPath OBJECT-TYPE
   SYNTAX         String
   ACCESS         read-write
   STATUS         mandatory
   DESCRIPTION    "iBMPSGTemperatureEventTargetObjectPath"
   REFERENCE      "IBMPSG_TemperatureEvent.TargetObjectPath"
::= { iBMPSGTemperatureEventBindings 3 }

iBMPSGTemperatureEventSeverity OBJECT-TYPE
   SYNTAX         Uint16
   ACCESS         read-write
   STATUS         mandatory
   DESCRIPTION    "1=Warning -- The temperature has exceeded a user-defined or manufacturer-defined warning level thresold
                   2=Critical -- The temperature has exceeded a user-defined or manufacturer-defined critical threshold"
   REFERENCE      "IBMPSG_TemperatureEvent.Severity"
::= { iBMPSGTemperatureEventBindings 4 }

iBMPSGTemperatureEventdescription OBJECT-TYPE
   SYNTAX         String
   ACCESS         read-write
   STATUS         mandatory
   DESCRIPTION    "iBMPSGTemperatureEventdescription"
   REFERENCE      "IBMPSG_TemperatureEvent.description"
::= { iBMPSGTemperatureEventBindings 5 }

iBMPSGTemperatureEventTimeStamp OBJECT-TYPE
   SYNTAX         Datetime
   ACCESS         read-write
   STATUS         mandatory
   DESCRIPTION    "iBMPSGTemperatureEventTimeStamp"
   REFERENCE      "IBMPSG_TemperatureEvent.TimeStamp"
::= { iBMPSGTemperatureEventBindings 6 }

iBMPSGTemperatureEvent TRAP-TYPE
   ENTERPRISE     ibmpsg
   VARIABLES    {
      iBMPSGTemperatureEventIdentifier,
      iBMPSGTemperatureEventSourceObjectPath,
      iBMPSGTemperatureEventTargetObjectPath,
      iBMPSGTemperatureEventSeverity,
      iBMPSGTemperatureEventdescription,
      iBMPSGTemperatureEventTimeStamp
   }
   DESCRIPTION    "This event is sent when the state of a system's temperature sensor changes
                   with respect to a manufacturer-defined and/or user-defined threshold."
   REFERENCE      "IBMPSG_TemperatureEvent"
::= 2


iBMPSGVoltageEventBindings OBJECT IDENTIFIER ::= { ibmpsgEvent 3 }

iBMPSGVoltageEventIdentifier OBJECT-TYPE
   SYNTAX         String
   ACCESS         read-write
   STATUS         mandatory
   DESCRIPTION    "iBMPSGVoltageEventIdentifier"
   REFERENCE      "IBMPSG_VoltageEvent.Identifier"
::= { iBMPSGVoltageEventBindings 1 }

iBMPSGVoltageEventSourceObjectPath OBJECT-TYPE
   SYNTAX         String
   ACCESS         read-write
   STATUS         mandatory
   DESCRIPTION    "iBMPSGVoltageEventSourceObjectPath"
   REFERENCE      "IBMPSG_VoltageEvent.SourceObjectPath"
::= { iBMPSGVoltageEventBindings 2 }

iBMPSGVoltageEventTargetObjectPath OBJECT-TYPE
   SYNTAX         String
   ACCESS         read-write
   STATUS         mandatory
   DESCRIPTION    "iBMPSGVoltageEventTargetObjectPath"
   REFERENCE      "IBMPSG_VoltageEvent.TargetObjectPath"
::= { iBMPSGVoltageEventBindings 3 }

iBMPSGVoltageEventSeverity OBJECT-TYPE
   SYNTAX         Uint16
   ACCESS         read-write
   STATUS         mandatory
   DESCRIPTION    "1=Warning -- The voltage has exceeded a manufacturer-defined warning level thresold
                   2=Critical -- The voltage has exceeded a manufacturer-defined critical threshold"
   REFERENCE      "IBMPSG_VoltageEvent.Severity"
::= { iBMPSGVoltageEventBindings 4 }

iBMPSGVoltageEventdescription OBJECT-TYPE
   SYNTAX         String
   ACCESS         read-write
   STATUS         mandatory
   DESCRIPTION    "iBMPSGVoltageEventdescription"
   REFERENCE      "IBMPSG_VoltageEvent.description"
::= { iBMPSGVoltageEventBindings 5 }

iBMPSGVoltageEventTimeStamp OBJECT-TYPE
   SYNTAX         Datetime
   ACCESS         read-write
   STATUS         mandatory
   DESCRIPTION    "iBMPSGVoltageEventTimeStamp"
   REFERENCE      "IBMPSG_VoltageEvent.TimeStamp"
::= { iBMPSGVoltageEventBindings 6 }

iBMPSGVoltageEvent TRAP-TYPE
   ENTERPRISE     ibmpsg
   VARIABLES    {
      iBMPSGVoltageEventIdentifier,
      iBMPSGVoltageEventSourceObjectPath,
      iBMPSGVoltageEventTargetObjectPath,
      iBMPSGVoltageEventSeverity,
      iBMPSGVoltageEventdescription,
      iBMPSGVoltageEventTimeStamp
   }
   DESCRIPTION    "This event is sent when the state of a system's voltage sensor changes
                   with respect to a manufacturer-defined threshold."
   REFERENCE      "IBMPSG_VoltageEvent"
::= 3

iBMPSGChassisEventBindings OBJECT IDENTIFIER ::= { ibmpsgEvent 4 }

iBMPSGChassisEventIdentifier OBJECT-TYPE
   SYNTAX         String
   ACCESS         read-write
   STATUS         mandatory
   DESCRIPTION    "iBMPSGChassisEventIdentifier"
   REFERENCE      "IBMPSG_ChassisEvent.Identifier"
::= { iBMPSGChassisEventBindings 1 }

iBMPSGChassisEventSourceObjectPath OBJECT-TYPE
   SYNTAX         String
   ACCESS         read-write
   STATUS         mandatory
   DESCRIPTION    "iBMPSGChassisEventSourceObjectPath"
   REFERENCE      "IBMPSG_ChassisEvent.SourceObjectPath"
::= { iBMPSGChassisEventBindings 2 }

iBMPSGChassisEventTargetObjectPath OBJECT-TYPE
   SYNTAX         String
   ACCESS         read-write
   STATUS         mandatory
   DESCRIPTION    "iBMPSGChassisEventTargetObjectPath"
   REFERENCE      "IBMPSG_ChassisEvent.TargetObjectPath"
::= { iBMPSGChassisEventBindings 3 }

iBMPSGChassisEventSeverity OBJECT-TYPE
   SYNTAX         Uint16
   ACCESS         read-write
   STATUS         mandatory
   DESCRIPTION    "2=Critical -- The system's cover has been removed"
   REFERENCE      "IBMPSG_ChassisEvent.Severity"
::= { iBMPSGChassisEventBindings 4 }

iBMPSGChassisEventdescription OBJECT-TYPE
   SYNTAX         String
   ACCESS         read-write
   STATUS         mandatory
   DESCRIPTION    "iBMPSGChassisEventdescription"
   REFERENCE      "IBMPSG_ChassisEvent.description"
::= { iBMPSGChassisEventBindings 5 }

iBMPSGChassisEventTimeStamp OBJECT-TYPE
   SYNTAX         Datetime
   ACCESS         read-write
   STATUS         mandatory
   DESCRIPTION    "iBMPSGChassisEventTimeStam"
   REFERENCE      "IBMPSG_ChassisEvent.TimeStamp"
::= { iBMPSGChassisEventBindings 6 }

iBMPSGChassisEvent TRAP-TYPE
   ENTERPRISE     ibmpsg
   VARIABLES    {
      iBMPSGChassisEventIdentifier,
      iBMPSGChassisEventSourceObjectPath,
      iBMPSGChassisEventTargetObjectPath,
      iBMPSGChassisEventSeverity,
      iBMPSGChassisEventdescription,
      iBMPSGChassisEventTimeStamp
   }
   DESCRIPTION    "This event is sent when the state of a system's chassis has changed."
   REFERENCE      "IBMPSG_ChassisEvent"
::= 4



iBMPSGFanEventBindings OBJECT IDENTIFIER ::= { ibmpsgEvent 5 }

iBMPSGFanEventIdentifier OBJECT-TYPE
   SYNTAX         String
   ACCESS         read-write
   STATUS         mandatory
   DESCRIPTION    "iBMPSGFanEventIdentifier"
   REFERENCE      "IBMPSG_FanEvent.Identifier"
::= { iBMPSGFanEventBindings 1 }

iBMPSGFanEventSourceObjectPath OBJECT-TYPE
   SYNTAX         String
   ACCESS         read-write
   STATUS         mandatory
   DESCRIPTION    "iBMPSGFanEventSourceObjectPath"
   REFERENCE      "IBMPSG_FanEvent.SourceObjectPath"
::= { iBMPSGFanEventBindings 2 }

iBMPSGFanEventTargetObjectPath OBJECT-TYPE
   SYNTAX         String
   ACCESS         read-write
   STATUS         mandatory
   DESCRIPTION    "iBMPSGFanEventTargetObjectPath"
   REFERENCE      "IBMPSG_FanEvent.TargetObjectPath"
::= { iBMPSGFanEventBindings 3 }

iBMPSGFanEventSeverity OBJECT-TYPE
   SYNTAX         Uint16
   ACCESS         read-write
   STATUS         mandatory
   DESCRIPTION    "2=Critical -- The fan has stopped."
   REFERENCE      "IBMPSG_FanEvent.Severity"
::= { iBMPSGFanEventBindings 4 }

iBMPSGFanEventdescription OBJECT-TYPE
   SYNTAX         String
   ACCESS         read-write
   STATUS         mandatory
   DESCRIPTION    "iBMPSGFanEventdescription"
   REFERENCE      "IBMPSG_FanEvent.description"
::= { iBMPSGFanEventBindings 5 }

iBMPSGFanEventTimeStamp OBJECT-TYPE
   SYNTAX         Datetime
   ACCESS         read-write
   STATUS         mandatory
   DESCRIPTION    "iBMPSGFanEventTimeStamp"
   REFERENCE      "IBMPSG_FanEvent.TimeStamp"
::= { iBMPSGFanEventBindings 6 }

iBMPSGFanEvent TRAP-TYPE
   ENTERPRISE     ibmpsg
   VARIABLES    {
      iBMPSGFanEventIdentifier,
      iBMPSGFanEventSourceObjectPath,
      iBMPSGFanEventTargetObjectPath,
      iBMPSGFanEventSeverity,
      iBMPSGFanEventdescription,
      iBMPSGFanEventTimeStamp
   }
   DESCRIPTION    "This event is sent when state of a system's fan has changed with respect to
                   manufacturer-defined rpm values."
   REFERENCE      "IBMPSG_FanEvent"
::=  5


iBMPSGProcessorEventBindings OBJECT IDENTIFIER ::= { ibmpsgEvent 6 }

iBMPSGProcessorEventIdentifier OBJECT-TYPE
   SYNTAX         String
   ACCESS         read-write
   STATUS         mandatory
   DESCRIPTION    "iBMPSGProcessorEventIdentifier"
   REFERENCE      "IBMPSG_ProcessorEvent.Identifier"
::= { iBMPSGProcessorEventBindings 1 }

iBMPSGProcessorEventSourceObjectPath OBJECT-TYPE
   SYNTAX         String
   ACCESS         read-write
   STATUS         mandatory
   DESCRIPTION    "iBMPSGProcessorEventSourceObjectPath"
   REFERENCE      "IBMPSG_ProcessorEvent.SourceObjectPath"
::= { iBMPSGProcessorEventBindings 2 }

iBMPSGProcessorEventTargetObjectPath OBJECT-TYPE
   SYNTAX         String
   ACCESS         read-write
   STATUS         mandatory
   DESCRIPTION    "iBMPSGProcessorEventTargetObjectPath"
   REFERENCE      "IBMPSG_ProcessorEvent.TargetObjectPath"
::= { iBMPSGProcessorEventBindings 3 }

iBMPSGProcessorEventSeverity OBJECT-TYPE
   SYNTAX         Uint16
   ACCESS         read-write
   STATUS         mandatory
   DESCRIPTION    "iBMPSGProcessorEventSeverity"
   REFERENCE      "IBMPSG_ProcessorEvent.Severity"
::= { iBMPSGProcessorEventBindings 4 }

iBMPSGProcessorEventdescription OBJECT-TYPE
   SYNTAX         String
   ACCESS         read-write
   STATUS         mandatory
   DESCRIPTION    "iBMPSGProcessorEventdescription"
   REFERENCE      "IBMPSG_ProcessorEvent.description"
::= { iBMPSGProcessorEventBindings 5 }

iBMPSGProcessorEventTimeStamp OBJECT-TYPE
   SYNTAX         Datetime
   ACCESS         read-write
   STATUS         mandatory
   DESCRIPTION    "iBMPSGProcessorEventTimeStamp"
   REFERENCE      "IBMPSG_ProcessorEvent.TimeStamp"
::= { iBMPSGProcessorEventBindings 6 }

iBMPSGProcessorEvent TRAP-TYPE
   ENTERPRISE     ibmpsg
   VARIABLES    {
      iBMPSGProcessorEventIdentifier,
      iBMPSGProcessorEventSourceObjectPath,
      iBMPSGProcessorEventTargetObjectPath,
      iBMPSGProcessorEventSeverity,
      iBMPSGProcessorEventdescription,
      iBMPSGProcessorEventTimeStamp
   }
   DESCRIPTION    "Unused."
   REFERENCE      "IBMPSG_ProcessorEvent"
::= 6


iBMPSGStorageEventBindings OBJECT IDENTIFIER ::= { ibmpsgEvent 7 }

iBMPSGStorageEventIdentifier OBJECT-TYPE
   SYNTAX         String
   ACCESS         read-write
   STATUS         mandatory
   DESCRIPTION    "iBMPSGStorageEventIdentifier"
   REFERENCE      "IBMPSG_StorageEvent.Identifier"
::= { iBMPSGStorageEventBindings 1 }

iBMPSGStorageEventSourceObjectPath OBJECT-TYPE
   SYNTAX         String
   ACCESS         read-write
   STATUS         mandatory
   DESCRIPTION    "iBMPSGStorageEventSourceObjectPath"
   REFERENCE      "IBMPSG_StorageEvent.SourceObjectPath"
::= { iBMPSGStorageEventBindings 2 }

iBMPSGStorageEventTargetObjectPath OBJECT-TYPE
   SYNTAX         String
   ACCESS         read-write
   STATUS         mandatory
   DESCRIPTION    "iBMPSGStorageEventTargetObjectPath"
   REFERENCE      "IBMPSG_StorageEvent.TargetObjectPath"
::= { iBMPSGStorageEventBindings 3 }

iBMPSGStorageEventSeverity OBJECT-TYPE
   SYNTAX         Uint16
   ACCESS         read-write
   STATUS         mandatory
   DESCRIPTION    "1=Warning -- Percentage hard drive space remaining has fallen below user-defined Warning level threshold.
                   2=Critical -- Percentage hard drive space remaining has fallen below user-defined Critical level threshold.
                              -- On systems with Remote Supervisor Adapter, DASD Controller failure."
   REFERENCE      "IBMPSG_StorageEvent.Severity"
::= { iBMPSGStorageEventBindings 4 }

iBMPSGStorageEventdescription OBJECT-TYPE
   SYNTAX         String
   ACCESS         read-write
   STATUS         mandatory
   DESCRIPTION    "iBMPSGStorageEventdescription"
   REFERENCE      "IBMPSG_StorageEvent.description"
::= { iBMPSGStorageEventBindings 5 }

iBMPSGStorageEventTimeStamp OBJECT-TYPE
   SYNTAX         Datetime
   ACCESS         read-write
   STATUS         mandatory
   DESCRIPTION    "iBMPSGStorageEventTimeStamp"
   REFERENCE      "IBMPSG_StorageEvent.TimeStamp"
::= { iBMPSGStorageEventBindings 6 }

iBMPSGStorageEvent TRAP-TYPE
   ENTERPRISE     ibmpsg
   VARIABLES    {
      iBMPSGStorageEventIdentifier,
      iBMPSGStorageEventSourceObjectPath,
      iBMPSGStorageEventTargetObjectPath,
      iBMPSGStorageEventSeverity,
      iBMPSGStorageEventdescription,
      iBMPSGStorageEventTimeStamp
   }
   DESCRIPTION    "On systems with no Remote Supervisor Adapter, this event is sent when the 
                   state of a system's hard drive space has changed with respect to user-defined 
                   levels of percentage hard drive space remaining.
                   On systems with a Remote Supervisor Adapter, this event is sent when the
                   system has experienced a DASD controller failure."
   REFERENCE      "IBMPSG_StorageEvent"
::= 7


iBMPSGAssetEventBindings OBJECT IDENTIFIER ::= { ibmpsgEvent 8 }

iBMPSGAssetEventIdentifier OBJECT-TYPE
   SYNTAX         String
   ACCESS         read-write
   STATUS         mandatory
   DESCRIPTION    "iBMPSGAssetEventIdentifier"
   REFERENCE      "IBMPSG_AssetEvent.Identifier"
::= { iBMPSGAssetEventBindings 1 }

iBMPSGAssetEventSourceObjectPath OBJECT-TYPE
   SYNTAX         String
   ACCESS         read-write
   STATUS         mandatory
   DESCRIPTION    "iBMPSGAssetEventSourceObjectPath"
   REFERENCE      "IBMPSG_AssetEvent.SourceObjectPath"
::= { iBMPSGAssetEventBindings 2 }

iBMPSGAssetEventTargetObjectPath OBJECT-TYPE
   SYNTAX         String
   ACCESS         read-write
   STATUS         mandatory
   DESCRIPTION    "iBMPSGAssetEventTargetObjectPath"
   REFERENCE      "IBMPSG_AssetEvent.TargetObjectPath"
::= { iBMPSGAssetEventBindings 3 }

iBMPSGAssetEventSeverity OBJECT-TYPE
   SYNTAX         Uint16
   ACCESS         read-write
   STATUS         mandatory
   DESCRIPTION    "iBMPSGAssetEventSeverity"
   REFERENCE      "IBMPSG_AssetEvent.Severity"
::= { iBMPSGAssetEventBindings 4 }

iBMPSGAssetEventdescription OBJECT-TYPE
   SYNTAX         String
   ACCESS         read-write
   STATUS         mandatory
   DESCRIPTION    "iBMPSGAssetEventdescription"
   REFERENCE      "IBMPSG_AssetEvent.description"
::= { iBMPSGAssetEventBindings 5 }

iBMPSGAssetEventTimeStamp OBJECT-TYPE
   SYNTAX         Datetime
   ACCESS         read-write
   STATUS         mandatory
   DESCRIPTION    "iBMPSGAssetEventTimeStamp"
   REFERENCE      "IBMPSG_AssetEvent.TimeStamp"
::= { iBMPSGAssetEventBindings 6 }

iBMPSGAssetEvent TRAP-TYPE
   ENTERPRISE     ibmpsg
   VARIABLES    {
      iBMPSGAssetEventIdentifier,
      iBMPSGAssetEventSourceObjectPath,
      iBMPSGAssetEventTargetObjectPath,
      iBMPSGAssetEventSeverity,
      iBMPSGAssetEventdescription,
      iBMPSGAssetEventTimeStamp
   }
   DESCRIPTION    "Unused."
   REFERENCE      "IBMPSG_AssetEvent"
::= 8


iBMPSGSMARTEventBindings OBJECT IDENTIFIER ::= { ibmpsgEvent 9 }

iBMPSGSMARTEventIdentifier OBJECT-TYPE
   SYNTAX         String
   ACCESS         read-write
   STATUS         mandatory
   DESCRIPTION    "iBMPSGSMARTEventIdentifier"
   REFERENCE      "IBMPSG_SMARTEvent.Identifier"
::= { iBMPSGSMARTEventBindings 1 }

iBMPSGSMARTEventSourceObjectPath OBJECT-TYPE
   SYNTAX         String
   ACCESS         read-write
   STATUS         mandatory
   DESCRIPTION    "iBMPSGSMARTEventSourceObjectPath"
   REFERENCE      "IBMPSG_SMARTEvent.SourceObjectPath"
::= { iBMPSGSMARTEventBindings 2 }

iBMPSGSMARTEventTargetObjectPath OBJECT-TYPE
   SYNTAX         String
   ACCESS         read-write
   STATUS         mandatory
   DESCRIPTION    "iBMPSGSMARTEventTargetObjectPath"
   REFERENCE      "IBMPSG_SMARTEvent.TargetObjectPath"
::= { iBMPSGSMARTEventBindings 3 }

iBMPSGSMARTEventSeverity OBJECT-TYPE
   SYNTAX         Uint16
   ACCESS         read-write
   STATUS         mandatory
   DESCRIPTION    "2=Critical - The hard drive is experiencing an imminent failure."
   REFERENCE      "IBMPSG_SMARTEvent.Severity"
::= { iBMPSGSMARTEventBindings 4 }

iBMPSGSMARTEventdescription OBJECT-TYPE
   SYNTAX         String
   ACCESS         read-write
   STATUS         mandatory
   DESCRIPTION    "iBMPSGSMARTEventdescription"
   REFERENCE      "IBMPSG_SMARTEvent.description"
::= { iBMPSGSMARTEventBindings 5 }

iBMPSGSMARTEventTimeStamp OBJECT-TYPE
   SYNTAX         Datetime
   ACCESS         read-write
   STATUS         mandatory
   DESCRIPTION    "iBMPSGSMARTEventTimeStamp"
   REFERENCE      "IBMPSG_SMARTEvent.TimeStamp"
::= { iBMPSGSMARTEventBindings 6 }

iBMPSGSMARTEvent TRAP-TYPE
   ENTERPRISE     ibmpsg
   VARIABLES    {
      iBMPSGSMARTEventIdentifier,
      iBMPSGSMARTEventSourceObjectPath,
      iBMPSGSMARTEventTargetObjectPath,
      iBMPSGSMARTEventSeverity,
      iBMPSGSMARTEventdescription,
      iBMPSGSMARTEventTimeStamp
   }
   DESCRIPTION    "This event is sent when the state of an IDE or SCSI hard drive that complies with the
                  Self-Monitoring, Analysis, and Reporting Technology changes with respect to
                  its availability."
   REFERENCE      "IBMPSG_SMARTEvent"
::= 9


iBMPSGPOSTEventBindings OBJECT IDENTIFIER ::= { ibmpsgEvent 10 }

iBMPSGPOSTEventIdentifier OBJECT-TYPE
   SYNTAX         String
   ACCESS         read-write
   STATUS         mandatory
   DESCRIPTION    "iBMPSGPOSTEventIdentifier"
   REFERENCE      "IBMPSG_POSTEvent.Identifier"
::= { iBMPSGPOSTEventBindings 1 }

iBMPSGPOSTEventSourceObjectPath OBJECT-TYPE
   SYNTAX         String
   ACCESS         read-write
   STATUS         mandatory
   DESCRIPTION    "iBMPSGPOSTEventSourceObjectPat"
   REFERENCE      "IBMPSG_POSTEvent.SourceObjectPath"
::= { iBMPSGPOSTEventBindings 2 }

iBMPSGPOSTEventTargetObjectPath OBJECT-TYPE
   SYNTAX         String
   ACCESS         read-write
   STATUS         mandatory
   DESCRIPTION    "iBMPSGPOSTEventTargetObjectPath"
   REFERENCE      "IBMPSG_POSTEvent.TargetObjectPath"
::= { iBMPSGPOSTEventBindings 3 }

iBMPSGPOSTEventSeverity OBJECT-TYPE
   SYNTAX         Uint16
   ACCESS         read-write
   STATUS         mandatory
   DESCRIPTION    "iBMPSGPOSTEventSeverity"
   REFERENCE      "IBMPSG_POSTEvent.Severity"
::= { iBMPSGPOSTEventBindings 4 }

iBMPSGPOSTEventdescription OBJECT-TYPE
   SYNTAX         String
   ACCESS         read-write
   STATUS         mandatory
   DESCRIPTION    "iBMPSGPOSTEventdescription"
   REFERENCE      "IBMPSG_POSTEvent.description"
::= { iBMPSGPOSTEventBindings 5 }

iBMPSGPOSTEventTimeStamp OBJECT-TYPE
   SYNTAX         Datetime
   ACCESS         read-write
   STATUS         mandatory
   DESCRIPTION    "iBMPSGPOSTEventTimeStamp"
   REFERENCE      "IBMPSG_POSTEvent.TimeStamp"
::= { iBMPSGPOSTEventBindings 6 }

iBMPSGPOSTEvent TRAP-TYPE
   ENTERPRISE     ibmpsg
   VARIABLES    {
      iBMPSGPOSTEventIdentifier,
      iBMPSGPOSTEventSourceObjectPath,
      iBMPSGPOSTEventTargetObjectPath,
      iBMPSGPOSTEventSeverity,
      iBMPSGPOSTEventdescription,
      iBMPSGPOSTEventTimeStamp
   }
   DESCRIPTION    "Unused."
   REFERENCE      "IBMPSG_POSTEvent"
::= 10


iBMPSGConfigurationChangeEventBindings OBJECT IDENTIFIER ::= { ibmpsgEvent 11 }

iBMPSGConfigurationChangeEventIdentifier OBJECT-TYPE
   SYNTAX         String
   ACCESS         read-write
   STATUS         mandatory
   DESCRIPTION    "iBMPSGConfigurationChangeEventIdentifier"
   REFERENCE      "IBMPSG_ConfigurationChangeEvent.Identifier"
::= { iBMPSGConfigurationChangeEventBindings 1 }

iBMPSGConfigurationChangeEventSourceObjectPath OBJECT-TYPE
   SYNTAX         String
   ACCESS         read-write
   STATUS         mandatory
   DESCRIPTION    "iBMPSGConfigurationChangeEventSourceObjectPath"
   REFERENCE      "IBMPSG_ConfigurationChangeEvent.SourceObjectPath"
::= { iBMPSGConfigurationChangeEventBindings 2 }

iBMPSGConfigurationChangeEventTargetObjectPath OBJECT-TYPE
   SYNTAX         String
   ACCESS         read-write
   STATUS         mandatory
   DESCRIPTION    "iBMPSGConfigurationChangeEventTargetObjectPath"
   REFERENCE      "IBMPSG_ConfigurationChangeEvent.TargetObjectPath"
::= { iBMPSGConfigurationChangeEventBindings 3 }

iBMPSGConfigurationChangeEventSeverity OBJECT-TYPE
   SYNTAX         Uint16
   ACCESS         read-write
   STATUS         mandatory
   DESCRIPTION    "iBMPSGConfigurationChangeEventSeverity"
   REFERENCE      "IBMPSG_ConfigurationChangeEvent.Severity"
::= { iBMPSGConfigurationChangeEventBindings 4 }

iBMPSGConfigurationChangeEventdescription OBJECT-TYPE
   SYNTAX         String
   ACCESS         read-write
   STATUS         mandatory
   DESCRIPTION    "iBMPSGConfigurationChangeEventdescription"
   REFERENCE      "IBMPSG_ConfigurationChangeEvent.description"
::= { iBMPSGConfigurationChangeEventBindings 5 }

iBMPSGConfigurationChangeEventTimeStamp OBJECT-TYPE
   SYNTAX         Datetime
   ACCESS         read-write
   STATUS         mandatory
   DESCRIPTION    "iBMPSGConfigurationChangeEventTimeStamp"
   REFERENCE      "IBMPSG_ConfigurationChangeEvent.TimeStamp"
::= { iBMPSGConfigurationChangeEventBindings 6 }

iBMPSGConfigurationChangeEvent TRAP-TYPE
   ENTERPRISE     ibmpsg
   VARIABLES    {
      iBMPSGConfigurationChangeEventIdentifier,
      iBMPSGConfigurationChangeEventSourceObjectPath,
      iBMPSGConfigurationChangeEventTargetObjectPath,
      iBMPSGConfigurationChangeEventSeverity,
      iBMPSGConfigurationChangeEventdescription,
      iBMPSGConfigurationChangeEventTimeStamp
   }
   DESCRIPTION    "Unused."
   REFERENCE      "IBMPSG_ConfigurationChangeEvent"
::= 11


iBMPSGLANLeashEventBindings OBJECT IDENTIFIER ::= { ibmpsgEvent 12 }

iBMPSGLANLeashEventIdentifier OBJECT-TYPE
   SYNTAX         String
   ACCESS         read-write
   STATUS         mandatory
   DESCRIPTION    "iBMPSGLANLeashEventIdentifier"
   REFERENCE      "IBMPSG_LANLeashEvent.Identifier"
::= { iBMPSGLANLeashEventBindings 1 }

iBMPSGLANLeashEventSourceObjectPath OBJECT-TYPE
   SYNTAX         String
   ACCESS         read-write
   STATUS         mandatory
   DESCRIPTION    "iBMPSGLANLeashEventSourceObjectPath"
   REFERENCE      "IBMPSG_LANLeashEvent.SourceObjectPath"
::= { iBMPSGLANLeashEventBindings 2 }

iBMPSGLANLeashEventTargetObjectPath OBJECT-TYPE
   SYNTAX         String
   ACCESS         read-write
   STATUS         mandatory
   DESCRIPTION    "iBMPSGLANLeashEventTargetObjectPath"
   REFERENCE      "IBMPSG_LANLeashEvent.TargetObjectPath"
::= { iBMPSGLANLeashEventBindings 3 }

iBMPSGLANLeashEventSeverity OBJECT-TYPE
   SYNTAX         Uint16
   ACCESS         read-write
   STATUS         mandatory
   DESCRIPTION    "1=Warning -- The system has been disconnected from the network."
   REFERENCE      "IBMPSG_LANLeashEvent.Severity"
::= { iBMPSGLANLeashEventBindings 4 }

iBMPSGLANLeashEventdescription OBJECT-TYPE
   SYNTAX         String
   ACCESS         read-write
   STATUS         mandatory
   DESCRIPTION    "iBMPSGLANLeashEventdescription"
   REFERENCE      "IBMPSG_LANLeashEvent.description"
::= { iBMPSGLANLeashEventBindings 5 }

iBMPSGLANLeashEventTimeStamp OBJECT-TYPE
   SYNTAX         Datetime
   ACCESS         read-write
   STATUS         mandatory
   DESCRIPTION    "iBMPSGLANLeashEventTimeStamp"
   REFERENCE      "IBMPSG_LANLeashEvent.TimeStamp"
::= { iBMPSGLANLeashEventBindings 6 }

iBMPSGLANLeashEvent TRAP-TYPE
   ENTERPRISE     ibmpsg
   VARIABLES    {
      iBMPSGLANLeashEventIdentifier,
      iBMPSGLANLeashEventSourceObjectPath,
      iBMPSGLANLeashEventTargetObjectPath,
      iBMPSGLANLeashEventSeverity,
      iBMPSGLANLeashEventdescription,
      iBMPSGLANLeashEventTimeStamp
   }
   DESCRIPTION    "This event is sent when the state of a system's LAN connectivity changes with
                   respect to the physical connection between its AlertOnLAN-capable NIC and the LAN."
   REFERENCE      "IBMPSG_LANLeashEvent"
::= 12


iBMPSGLeaseExpirationEventBindings OBJECT IDENTIFIER ::= { ibmpsgEvent 13 }

iBMPSGLeaseExpirationEventIdentifier OBJECT-TYPE
   SYNTAX         String
   ACCESS         read-write
   STATUS         mandatory
   DESCRIPTION    "iBMPSGLeaseExpirationEventIdentifier"
   REFERENCE      "IBMPSG_LeaseExpirationEvent.Identifier"
::= { iBMPSGLeaseExpirationEventBindings 1 }

iBMPSGLeaseExpirationEventSourceObjectPath OBJECT-TYPE
   SYNTAX         String
   ACCESS         read-write
   STATUS         mandatory
   DESCRIPTION    "iBMPSGLeaseExpirationEventSourceObjectPath"
   REFERENCE      "IBMPSG_LeaseExpirationEvent.SourceObjectPath"
::= { iBMPSGLeaseExpirationEventBindings 2 }

iBMPSGLeaseExpirationEventTargetObjectPath OBJECT-TYPE
   SYNTAX         String
   ACCESS         read-write
   STATUS         mandatory
   DESCRIPTION    "iBMPSGLeaseExpirationEventTargetObjectPath"
   REFERENCE      "IBMPSG_LeaseExpirationEvent.TargetObjectPath"
::= { iBMPSGLeaseExpirationEventBindings 3 }

iBMPSGLeaseExpirationEventSeverity OBJECT-TYPE
   SYNTAX         Uint16
   ACCESS         read-write
   STATUS         mandatory
   DESCRIPTION    "1=Warning -- The system's lease has expired."
   REFERENCE      "IBMPSG_LeaseExpirationEvent.Severity"
::= { iBMPSGLeaseExpirationEventBindings 4 }

iBMPSGLeaseExpirationEventdescription OBJECT-TYPE
   SYNTAX         String
   ACCESS         read-write
   STATUS         mandatory
   DESCRIPTION    "iBMPSGLeaseExpirationEventdescription"
   REFERENCE      "IBMPSG_LeaseExpirationEvent.description"
::= { iBMPSGLeaseExpirationEventBindings 5 }

iBMPSGLeaseExpirationEventTimeStamp OBJECT-TYPE
   SYNTAX         Datetime
   ACCESS         read-write
   STATUS         mandatory
   DESCRIPTION    "iBMPSGLeaseExpirationEventTimeStamp"
   REFERENCE      "IBMPSG_LeaseExpirationEvent.TimeStamp"
::= { iBMPSGLeaseExpirationEventBindings 6 }

iBMPSGLeaseExpirationEvent TRAP-TYPE
   ENTERPRISE     ibmpsg
   VARIABLES    {
      iBMPSGLeaseExpirationEventIdentifier,
      iBMPSGLeaseExpirationEventSourceObjectPath,
      iBMPSGLeaseExpirationEventTargetObjectPath,
      iBMPSGLeaseExpirationEventSeverity,
      iBMPSGLeaseExpirationEventdescription,
      iBMPSGLeaseExpirationEventTimeStamp
   }
   DESCRIPTION    "This event is sent when a system's Lease Expiration date has been reached
                   with respect to the value configured for the date in the Asset ID tool."
   REFERENCE      "IBMPSG_LeaseExpirationEvent"
::= 13


iBMPSGWarrantyExpirationEventBindings OBJECT IDENTIFIER ::= { ibmpsgEvent 14 }

iBMPSGWarrantyExpirationEventIdentifier OBJECT-TYPE
   SYNTAX         String
   ACCESS         read-write
   STATUS         mandatory
   DESCRIPTION    "iBMPSGWarrantyExpirationEventIdentifier"
   REFERENCE      "IBMPSG_WarrantyExpirationEvent.Identifier"
::= { iBMPSGWarrantyExpirationEventBindings 1 }

iBMPSGWarrantyExpirationEventSourceObjectPath OBJECT-TYPE
   SYNTAX         String
   ACCESS         read-write
   STATUS         mandatory
   DESCRIPTION    "iBMPSGWarrantyExpirationEventSourceObjectPath"
   REFERENCE      "IBMPSG_WarrantyExpirationEvent.SourceObjectPath"
::= { iBMPSGWarrantyExpirationEventBindings 2 }

iBMPSGWarrantyExpirationEventTargetObjectPath OBJECT-TYPE
   SYNTAX         String
   ACCESS         read-write
   STATUS         mandatory
   DESCRIPTION    "iBMPSGWarrantyExpirationEventTargetObjectPath"
   REFERENCE      "IBMPSG_WarrantyExpirationEvent.TargetObjectPath"
::= { iBMPSGWarrantyExpirationEventBindings 3 }

iBMPSGWarrantyExpirationEventSeverity OBJECT-TYPE
   SYNTAX         Uint16
   ACCESS         read-write
   STATUS         mandatory
   DESCRIPTION    "1=Warning -- The system's warranty has expired."
   REFERENCE      "IBMPSG_WarrantyExpirationEvent.Severity"
::= { iBMPSGWarrantyExpirationEventBindings 4 }

iBMPSGWarrantyExpirationEventdescription OBJECT-TYPE
   SYNTAX         String
   ACCESS         read-write
   STATUS         mandatory
   DESCRIPTION    "iBMPSGWarrantyExpirationEventdescription"
   REFERENCE      "IBMPSG_WarrantyExpirationEvent.description"
::= { iBMPSGWarrantyExpirationEventBindings 5 }

iBMPSGWarrantyExpirationEventTimeStamp OBJECT-TYPE
   SYNTAX         Datetime
   ACCESS         read-write
   STATUS         mandatory
   DESCRIPTION    "iBMPSGWarrantyExpirationEventTimeStamp"
   REFERENCE      "IBMPSG_WarrantyExpirationEvent.TimeStamp"
::= { iBMPSGWarrantyExpirationEventBindings 6 }

iBMPSGWarrantyExpirationEvent TRAP-TYPE
   ENTERPRISE     ibmpsg
   VARIABLES    {
      iBMPSGWarrantyExpirationEventIdentifier,
      iBMPSGWarrantyExpirationEventSourceObjectPath,
      iBMPSGWarrantyExpirationEventTargetObjectPath,
      iBMPSGWarrantyExpirationEventSeverity,
      iBMPSGWarrantyExpirationEventdescription,
      iBMPSGWarrantyExpirationEventTimeStamp
   }
   DESCRIPTION    "This event is sent when a system's Warranty Expiration date has been reached
                   with respect to the value configured for the date in the Asset ID tool."
   REFERENCE      "IBMPSG_WarrantyExpirationEvent"
::= 14


iBMPSGRedundantNICEventBindings OBJECT IDENTIFIER ::= { ibmpsgEvent 15 }

iBMPSGRedundantNICEventIdentifier OBJECT-TYPE
   SYNTAX         String
   ACCESS         read-write
   STATUS         mandatory
   DESCRIPTION    "iBMPSGRedundantNICEventIdentifier"
   REFERENCE	  "IBMPSG_RedundantNICEvent.identifier"
::= { iBMPSGRedundantNICEventBindings 1 }

iBMPSGRedundantNICEventSourceObjectPath OBJECT-TYPE
   SYNTAX         String
   ACCESS         read-write
   STATUS         mandatory
   DESCRIPTION    "iBMPSGRedundantNICEventSourceObjectPath"
   REFERENCE	  "IBMPSG_RedundantNICEvent.SourceObjectPath"
::= { iBMPSGRedundantNICEventBindings 2 }

iBMPSGRedundantNICEventTargetObjectPath OBJECT-TYPE
   SYNTAX         String
   ACCESS         read-write
   STATUS         mandatory
   DESCRIPTION    "iBMPSGRedundantNICEventTargetObjectPath"
   REFERENCE	  "IBMPSG_RedundantNICEvent.TargetObjectPath"
::= { iBMPSGRedundantNICEventBindings 3 }

iBMPSGRedundantNICEventdescription OBJECT-TYPE
   SYNTAX         String
   ACCESS         read-write
   STATUS         mandatory
   DESCRIPTION    "iBMPSGRedundantNICEventdescription"
   REFERENCE	  "IBMPSG_RedundantNICEvent.description"
::= { iBMPSGRedundantNICEventBindings 4 }

iBMPSGRedundantNICEventSeverity OBJECT-TYPE
   SYNTAX         Uint16
   ACCESS         read-write
   STATUS         mandatory
   DESCRIPTION    "1=Warning -- A redundant NIC event occurred."
   REFERENCE	  "IBMPSG_RedundantNICEvent.severity"
::= { iBMPSGRedundantNICEventBindings 5 }

iBMPSGRedundantNICEventTimeStamp OBJECT-TYPE
   SYNTAX         Datetime
   ACCESS         read-write
   STATUS         mandatory
   DESCRIPTION    "iBMPSGRedundantNICEventTimeStamp"
   REFERENCE	  "IBMPSG_RedundantNICEvent.timestamp"
::= { iBMPSGRedundantNICEventBindings 6 }

iBMPSGRedundantNICEvent TRAP-TYPE
   ENTERPRISE     ibmpsg
   VARIABLES    {
      iBMPSGRedundantNICEventIdentifier,
      iBMPSGRedundantNICEventSourceObjectPath,
      iBMPSGRedundantNICEventTargetObjectPath,
      iBMPSGRedundantNICEventdescription,
      iBMPSGRedundantNICEventSeverity,
      iBMPSGRedundantNICEventTimeStamp
   }
   DESCRIPTION	"This event is sent when the state of a system's NIC changes state with
                   respect to redundancy, but due to a limitation of the capabilities of
                   the NIC, a determination could not be made between a switchover and
                   a switchback."
   REFERENCE	"IBMPSG_RedundantNICEvent"
::= 15


iBMPSGRedundantNICSwitchoverEventBindings OBJECT IDENTIFIER ::= { ibmpsgEvent 16 }

iBMPSGRedundantNICSwitchoverEventIdentifier OBJECT-TYPE
   SYNTAX         String
   ACCESS         read-write
   STATUS         mandatory
   DESCRIPTION    "iBMPSGRedundantNICSwitchoverEventIdentifier"
   REFERENCE	  "IBMPSG_RedundantNICEvent.identifier"
::= { iBMPSGRedundantNICSwitchoverEventBindings 1 }

iBMPSGRedundantNICSwitchoverEventSourceObjectPath OBJECT-TYPE
   SYNTAX         String
   ACCESS         read-write
   STATUS         mandatory
   DESCRIPTION    "iBMPSGRedundantNICSwitchoverEventSourceObjectPath"
   REFERENCE	  "IBMPSG_RedundantNICSwitchoverEvent.SourceObjectPath"
::= { iBMPSGRedundantNICSwitchoverEventBindings 2 }

iBMPSGRedundantNICSwitchoverEventTargetObjectPath OBJECT-TYPE
   SYNTAX         String
   ACCESS         read-write
   STATUS         mandatory
   DESCRIPTION    "iBMPSGRedundantNICSwitchoverEventTargetObjectPath"
   REFERENCE	  "IBMPSG_RedundantNICSwitchoverEvent.TargetObjectPath"
::= { iBMPSGRedundantNICSwitchoverEventBindings 3 }

iBMPSGRedundantNICSwitchoverEventdescription OBJECT-TYPE
   SYNTAX         String
   ACCESS         read-write
   STATUS         mandatory
   DESCRIPTION    "iBMPSGRedundantNICSwitchoverEventdescription"
   REFERENCE	  "IBMPSG_RedundantNICSwitchoverEvent.description"
::= { iBMPSGRedundantNICSwitchoverEventBindings 4 }

iBMPSGRedundantNICSwitchoverEventSeverity OBJECT-TYPE
   SYNTAX         Uint16
   ACCESS         read-write
   STATUS         mandatory
   DESCRIPTION    "1=Warning -- A failing NIC switched over to a redundant NIC."
   REFERENCE	  "IBMPSG_RedundantNICSwitchoverEvent.severity"
::= { iBMPSGRedundantNICSwitchoverEventBindings 5 }

iBMPSGRedundantNICSwitchoverEventTimeStamp OBJECT-TYPE
   SYNTAX         Datetime
   ACCESS         read-write
   STATUS         mandatory
   DESCRIPTION    "iBMPSGRedundantNICSwitchoverEventTimeStamp"
   REFERENCE	  "IBMPSG_RedundantNICSwitchoverEvent.timestamp"
::= { iBMPSGRedundantNICSwitchoverEventBindings 6 }

iBMPSGRedundantNICSwitchoverEvent TRAP-TYPE
   ENTERPRISE     ibmpsg
   VARIABLES    {
      iBMPSGRedundantNICSwitchoverEventIdentifier,
      iBMPSGRedundantNICSwitchoverEventSourceObjectPath,
      iBMPSGRedundantNICSwitchoverEventTargetObjectPath,
      iBMPSGRedundantNICSwitchoverEventdescription,
      iBMPSGRedundantNICSwitchoverEventSeverity,
      iBMPSGRedundantNICSwitchoverEventTimeStamp
   }
   DESCRIPTION	"This event is sent when the active NIC in a system changes by failing over
                   to a redundant NIC."
   REFERENCE	"IBMPSG_RedundantNICSwitchoverEvent"
::= 16


iBMPSGRedundantNICSwitchbackEventBindings OBJECT IDENTIFIER ::= { ibmpsgEvent 17 }

iBMPSGRedundantNICSwitchbackEventIdentifier OBJECT-TYPE
   SYNTAX         String
   ACCESS         read-write
   STATUS         mandatory
   DESCRIPTION    "iBMPSGRedundantNICSwitchbackEventIdentifier"
   REFERENCE	  "IBMPSG_RedundantNICSwitchbackEvent.identifier"
::= { iBMPSGRedundantNICSwitchbackEventBindings 1 }

iBMPSGRedundantNICSwitchbackEventSourceObjectPath OBJECT-TYPE
   SYNTAX         String
   ACCESS         read-write
   STATUS         mandatory
   DESCRIPTION    "iBMPSGRedundantNICSwitchbackEventSourceObjectPath"
   REFERENCE	  "IBMPSG_RedundantNICSwitchbackEvent.SourceObjectPath"
::= { iBMPSGRedundantNICSwitchbackEventBindings 2 }

iBMPSGRedundantNICSwitchbackEventTargetObjectPath OBJECT-TYPE
   SYNTAX         String
   ACCESS         read-write
   STATUS         mandatory
   DESCRIPTION    "iBMPSGRedundantNICSwitchbackEventTargetObjectPath"
   REFERENCE	  "IBMPSG_RedundantNICSwitchbackEvent.TargetObjectPath"
::= { iBMPSGRedundantNICSwitchbackEventBindings 3 }

iBMPSGRedundantNICSwitchbackEventdescription OBJECT-TYPE
   SYNTAX         String
   ACCESS         read-write
   STATUS         mandatory
   DESCRIPTION    "iBMPSGRedundantNICSwitchbackEventdescription"
   REFERENCE	  "IBMPSG_RedundantNICSwitchbackEvent.description"
::= { iBMPSGRedundantNICSwitchbackEventBindings 4 }

iBMPSGRedundantNICSwitchbackEventSeverity OBJECT-TYPE
   SYNTAX         Uint16
   ACCESS         read-write
   STATUS         mandatory
   DESCRIPTION    "1=Warning -- The system's NIC has recovered and switched back, re-instating redundancy."
   REFERENCE	  "IBMPSG_RedundantNICSwitchbackEvent.severity"
::= { iBMPSGRedundantNICSwitchbackEventBindings 5 }

iBMPSGRedundantNICSwitchbackEventTimeStamp OBJECT-TYPE
   SYNTAX         Datetime
   ACCESS         read-write
   STATUS         mandatory
   DESCRIPTION    "iBMPSGRedundantNICSwitchbackEventTimeStamp"
   REFERENCE	  "IBMPSG_RedundantNICSwitchbackEvent.timestamp"
::= { iBMPSGRedundantNICSwitchbackEventBindings 6 }

iBMPSGRedundantNICSwitchbackEvent TRAP-TYPE
   ENTERPRISE     ibmpsg
   VARIABLES    {
      iBMPSGRedundantNICSwitchbackEventIdentifier,
      iBMPSGRedundantNICSwitchbackEventSourceObjectPath,
      iBMPSGRedundantNICSwitchbackEventTargetObjectPath,
      iBMPSGRedundantNICSwitchbackEventSeverity,
      iBMPSGRedundantNICSwitchbackEventdescription,
      iBMPSGRedundantNICSwitchbackEventTimeStamp
   }
   DESCRIPTION	"This event is sent when the active NIC in a system changes due
                   to a recovery from a redundant NIC."
   REFERENCE	"IBMPSG_RedundantNICSwitchbackEvent"
::= 17


iBMPSGProcessorPFEventBindings OBJECT IDENTIFIER ::= { ibmpsgEvent 18 }

iBMPSGProcessorPFEventIdentifier OBJECT-TYPE
   SYNTAX         String
   ACCESS         read-write
   STATUS         mandatory
   DESCRIPTION    "iBMPSGProcessorPFEventIdentifier"
   REFERENCE	  "IBMPSG_ProcessorPFEvent.identifier"
::= { iBMPSGProcessorPFEventBindings 1 }

iBMPSGProcessorPFEventSourceObjectPath OBJECT-TYPE
   SYNTAX         String
   ACCESS         read-write
   STATUS         mandatory
   DESCRIPTION    "iBMPSGProcessorPFEventSourceObjectPath"
   REFERENCE	  "IBMPSG_ProcessorPFEvent.sourceobjectpath"
::= { iBMPSGProcessorPFEventBindings 2 }

iBMPSGProcessorPFEventTargetObjectPath OBJECT-TYPE
   SYNTAX         String
   ACCESS         read-write
   STATUS         mandatory
   DESCRIPTION    "BMPSGProcessorPFEventTargetObjectPath"
   REFERENCE	  "IBMPSG_ProcessorPFEvent.targetobjectpath"
::= { iBMPSGProcessorPFEventBindings 3 }

iBMPSGProcessorPFEventSeverity OBJECT-TYPE
   SYNTAX         Uint16
   ACCESS         read-write
   STATUS         mandatory
   DESCRIPTION    "2=Critical -- The system's processor is experiencing an imminent failure."
   REFERENCE	  "IBMPSG_ProcessorPFEvent.severity"
::= { iBMPSGProcessorPFEventBindings 4 }

iBMPSGProcessorPFEventdescription OBJECT-TYPE
   SYNTAX         String
   ACCESS         read-write
   STATUS         mandatory
   DESCRIPTION    "iBMPSGProcessorPFEventdescription"
   REFERENCE	  "IBMPSG_ProcessorPFEvent.description"
::= { iBMPSGProcessorPFEventBindings 5 }

iBMPSGProcessorPFEventTimeStamp OBJECT-TYPE
   SYNTAX         Datetime
   ACCESS         read-write
   STATUS         mandatory
   DESCRIPTION    "iBMPSGProcessorPFEventTimeStamp"
   REFERENCE	  "IBMPSG_ProcessorPFEvent.timestamp"
::= { iBMPSGProcessorPFEventBindings 6 }

iBMPSGProcessorPFEvent TRAP-TYPE
   ENTERPRISE     ibmpsg
   VARIABLES    {
      iBMPSGProcessorPFEventIdentifier,
      iBMPSGProcessorPFEventSourceObjectPath,
      iBMPSGProcessorPFEventTargetObjectPath,      
      iBMPSGProcessorPFEventSeverity,
      iBMPSGProcessorPFEventdescription,
      iBMPSGProcessorPFEventTimeStamp
   }
   DESCRIPTION	"This event is sent when a system's processor changes state with respect to availability."
   REFERENCE	"IBMPSG_ProcessorPFEvent"
::= 18


iBMPSGMemoryPFEventBindings OBJECT IDENTIFIER ::= { ibmpsgEvent 19 }

iBMPSGMemoryPFEventIdentifier OBJECT-TYPE
   SYNTAX         String
   ACCESS         read-write
   STATUS         mandatory
   DESCRIPTION    "iBMPSGMemoryPFEventIdentifier"
   REFERENCE	  "IBMPSG_MemoryPFEvent.identifier"
::= { iBMPSGMemoryPFEventBindings 1 }

iBMPSGMemoryPFEventSourceObjectPath OBJECT-TYPE
   SYNTAX         String
   ACCESS         read-write
   STATUS         mandatory
   DESCRIPTION    "iBMPSGMemoryPFEventSourceObjectPath"
   REFERENCE	  "IBMPSG_MemoryPFEvent.sourceobjectpath"
::= { iBMPSGMemoryPFEventBindings 2 }

iBMPSGMemoryPFEventTargetObjectPath OBJECT-TYPE
   SYNTAX         String
   ACCESS         read-write
   STATUS         mandatory
   DESCRIPTION    "iBMPSGMemoryPFEventTargetObjectPath"
   REFERENCE	  "IBMPSG_MemoryPFEvent.targetobjectpath"
::= { iBMPSGMemoryPFEventBindings 3 }

iBMPSGMemoryPFEventSeverity OBJECT-TYPE
   SYNTAX         Uint16
   ACCESS         read-write
   STATUS         mandatory
   DESCRIPTION    "2=Critical -- A DIMM in the system is experiencing an imminent failure."
   REFERENCE	  "IBMPSG_MemoryPFEvent.severity"
::= { iBMPSGMemoryPFEventBindings 4 }

iBMPSGMemoryPFEventdescription OBJECT-TYPE
   SYNTAX         String
   ACCESS         read-write
   STATUS         mandatory
   DESCRIPTION    "iBMPSGMemoryPFEventdescription"
   REFERENCE	  "IBMPSG_MemoryPFEvent.description"
::= { iBMPSGMemoryPFEventBindings 5 }

iBMPSGMemoryPFEventTimeStamp OBJECT-TYPE
   SYNTAX         Datetime
   ACCESS         read-write
   STATUS         mandatory
   DESCRIPTION    "iBMPSGMemoryPFEventTimeStamp"
   REFERENCE	  "IBMPSG_MemoryPFEvent.timestamp"
::= { iBMPSGMemoryPFEventBindings 6 }

iBMPSGMemoryPFEvent TRAP-TYPE
   ENTERPRISE     ibmpsg
   VARIABLES    {
      iBMPSGMemoryPFEventIdentifier,
      iBMPSGMemoryPFEventSourceObjectPath,
      iBMPSGMemoryPFEventTargetObjectPath,
      iBMPSGMemoryPFEventSeverity,
      iBMPSGMemoryPFEventdescription,
      iBMPSGMemoryPFEventTimeStamp
   }
   DESCRIPTION	"This event is sent when a system's DIMM changes state with respect to availability."
   REFERENCE	"IBMPSG_MemoryPFEvent"
::= 19


iBMPSGPFAEventBindings OBJECT IDENTIFIER ::= { ibmpsgEvent 22 }

iBMPSGPFAEventIdentifier OBJECT-TYPE
   SYNTAX         String
   ACCESS         read-write
   STATUS         mandatory
   DESCRIPTION    "iBMPSGPFAEventIdentifier"
   REFERENCE	  "IBMPSG_PFAEvent.identifier"
::= { iBMPSGPFAEventBindings 1 }

iBMPSGPFAEventSourceObjectPath OBJECT-TYPE
   SYNTAX         String
   ACCESS         read-write
   STATUS         mandatory
   DESCRIPTION    "iBMPSGPFAEventSourceObjectPath"
   REFERENCE	  "IBMPSG_PFAEvent.sourceobjectpath"
::= { iBMPSGPFAEventBindings 2 }

iBMPSGPFAEventTargetObjectPath OBJECT-TYPE
   SYNTAX         String
   ACCESS         read-write
   STATUS         mandatory
   DESCRIPTION    "iBMPSGPFAEventTargetObjectPath"
   REFERENCE	  "IBMPSG_PFAEvent.targetobjectpath"
::= { iBMPSGPFAEventBindings 3 }

iBMPSGPFAEventSeverity OBJECT-TYPE
   SYNTAX         Uint16
   ACCESS         read-write
   STATUS         mandatory
   DESCRIPTION    "2=Critical -- The system is experiencing an imminent failure."
   REFERENCE	  "IBMPSG_PFAEvent.severity"
::= { iBMPSGPFAEventBindings 4 }

iBMPSGPFAEventdescription OBJECT-TYPE
   SYNTAX         String
   ACCESS         read-write
   STATUS         mandatory
   DESCRIPTION    "iBMPSGPFAEventdescription"
   REFERENCE	  "IBMPSG_PFAEvent.description"
::= { iBMPSGPFAEventBindings 5 }

iBMPSGPFAEventTimeStamp OBJECT-TYPE
   SYNTAX         Datetime
   ACCESS         read-write
   STATUS         mandatory
   DESCRIPTION    "iBMPSGPFAEventTimeStamp"
   REFERENCE	  "IBMPSG_PFAEvent.timestamp"
::= { iBMPSGPFAEventBindings 6 }

iBMPSGPFAEvent TRAP-TYPE
   ENTERPRISE     ibmpsg
   VARIABLES    {
      iBMPSGPFAEventIdentifier,
      iBMPSGPFAEventSourceObjectPath,
      iBMPSGPFAEventTargetObjectPath,
      iBMPSGPFAEventSeverity,
      iBMPSGPFAEventdescription,
      iBMPSGPFAEventTimeStamp
   }
   DESCRIPTION	"This event is sent when the Remote Supervisor Adapter detects that
                   a system is about to fail."
   REFERENCE	"IBMPSG_PFAEvent"
::= 22


iBMPSGPowerSupplyEventBindings OBJECT IDENTIFIER ::= { ibmpsgEvent 23 }

iBMPSGPowerSupplyEventIdentifier OBJECT-TYPE
   SYNTAX         String
   ACCESS         read-write
   STATUS         mandatory
   DESCRIPTION    "iBMPSGPowerSupplyEventIdentifier"
   REFERENCE	  "IBMPSG_PowerSupplyEvent.identifier"
::= { iBMPSGPowerSupplyEventBindings 1 }

iBMPSGPowerSupplyEventSourceObjectPath OBJECT-TYPE
   SYNTAX         String
   ACCESS         read-write
   STATUS         mandatory
   DESCRIPTION    "iBMPSGPowerSupplyEventSourceObjectPath"
   REFERENCE	  "IBMPSG_PowerSupplyEvent.sourceobjectpath"
::= { iBMPSGPowerSupplyEventBindings 2 }

iBMPSGPowerSupplyEventTargetObjectPath OBJECT-TYPE
   SYNTAX         String
   ACCESS         read-write
   STATUS         mandatory
   DESCRIPTION    "iBMPSGPowerSupplyEventTargetObjectPath"
   REFERENCE	  "IBMPSG_PowerSupplyEvent.targetobjectpath"
::= { iBMPSGPowerSupplyEventBindings 3 }

iBMPSGPowerSupplyEventSeverity OBJECT-TYPE
   SYNTAX         Uint16
   ACCESS         read-write
   STATUS         mandatory
   DESCRIPTION    "0=Normal -- A failed power supply has been recovered.
                   2=Critical -- A power supply in a system has failed and there's been a possible loss of redundancy."
   REFERENCE	  "IBMPSG_PowerSupplyEvent.severity"
::= { iBMPSGPowerSupplyEventBindings 4 }

iBMPSGPowerSupplyEventdescription OBJECT-TYPE
   SYNTAX         String
   ACCESS         read-write
   STATUS         mandatory
   DESCRIPTION    "iBMPSGPowerSupplyEventdescription"
   REFERENCE	  "IBMPSG_PowerSupplyEvent.description"
::= { iBMPSGPowerSupplyEventBindings 5 }

iBMPSGPowerSupplyEventTimeStamp OBJECT-TYPE
   SYNTAX         Datetime
   ACCESS         read-write
   STATUS         mandatory
   DESCRIPTION    "iBMPSGPowerSupplyEventTimeStamp"
   REFERENCE	  "IBMPSG_PowerSupplyEvent.timestamp"
::= { iBMPSGPowerSupplyEventBindings 6 }

iBMPSGPowerSupplyEvent TRAP-TYPE
   ENTERPRISE     ibmpsg
   VARIABLES    {
      iBMPSGPowerSupplyEventIdentifier,
      iBMPSGPowerSupplyEventSourceObjectPath,
      iBMPSGPowerSupplyEventTargetObjectPath,
      iBMPSGPowerSupplyEventSeverity,
      iBMPSGPowerSupplyEventdescription,
      iBMPSGPowerSupplyEventTimeStamp
   }
   DESCRIPTION	"This event is sent when the Remote Supervisor Adapter detects that the
                   state of a system's power supply changes with respect to availability."
   REFERENCE	"IBMPSG_PowerSupplyEvent"
::= 23


iBMPSGErrorLogEventBindings OBJECT IDENTIFIER ::= { ibmpsgEvent 24 }

iBMPSGErrorLogEventIdentifier OBJECT-TYPE
   SYNTAX         String
   ACCESS         read-write
   STATUS         mandatory
   DESCRIPTION    "iBMPSGErrorLogEventIdentifier"
   REFERENCE	  "IBMPSG_ErrorLogEvent.identifier"
::= { iBMPSGErrorLogEventBindings 1 }

iBMPSGErrorLogEventSourceObjectPath OBJECT-TYPE
   SYNTAX         String
   ACCESS         read-write
   STATUS         mandatory
   DESCRIPTION    "iBMPSGErrorLogEventSourceObjectPath"
   REFERENCE	  "IBMPSG_ErrorLogEvent.sourceobjectpath"
::= { iBMPSGErrorLogEventBindings 2 }

iBMPSGErrorLogEventTargetObjectPath OBJECT-TYPE
   SYNTAX         String
   ACCESS         read-write
   STATUS         mandatory
   DESCRIPTION    "iBMPSGErrorLogEventTargetObjectPath"
   REFERENCE	  "IBMPSG_ErrorLogEvent.targetobjectpath"
::= { iBMPSGErrorLogEventBindings 3 }

iBMPSGErrorLogEventSeverity OBJECT-TYPE
   SYNTAX         Uint16
   ACCESS         read-write
   STATUS         mandatory
   DESCRIPTION    "1=Warning -- The Remote Supervisor Adapter's error log is 75% full.
                   2=Critical -- The Remote Supervisor Adapter's error log is 100% full."
   REFERENCE	  "IBMPSG_ErrorLogEvent.severity"
::= { iBMPSGErrorLogEventBindings 4 }

iBMPSGErrorLogEventdescription OBJECT-TYPE
   SYNTAX         String
   ACCESS         read-write
   STATUS         mandatory
   DESCRIPTION    "iBMPSGErrorLogEventdescription"
   REFERENCE	  "IBMPSG_ErrorLogEvent.description"
::= { iBMPSGErrorLogEventBindings 5 }

iBMPSGErrorLogEventTimeStamp OBJECT-TYPE
   SYNTAX         Datetime
   ACCESS         read-write
   STATUS         mandatory
   DESCRIPTION    "iBMPSGErrorLogEventTimeStamp"
   REFERENCE	  "IBMPSG_ErrorLogEvent.timestamp"
::= { iBMPSGErrorLogEventBindings 6 }

iBMPSGErrorLogEvent TRAP-TYPE
   ENTERPRISE     ibmpsg
   VARIABLES    {
      iBMPSGErrorLogEventIdentifier,
      iBMPSGErrorLogEventSourceObjectPath,
      iBMPSGErrorLogEventTargetObjectPath,
      iBMPSGErrorLogEventSeverity,
      iBMPSGErrorLogEventdescription,
      iBMPSGErrorLogEventTimeStamp
   }
   DESCRIPTION	"This event is sent when the Remote Supervisor Adapter detects that its error
                   log is 75% full and/or 100% full."
   REFERENCE	"IBMPSG_ErrorLogEvent"
::= 24


iBMPSGRemoteLoginEventBindings OBJECT IDENTIFIER ::= { ibmpsgEvent 25 }

iBMPSGRemoteLoginEventIdentifier OBJECT-TYPE
   SYNTAX         String
   ACCESS         read-write
   STATUS         mandatory
   DESCRIPTION    "iBMPSGRemoteLoginEventIdentifier"
   REFERENCE	  "IBMPSG_RemoteLoginEvent.identifier"
::= { iBMPSGRemoteLoginEventBindings 1 }

iBMPSGRemoteLoginEventSourceObjectPath OBJECT-TYPE
   SYNTAX         String
   ACCESS         read-write
   STATUS         mandatory
   DESCRIPTION    "iBMPSGRemoteLoginEventSourceObjectPath"
   REFERENCE	  "IBMPSG_RemoteLoginEvent.sourceobjectpath"
::= { iBMPSGRemoteLoginEventBindings 2 }

iBMPSGRemoteLoginEventTargetObjectPath OBJECT-TYPE
   SYNTAX         String
   ACCESS         read-write
   STATUS         mandatory
   DESCRIPTION    "iBMPSGRemoteLoginEventTargetObjectPath"
   REFERENCE	  "IBMPSG_RemoteLoginEvent.targetobjectpath"
::= { iBMPSGRemoteLoginEventBindings 3 }

iBMPSGRemoteLoginEventSeverity OBJECT-TYPE
   SYNTAX         Uint16
   ACCESS         read-write
   STATUS         mandatory
   DESCRIPTION    "1=Warning -- Someone has logged in remotely to the Remote Supervisor Adapter."
   REFERENCE	  "IBMPSG_RemoteLoginEvent.severity"
::= { iBMPSGRemoteLoginEventBindings 4 }

iBMPSGRemoteLoginEventdescription OBJECT-TYPE
   SYNTAX         String
   ACCESS         read-write
   STATUS         mandatory
   DESCRIPTION    "iBMPSGRemoteLoginEventdescription"
   REFERENCE	  "IBMPSG_RemoteLoginEvent.description"
::= { iBMPSGRemoteLoginEventBindings 5 }

iBMPSGRemoteLoginEventTimeStamp OBJECT-TYPE
   SYNTAX         Datetime
   ACCESS         read-write
   STATUS         mandatory
   DESCRIPTION    "iBMPSGRemoteLoginEventTimeStamp"
   REFERENCE	  "IBMPSG_RemoteLoginEvent.timestamp"
::= { iBMPSGRemoteLoginEventBindings 6 }

iBMPSGRemoteLoginEvent TRAP-TYPE
   ENTERPRISE     ibmpsg
   VARIABLES    {
      iBMPSGRemoteLoginEventIdentifier,
      iBMPSGRemoteLoginEventSourceObjectPath,
      iBMPSGRemoteLoginEventTargetObjectPath,
      iBMPSGRemoteLoginEventSeverity,
      iBMPSGRemoteLoginEventdescription,
      iBMPSGRemoteLoginEventTimeStamp
   }
   DESCRIPTION	"This event is sent when the state of the Remote Supervisor Adapter changes
                   with respect to security because a user has logged into it."
   REFERENCE	"IBMPSG_RemoteLoginEvent"
::= 25


iBMPSGNetworkAdapterFailedEventBindings OBJECT IDENTIFIER ::= { ibmpsgEvent 26 }

iBMPSGNetworkAdapterFailedEventIdentifier OBJECT-TYPE
   SYNTAX         String
   ACCESS         read-write
   STATUS         mandatory
   DESCRIPTION    "iBMPSGNetworkAdapterFailedEventIdentifier"
   REFERENCE	  "IBMPSG_NetworkAdapterFailedEvent.identifier"
::= { iBMPSGNetworkAdapterFailedEventBindings 1 }

iBMPSGNetworkAdapterFailedEventSourceObjectPath OBJECT-TYPE
   SYNTAX         String
   ACCESS         read-write
   STATUS         mandatory
   DESCRIPTION    "iBMPSGNetworkAdapterFailedEventSourceObjectPath"
   REFERENCE	  "IBMPSG_NetworkAdapterFailedEvent.sourceobjectpath"
::= { iBMPSGNetworkAdapterFailedEventBindings 2 }

iBMPSGNetworkAdapterFailedEventTargetObjectPath OBJECT-TYPE
   SYNTAX         String
   ACCESS         read-write
   STATUS         mandatory
   DESCRIPTION    "The CIM ObjectPath of the physical network adapter instance that has experienced
		   a change in state."
   REFERENCE	  "IBMPSG_NetworkAdapterFailedEvent.targetobjectpath"
::= { iBMPSGNetworkAdapterFailedEventBindings 3 }

iBMPSGNetworkAdapterFailedEventSeverity OBJECT-TYPE
   SYNTAX         Uint16
   ACCESS         read-write
   STATUS         mandatory
   DESCRIPTION    "2=Critical -- The network adapter referenced in the target object path has failed.
		   0=Normal -- The network adapter referenced in the target object path has been recovered."
   REFERENCE	  "IBMPSG_NetworkAdapterFailedEvent.severity"
::= { iBMPSGNetworkAdapterFailedEventBindings 4 }

iBMPSGNetworkAdapterFailedEventdescription OBJECT-TYPE
   SYNTAX         String
   ACCESS         read-write
   STATUS         mandatory
   DESCRIPTION    "The network adapter in the specified slot or port has failed."
   REFERENCE	  "IBMPSG_NetworkAdapterFailedEvent.description"
::= { iBMPSGNetworkAdapterFailedEventBindings 5 }

iBMPSGNetworkAdapterFailedEventTimeStamp OBJECT-TYPE
   SYNTAX         Datetime
   ACCESS         read-write
   STATUS         mandatory
   DESCRIPTION    "The date and time of the adapter failure on the managed system."
   REFERENCE	  "IBMPSG_NetworkAdapterFailedEvent.timestamp"
::= { iBMPSGNetworkAdapterFailedEventBindings 6 }

iBMPSGNetworkAdapterFailedEventComponentID OBJECT-TYPE
   SYNTAX	Uint16
   ACCESS	read-only
   STATUS	mandatory
   DESCRIPTION  "The physical PCI Slot number or the onboard Port number of the NIC."
   REFERENCE	"IBMPSG_NetworkAdapterFailedEvent.ComponentID"
::= { iBMPSGNetworkAdapterFailedEventBindings 7 }

iBMPSGNetworkAdapterFailedEvent TRAP-TYPE
   ENTERPRISE     ibmpsg
   VARIABLES    {
      iBMPSGNetworkAdapterFailedEventIdentifier,
      iBMPSGNetworkAdapterFailedEventSourceObjectPath,
      iBMPSGNetworkAdapterFailedEventTargetObjectPath,
      iBMPSGNetworkAdapterFailedEventSeverity,
      iBMPSGNetworkAdapterFailedEventdescription,
      iBMPSGNetworkAdapterFailedEventTimeStamp,
      iBMPSGNetworkAdapterFailedEventComponentID
   }
   DESCRIPTION	"This event is sent when the state of a system's NIC fails."
   REFERENCE	"IBMPSG_NetworkAdapterFailedEvent"
::= 26


iBMPSGNetworkAdapterOfflineEventBindings OBJECT IDENTIFIER ::= { ibmpsgEvent 27 }

iBMPSGNetworkAdapterOfflineEventIdentifier OBJECT-TYPE
   SYNTAX         String
   ACCESS         read-write
   STATUS         mandatory
   DESCRIPTION    "iBMPSGNetworkAdapterOfflineEventIdentifier"
   REFERENCE	  "IBMPSG_NetworkAdapterOfflineEvent.identifier"
::= { iBMPSGNetworkAdapterOfflineEventBindings 1 }

iBMPSGNetworkAdapterOfflineEventSourceObjectPath OBJECT-TYPE
   SYNTAX         String
   ACCESS         read-write
   STATUS         mandatory
   DESCRIPTION    "iBMPSGNetworkAdapterOfflineEventSourceObjectPath"
   REFERENCE	  "IBMPSG_NetworkAdapterOfflineEvent.sourceobjectpath"
::= { iBMPSGNetworkAdapterOfflineEventBindings 2 }

iBMPSGNetworkAdapterOfflineEventTargetObjectPath OBJECT-TYPE
   SYNTAX         String
   ACCESS         read-write
   STATUS         mandatory
   DESCRIPTION    "The CIM ObjectPath of the physical network adapter instance that has experienced
		   a change in state."
   REFERENCE	  "IBMPSG_NetworkAdapterOfflineEvent.targetobjectpath"
::= { iBMPSGNetworkAdapterOfflineEventBindings 3 }

iBMPSGNetworkAdapterOfflineEventSeverity OBJECT-TYPE
   SYNTAX         Uint16
   ACCESS         read-write
   STATUS         mandatory
   DESCRIPTION    "1=Warning -- The network adapter referenced in the target object path has gone offline."
   REFERENCE	  "IBMPSG_NetworkAdapterOfflineEvent.severity"
::= { iBMPSGNetworkAdapterOfflineEventBindings 4 }

iBMPSGNetworkAdapterOfflineEventdescription OBJECT-TYPE
   SYNTAX         String
   ACCESS         read-write
   STATUS         mandatory
   DESCRIPTION    "The network adapter in the specified slot or port has gone offline."
   REFERENCE	  "IBMPSG_NetworkAdapterOfflineEvent.description"
::= { iBMPSGNetworkAdapterOfflineEventBindings 5 }

iBMPSGNetworkAdapterOfflineEventTimeStamp OBJECT-TYPE
   SYNTAX         Datetime
   ACCESS         read-write
   STATUS         mandatory
   DESCRIPTION    "The date and time that the network adapter went offline on the managed system."
   REFERENCE	  "IBMPSG_NetworkAdapterOfflineEvent.timestamp"
::= { iBMPSGNetworkAdapterOfflineEventBindings 6 }

iBMPSGNetworkAdapterOfflineEventComponentID OBJECT-TYPE
   SYNTAX	Uint16
   ACCESS	read-only
   STATUS	mandatory
   DESCRIPTION  "The physical PCI Slot number or the onboard Port number of the NIC."
   REFERENCE	"IBMPSG_NetworkAdapterOfflineEvent.ComponentID"
::= { iBMPSGNetworkAdapterOfflineEventBindings 7 }

iBMPSGNetworkAdapterOfflineEvent TRAP-TYPE
   ENTERPRISE     ibmpsg
   VARIABLES    {
      iBMPSGNetworkAdapterOfflineEventIdentifier,
      iBMPSGNetworkAdapterOfflineEventSourceObjectPath,
      iBMPSGNetworkAdapterOfflineEventTargetObjectPath,
      iBMPSGNetworkAdapterOfflineEventSeverity,
      iBMPSGNetworkAdapterOfflineEventdescription,
      iBMPSGNetworkAdapterOfflineEventTimeStamp,
      iBMPSGNetworkAdapterOfflineEventComponentID
   }
   DESCRIPTION	"This event is sent when the state of a system's NIC goes offline."
   REFERENCE	"IBMPSG_NetworkAdapterOfflineEvent"
::= 27


iBMPSGNetworkAdapterOnlineEventBindings OBJECT IDENTIFIER ::= { ibmpsgEvent 28 }

iBMPSGNetworkAdapterOnlineEventIdentifier OBJECT-TYPE
   SYNTAX         String
   ACCESS         read-write
   STATUS         mandatory
   DESCRIPTION    "iBMPSGNetworkAdapterOnlineEventIdentifier"
   REFERENCE	  "IBMPSG_NetworkAdapterOnlineEvent.identifier"
::= { iBMPSGNetworkAdapterOnlineEventBindings 1 }

iBMPSGNetworkAdapterOnlineEventSourceObjectPath OBJECT-TYPE
   SYNTAX         String
   ACCESS         read-write
   STATUS         mandatory
   DESCRIPTION    "iBMPSGNetworkAdapterOnlineEventSourceObjectPath"
   REFERENCE	  "IBMPSG_NetworkAdapterOnlineEvent.sourceobjectpath"
::= { iBMPSGNetworkAdapterOnlineEventBindings 2 }

iBMPSGNetworkAdapterOnlineEventTargetObjectPath OBJECT-TYPE
   SYNTAX         String
   ACCESS         read-write
   STATUS         mandatory
   DESCRIPTION    "The CIM ObjectPath of the physical network adapter instance that has experienced
		   a change in state."
   REFERENCE	  "IBMPSG_NetworkAdapterOnlineEvent.targetobjectpath"
::= { iBMPSGNetworkAdapterOnlineEventBindings 3 }

iBMPSGNetworkAdapterOnlineEventSeverity OBJECT-TYPE
   SYNTAX         Uint16
   ACCESS         read-write
   STATUS         mandatory
   DESCRIPTION    "0=Normal -- The network adapter referenced in the target object path has come online."
   REFERENCE	  "IBMPSG_NetworkAdapterOnlineEvent.severity"
::= { iBMPSGNetworkAdapterOnlineEventBindings 4 }

iBMPSGNetworkAdapterOnlineEventdescription OBJECT-TYPE
   SYNTAX         String
   ACCESS         read-write
   STATUS         mandatory
   DESCRIPTION    "The network adapter in the specified slot or port has come online."
   REFERENCE	  "IBMPSG_NetworkAdapterOnlineEvent.description"
::= { iBMPSGNetworkAdapterOnlineEventBindings 5 }

iBMPSGNetworkAdapterOnlineEventTimeStamp OBJECT-TYPE
   SYNTAX         Datetime
   ACCESS         read-write
   STATUS         mandatory
   DESCRIPTION    "The date and time that the network adapter came online on the managed system."
   REFERENCE	  "IBMPSG_NetworkAdapterOnlineEvent.timestamp"
::= { iBMPSGNetworkAdapterOnlineEventBindings 6 }

iBMPSGNetworkAdapterOnlineEventComponentID OBJECT-TYPE
   SYNTAX	Uint16
   ACCESS	read-only
   STATUS	mandatory
   DESCRIPTION  "The physical PCI Slot number or the onboard Port number of the NIC."
   REFERENCE	"IBMPSG_NetworkAdapterFailedEvent.ComponentID"
::= { iBMPSGNetworkAdapterOnlineEventBindings 7 }

iBMPSGNetworkAdapterOnlineEvent TRAP-TYPE
   ENTERPRISE     ibmpsg
   VARIABLES    {
      iBMPSGNetworkAdapterOnlineEventIdentifier,
      iBMPSGNetworkAdapterOnlineEventSourceObjectPath,
      iBMPSGNetworkAdapterOnlineEventTargetObjectPath,
      iBMPSGNetworkAdapterOnlineEventSeverity,
      iBMPSGNetworkAdapterOnlineEventdescription,
      iBMPSGNetworkAdapterOnlineEventTimeStamp,
      iBMPSGNetworkAdapterOnlineEventComponentID
   }
   DESCRIPTION	"This event is sent when the state of a system's NIC goes online."
   REFERENCE	"IBMPSG_NetworkAdapterOnlineEvent"
::= 28


iBMPSGSPPowerSupplyEventBindings OBJECT IDENTIFIER ::= { ibmpsgEvent 29 }

iBMPSGSPPowerSupplyEventIdentifier OBJECT-TYPE
   SYNTAX         String
   ACCESS         read-write
   STATUS         mandatory
   DESCRIPTION    "iBMPSGSPPowerSupplyEventIdentifier"
   REFERENCE	  "IBMPSG_SP_PowerSupplyEvent.identifier"
::= { iBMPSGSPPowerSupplyEventBindings 1 }

iBMPSGSPPowerSupplyEventSourceObjectPath OBJECT-TYPE
   SYNTAX         String
   ACCESS         read-write
   STATUS         mandatory
   DESCRIPTION    "iBMPSGSPPowerSupplyEventSourceObjectPath"
   REFERENCE	  "IBMPSG_SP_PowerSupplyEvent.sourceobjectpath"
::= { iBMPSGSPPowerSupplyEventBindings 2 }

iBMPSGSPPowerSupplyEventTargetObjectPath OBJECT-TYPE
   SYNTAX         String
   ACCESS         read-write
   STATUS         mandatory
   DESCRIPTION    "iBMPSGSPPowerSupplyEventTargetObjectPat"
   REFERENCE	  "IBMPSG_SP_PowerSupplyEvent.targetobjectpath"
::= { iBMPSGSPPowerSupplyEventBindings 3 }

iBMPSGSPPowerSupplyEventSeverity OBJECT-TYPE
   SYNTAX         Uint16
   ACCESS         read-write
   STATUS         mandatory
   DESCRIPTION    "2=Critical -- A power supply in a system has failed and there has been a possible loss of redundancy."
   REFERENCE	  "IBMPSG_SP_PowerSupplyEvent.severity"
::= { iBMPSGSPPowerSupplyEventBindings 4 }

iBMPSGSPPowerSupplyEventdescription OBJECT-TYPE
   SYNTAX         String
   ACCESS         read-write
   STATUS         mandatory
   DESCRIPTION    "iBMPSGSPPowerSupplyEventdescription"
   REFERENCE	  "IBMPSG_SP_PowerSupplyEvent.description"
::= { iBMPSGSPPowerSupplyEventBindings 5 }

iBMPSGSPPowerSupplyEventTimeStamp OBJECT-TYPE
   SYNTAX         Datetime
   ACCESS         read-write
   STATUS         mandatory
   DESCRIPTION    "iBMPSGSPPowerSupplyEventTimeStamp"
   REFERENCE	  "IBMPSG_SP_PowerSupplyEvent.timestamp"
::= { iBMPSGSPPowerSupplyEventBindings 6 }

iBMPSGSPPowerSupplyEvent TRAP-TYPE
   ENTERPRISE     ibmpsg
   VARIABLES    {
      iBMPSGSPPowerSupplyEventIdentifier,
      iBMPSGSPPowerSupplyEventSourceObjectPath,
      iBMPSGSPPowerSupplyEventTargetObjectPath,
      iBMPSGSPPowerSupplyEventSeverity,
      iBMPSGSPPowerSupplyEventdescription,
      iBMPSGSPPowerSupplyEventTimeStamp
   }
   DESCRIPTION	"This event is sent when the Remote Supervisor Adapter detects that the
                   state of a system's power supply changes with respect to availability."
   REFERENCE	"IBMPSG_SP_PowerSupplyEvent"
::= 29


iBMPSGDASDBackplaneEventBindings OBJECT IDENTIFIER ::= { ibmpsgEvent 30 }

iBMPSGDASDBackplaneEventIdentifier OBJECT-TYPE
   SYNTAX         String
   ACCESS         read-write
   STATUS         mandatory
   DESCRIPTION    "iBMPSGDASDBackplaneEventIdentifier"
   REFERENCE	  "IBMPSG_DASDBackplaneEvent.identifier"
::= { iBMPSGDASDBackplaneEventBindings 1 }

iBMPSGDASDBackplaneEventSourceObjectPath OBJECT-TYPE
   SYNTAX         String
   ACCESS         read-write
   STATUS         mandatory
   DESCRIPTION    "iBMPSGDASDBackplaneEventSourceObjectPath"
   REFERENCE	  "IBMPSG_DASDBackplaneEvent.sourceobjectpath"
::= { iBMPSGDASDBackplaneEventBindings 2 }

iBMPSGDASDBackplaneEventTargetObjectPath OBJECT-TYPE
   SYNTAX         String
   ACCESS         read-write
   STATUS         mandatory
   DESCRIPTION    "iBMPSGDASDBackplaneEventTargetObjectPath"
   REFERENCE	  "IBMPSG_DASDBackplaneEvent.targetobjectpath"
::= { iBMPSGDASDBackplaneEventBindings 3 }

iBMPSGDASDBackplaneEventSeverity OBJECT-TYPE
   SYNTAX         Uint16
   ACCESS         read-write
   STATUS         mandatory
   DESCRIPTION    "2=Critical -- A hard drive failure has occured."
   REFERENCE	  "IBMPSG_DASDBackplaneEvent.severity"
::= { iBMPSGDASDBackplaneEventBindings 4 }

iBMPSGDASDBackplaneEventdescription OBJECT-TYPE
   SYNTAX         String
   ACCESS         read-write
   STATUS         mandatory
   DESCRIPTION    "iBMPSGDASDBackplaneEventdescription"
   REFERENCE	  "IBMPSG_DASDBackplaneEvent.description"
::= { iBMPSGDASDBackplaneEventBindings 5 }

iBMPSGDASDBackplaneEventTimeStamp OBJECT-TYPE
   SYNTAX         Datetime
   ACCESS         read-write
   STATUS         mandatory
   DESCRIPTION    "iBMPSGDASDBackplaneEventTimeStamp"
   REFERENCE	  "IBMPSG_DASDBackplaneEvent.timestamp"
::= { iBMPSGDASDBackplaneEventBindings 6 }

iBMPSGDASDBackplaneEvent TRAP-TYPE
   ENTERPRISE     ibmpsg
   VARIABLES    {
      iBMPSGDASDBackplaneEventIdentifier,
      iBMPSGDASDBackplaneEventSourceObjectPath,
      iBMPSGDASDBackplaneEventTargetObjectPath,
      iBMPSGDASDBackplaneEventSeverity,
      iBMPSGDASDBackplaneEventdescription,
      iBMPSGDASDBackplaneEventTimeStamp
   }
   DESCRIPTION	"This event is sent when the Remote Supervisor Adapter detects that the
                   drive backplane experiences a critical error."
   REFERENCE	"IBMPSG_DASDBackplaneEvent"
::= 30


iBMPSGGenericFanEventBindings OBJECT IDENTIFIER ::= { ibmpsgEvent 31 }

iBMPSGGenericFanEventIdentifier OBJECT-TYPE
   SYNTAX         String
   ACCESS         read-write
   STATUS         mandatory
   DESCRIPTION    "iBMPSGGenericFanEventIdentifier"
   REFERENCE	  "IBMPSG_GenericFanEvent.identifier"
::= { iBMPSGGenericFanEventBindings 1 }

iBMPSGGenericFanEventSourceObjectPath OBJECT-TYPE
   SYNTAX         String
   ACCESS         read-write
   STATUS         mandatory
   DESCRIPTION    "iBMPSGGenericFanEventSourceObjectPath"
   REFERENCE	  "IBMPSG_GenericFanEvent.sourceobjectpath"
::= { iBMPSGGenericFanEventBindings 2 }

iBMPSGGenericFanEventTargetObjectPath OBJECT-TYPE
   SYNTAX         String
   ACCESS         read-write
   STATUS         mandatory
   DESCRIPTION    "iBMPSGGenericFanEventTargetObjectPath"
   REFERENCE	  "IBMPSG_GenericFanEvent.targetobjectpath"
::= { iBMPSGGenericFanEventBindings 3 }

iBMPSGGenericFanEventSeverity OBJECT-TYPE
   SYNTAX         Uint16
   ACCESS         read-write
   STATUS         mandatory
   DESCRIPTION    "2=Critical -- The fan has stopped."
   REFERENCE	  "IBMPSG_GenericFanEvent.severity"
::= { iBMPSGGenericFanEventBindings 4 }

iBMPSGGenericFanEventdescription OBJECT-TYPE
   SYNTAX         String
   ACCESS         read-write
   STATUS         mandatory
   DESCRIPTION    "iBMPSGGenericFanEventdescription"
   REFERENCE	  "IBMPSG_GenericFanEvent.description"
::= { iBMPSGGenericFanEventBindings 5 }

iBMPSGGenericFanEventTimeStamp OBJECT-TYPE
   SYNTAX         Datetime
   ACCESS         read-write
   STATUS         mandatory
   DESCRIPTION    "iBMPSGGenericFanEventTimeStamp"
   REFERENCE	  "IBMPSG_GenericFanEvent.timestamp"
::= { iBMPSGGenericFanEventBindings 6 }

iBMPSGGenericFanEvent TRAP-TYPE
   ENTERPRISE     ibmpsg
   VARIABLES    {
      iBMPSGGenericFanEventIdentifier,
      iBMPSGGenericFanEventSourceObjectPath,
      iBMPSGGenericFanEventTargetObjectPath,
      iBMPSGGenericFanEventSeverity,
      iBMPSGGenericFanEventdescription,
      iBMPSGGenericFanEventTimeStamp
   }
   DESCRIPTION	"This event is sent when the Remote Supervisor Adapter detects that the
                   state of a system's fan has changed with respect to
                   manufacturer-defined rpm values"
   REFERENCE	"IBMPSG_GenericFanEvent"
::= 31


iBMPSGGenericVoltageEventBindings OBJECT IDENTIFIER ::= { ibmpsgEvent 32 }

iBMPSGGenericVoltageEventIdentifier OBJECT-TYPE
   SYNTAX         String
   ACCESS         read-write
   STATUS         mandatory
   DESCRIPTION    "iBMPSGGenericVoltageEventIdentifier"
   REFERENCE	  "IBMPSG_GenericVoltageEvent.identifier"
::= { iBMPSGGenericVoltageEventBindings 1 }

iBMPSGGenericVoltageEventSourceObjectPath OBJECT-TYPE
   SYNTAX         String
   ACCESS         read-write
   STATUS         mandatory
   DESCRIPTION    "iBMPSGGenericVoltageEventSourceObjectPath"
   REFERENCE	  "IBMPSG_GenericVoltageEvent.sourceobjectpath"
::= { iBMPSGGenericVoltageEventBindings 2 }

iBMPSGGenericVoltageEventTargetObjectPath OBJECT-TYPE
   SYNTAX         String
   ACCESS         read-write
   STATUS         mandatory
   DESCRIPTION    "iBMPSGGenericVoltageEventTargetObjectPath"
   REFERENCE	  "IBMPSG_GenericVoltageEvent.targetobjectpath"
::= { iBMPSGGenericVoltageEventBindings 3 }

iBMPSGGenericVoltageEventSeverity OBJECT-TYPE
   SYNTAX         Uint16
   ACCESS         read-write
   STATUS         mandatory
   DESCRIPTION    "1=Warning -- The voltage has exceeded a manufacturer-defined warning level thresold
                   2=Critical -- The voltage has exceeded a manufacturer-defined critical threshold"
   REFERENCE	  "IBMPSG_GenericVoltageEvent.severity"
::= { iBMPSGGenericVoltageEventBindings 4 }

iBMPSGGenericVoltageEventdescription OBJECT-TYPE
   SYNTAX         String
   ACCESS         read-write
   STATUS         mandatory
   DESCRIPTION    "iBMPSGGenericVoltageEventdescription"
   REFERENCE	  "IBMPSG_GenericVoltageEvent.description"
::= { iBMPSGGenericVoltageEventBindings 5 }

iBMPSGGenericVoltageEventTimeStamp OBJECT-TYPE
   SYNTAX         Datetime
   ACCESS         read-write
   STATUS         mandatory
   DESCRIPTION    "iBMPSGGenericVoltageEventTimeStamp"
   REFERENCE	  "IBMPSG_GenericVoltageEvent.timestamp"
::= { iBMPSGGenericVoltageEventBindings 6 }

iBMPSGGenericVoltageEvent TRAP-TYPE
   ENTERPRISE     ibmpsg
   VARIABLES    {
      iBMPSGGenericVoltageEventIdentifier,
      iBMPSGGenericVoltageEventSourceObjectPath,
      iBMPSGGenericVoltageEventTargetObjectPath,
      iBMPSGGenericVoltageEventSeverity,
      iBMPSGGenericVoltageEventdescription,
      iBMPSGGenericVoltageEventTimeStamp
   }
   DESCRIPTION	"This event is sent when the Remote Supervisor Adapter detects that the
                   state of a system's voltage sensor changes with respect to a 
                   manufacturer-defined threshold."
   REFERENCE	"IBMPSG_GenericVoltageEvent"
::= 32

END
