-- *****************************************************************
-- CISCO-SWITCH-HARDWARE-CAPACITY-CAPABILITY.my:
-- Cisco CISCO-SWITCH-HARDWARE-CAPACITY-MIB AGENT-CAPABILITIES
--
-- October 2008, Jayakumar Kadirvelu
--
-- Copyright (c) 2008 by Cisco Systems, Inc.
-- All rights reserved.
-- *****************************************************************

CISCO-SWITCH-HARDWARE-CAPACITY-CAPABILITY DEFINITIONS ::= BEGIN

IMPORTS
        MODULE-IDENTITY
                FROM SNMPv2-SMI
        AGENT-CAPABILITIES
                FROM SNMPv2-CONF
        ciscoAgentCapability
                FROM CISCO-SMI;

cSwitchHwCapacityCapability MODULE-IDENTITY
        LAST-UPDATED        "200810290000Z"
        ORGANIZATION        "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of 
                CISCO-SWITCH-HARDWARE-CAPACITY-MIB."
        REVISION        "200810290000Z"
        DESCRIPTION
                "Initial version of this MIB module."
        ::= { ciscoAgentCapability 9999901 }


cSwitchHwCapacityCapV12R0233SXIPCat6k AGENT-CAPABILITIES
    PRODUCT-RELEASE     "Cisco IOS 12.2(33)SXI on Catalyst 6000/6500
                         series devices."
    STATUS              current
    DESCRIPTION         "CISCO-SWITCH-HARDWARE-CAPACITY-MIB 
                        capabilities."

    SUPPORTS            CISCO-SWITCH-HARDWARE-CAPACITY-MIB
        INCLUDES        { cshcMacUsageGroup,
                          cshcVpnCamUsageGroup,
                          cshcFibTcamUsageGroup,
                          cshcProtocolFibTcamUsageGroup,
                          cshcAdjacencyUsageGroup,
                          cshcForwardingLoadGroup,
                          cshcModuleInterfaceDropsGroup,
                          cshcInterfaceBufferGroup,
                          cshcInternalChannelGroup,
                          cshcCPURateLimiterResourcesGroup,
                          cshcIcamResourcesGroup,
                          cshcNetflowFlowMaskResourceGroup }
    ::= { cSwitchHwCapacityCapability 1 }
END
