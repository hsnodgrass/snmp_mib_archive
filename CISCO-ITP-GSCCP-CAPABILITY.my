-- *****************************************************************
-- CISCO-ITP-GSCCP-CAPABILITY.my: ITP Gateway Signaling Connection
-- Control Part Agent capability MIB
--
-- May 2003, John Linton and Shekhar Acharya
--
-- Copyright (c) 2003, 2006-2007 by cisco Systems Inc.
--
-- All rights reserved.
-- ***************************************************************

CISCO-ITP-GSCCP-CAPABILITY DEFINITIONS ::= BEGIN

IMPORTS
    MODULE-IDENTITY
        FROM SNMPv2-SMI
    AGENT-CAPABILITIES
        FROM SNMPv2-CONF
    ciscoAgentCapability
        FROM CISCO-SMI;


ciscoGsccpCapability MODULE-IDENTITY
    LAST-UPDATED    "200705170000Z"
    ORGANIZATION    "Cisco Systems, Inc."
    CONTACT-INFO
            "Cisco Systems
            Customer Service

            Postal: 170 West Tasman Drive
            San Jose, CA  95134
            USA

            Tel: +1 800 553-NETS

            E-mail: cs-ss7@cisco.com"
    DESCRIPTION
        "Agent capabilities for the CISCO-ITP-GSCCP-MIB."
    REVISION        "200705170000Z"
    DESCRIPTION
        "Added ciscoGsccpCapabilityV12R0218IXA and
        ciscoGsccpCapabilityV12R0411SW capability
        statements.  Corrected all capability statements
        to indicate that cgsccpGttConPcRowStatus was
        implemented as read-only rather than
        cgsccpGttConPcTable."
    REVISION        "200501140000Z"
    DESCRIPTION
        "Added ciscoGsccpCapabilityV12R025000SW1
        capability statement.  Added
        ciscoGsccpNotificationsGroupSup1,
        ciscoGsccpGttErrorsGroup and
        ciscoGsccpGttPrefGroupSup1 object goups."
    REVISION        "200410070000Z"
    DESCRIPTION
        "Added ciscoGsccpCapabilityV12R023000SW1
        capability statement.  Replaced
        ciscoGsccpGttAppGroupRev2 object group with
        ciscoGsccpGttAppGroupRev3."
    REVISION        "200312080000Z"
    DESCRIPTION
        "Support for cross instance global title
        translation.

         Added ciscoGsccpCapabilityV12R022004SW
         capability statement.  Replaced
         ciscoGsccpGttAppGroup object group with
         ciscoGsccpGttAppGroupRev2.  Replaced
         ciscoGsccpGttGtaGroup with
         ciscoGsccpGttGtaGroupRev2."
    REVISION        "200310280000Z"
    DESCRIPTION
        "Changes to allow GTT prefix conversion
        to be specified per instance.

        Added ciscoGsccpCapabilityV12R0204MB13
        capability statement."
    REVISION        "200305200000Z"
    DESCRIPTION
        "Initial version of this MIB module."
    ::= { ciscoAgentCapability 539 }



ciscoGsccpCapabilityV12R0204MB10 AGENT-CAPABILITIES
    PRODUCT-RELEASE "Cisco IOS 12.2(4)MB10"
    STATUS          current
    DESCRIPTION
        "IOS 12.2(4)MB10 Cisco CISCO-ITP-GSCCP-MIB.my User
        Agent MIB capabilities."

    SUPPORTS        CISCO-ITP-GSCCP-MIB
    INCLUDES        {
                        ciscoGsccpGlobalEntryGroup,
                        ciscoGsccpInstTableEntryGroup,
                        ciscoGsccpGttConPcGroup,
                        ciscoGsccpGttAppGroup,
                        ciscoGsccpGttMapGroup,
                        ciscoGsccpGttSelGroup,
                        ciscoGsccpGttGtaGroup,
                        ciscoGsccpGttPrefGroup,
                        ciscoGsccpNotificationsGroup
                    }
    VARIATION       cgsccpGttConPcRowStatus
    DESCRIPTION
        "Implemented as read-only."

    VARIATION       cgsccpGttTranslateRate
    ACCESS          not-implemented
    DESCRIPTION
        "Not implemented."

    ::= { ciscoGsccpCapability 1 }

ciscoGsccpCapabilityV12R0204MB13 AGENT-CAPABILITIES
    PRODUCT-RELEASE "Cisco IOS 12.2(4)MB13"
    STATUS          current
    DESCRIPTION
        "IOS 12.2(4)MB13 Cisco CISCO-ITP-GSCCP-MIB.my User
        Agent MIB capabilities."

    SUPPORTS        CISCO-ITP-GSCCP-MIB
    INCLUDES        {
                        ciscoGsccpGlobalEntryGroup,
                        ciscoGsccpInstTableEntryGroup,
                        ciscoGsccpGttConPcGroup,
                        ciscoGsccpGttAppGroup,
                        ciscoGsccpGttMapGroup,
                        ciscoGsccpGttSelGroup,
                        ciscoGsccpGttGtaGroup,
                        ciscoGsccpGttPrefGroupRev1,
                        ciscoGsccpNotificationsGroup
                    }
    VARIATION       cgsccpGttConPcRowStatus
    DESCRIPTION
        "Implemented as read-only."

    ::= { ciscoGsccpCapability 2 }

ciscoGsccpCapabilityV12R022004SW AGENT-CAPABILITIES
    PRODUCT-RELEASE "Cisco IOS 12.2(20.4)SW"
    STATUS          current
    DESCRIPTION
        "IOS 12.2(20.4)SW Cisco CISCO-ITP-GSCCP-MIB.my User
        Agent MIB capabilities."

    SUPPORTS        CISCO-ITP-GSCCP-MIB
    INCLUDES        {
                        ciscoGsccpGlobalEntryGroupRev1,
                        ciscoGsccpGttConPcGroup,
                        ciscoGsccpGttMapGroup,
                        ciscoGsccpGttSelGroup,
                        ciscoGsccpGttPrefGroupRev1,
                        ciscoGsccpNotificationsGroup,
                        ciscoGsccpInstTableEntryGroupRev1,
                        ciscoGsccpGttAppGroupRev2,
                        ciscoGsccpGttGtaGroupRev2
                    }
    VARIATION       cgsccpGttConPcRowStatus
    DESCRIPTION
        "Implemented as read-only."

    ::= { ciscoGsccpCapability 3 }

ciscoGsccpCapabilityV12R023000SW1 AGENT-CAPABILITIES
    PRODUCT-RELEASE "Cisco IOS 12.2(23)SW1"
    STATUS          current
    DESCRIPTION
        "IOS 12.2(23)SW1 Cisco CISCO-ITP-GSCCP-MIB.my User
        Agent MIB capabilities."

    SUPPORTS        CISCO-ITP-GSCCP-MIB
    INCLUDES        {
                        ciscoGsccpGlobalEntryGroupRev1,
                        ciscoGsccpGttConPcGroup,
                        ciscoGsccpGttMapGroup,
                        ciscoGsccpGttSelGroup,
                        ciscoGsccpGttPrefGroupRev1,
                        ciscoGsccpNotificationsGroup,
                        ciscoGsccpInstTableEntryGroupRev1,
                        ciscoGsccpGttGtaGroupRev2,
                        ciscoGsccpGttAppGroupRev3
                    }
    VARIATION       cgsccpGttConPcRowStatus
    DESCRIPTION
        "Implemented as read-only."

    ::= { ciscoGsccpCapability 4 }

ciscoGsccpCapabilityV12R025000SW1 AGENT-CAPABILITIES
    PRODUCT-RELEASE "Cisco IOS 12.2(25)SW1"
    STATUS          current
    DESCRIPTION
        "IOS 12.2(25)SW1 Cisco CISCO-ITP-GSCCP-MIB.my User
        Agent MIB capabilities."

    SUPPORTS        CISCO-ITP-GSCCP-MIB
    INCLUDES        {
                        ciscoGsccpGlobalEntryGroupRev1,
                        ciscoGsccpGttConPcGroup,
                        ciscoGsccpGttMapGroup,
                        ciscoGsccpGttSelGroup,
                        ciscoGsccpGttPrefGroupRev1,
                        ciscoGsccpNotificationsGroup,
                        ciscoGsccpInstTableEntryGroupRev1,
                        ciscoGsccpGttGtaGroupRev2,
                        ciscoGsccpGttAppGroupRev3,
                        ciscoGsccpNotificationsGroupSup1,
                        ciscoGsccpGttErrorsGroup,
                        ciscoGsccpGttPrefGroupSup1
                    }
    VARIATION       cgsccpGttConPcRowStatus
    DESCRIPTION
        "Implemented as read-only."

    ::= { ciscoGsccpCapability 5 }

ciscoGsccpCapabilityV12R0218IXA AGENT-CAPABILITIES
    PRODUCT-RELEASE "Cisco IOS 12.2(18)IXA"
    STATUS          current
    DESCRIPTION
        "IOS 12.2(18)IXA Cisco CISCO-ITP-GSCCP-MIB.my User Agent MIB
        capabilities."

    SUPPORTS        CISCO-ITP-GSCCP-MIB
    INCLUDES        {
                        ciscoGsccpGlobalEntryGroupRev1,
                        ciscoGsccpGttConPcGroup,
                        ciscoGsccpGttMapGroup,
                        ciscoGsccpGttSelGroup,
                        ciscoGsccpNotificationsGroup,
                        ciscoGsccpGttPrefGroupRev1,
                        ciscoGsccpInstTableEntryGroupRev1,
                        ciscoGsccpGttGtaGroupRev2,
                        ciscoGsccpGttAppGroupRev3,
                        ciscoGsccpNotificationsGroupSup1,
                        ciscoGsccpGttErrorsGroup,
                        ciscoGsccpGttPrefGroupSup1
                    }
    VARIATION       cgsccpGttConPcRowStatus
    DESCRIPTION
        "Implemented as read-only."

    ::= { ciscoGsccpCapability 6 }

ciscoGsccpCapabilityV12R0411SW AGENT-CAPABILITIES
    PRODUCT-RELEASE "Cisco IOS IOS 12.4(11)SW"
    STATUS          current
    DESCRIPTION
        "Cisco IOS IOS 12.4(11)SW Cisco CISCO-ITP-GSCCP-MIB.my
        User Agent MIB capabilities."

    SUPPORTS        CISCO-ITP-GSCCP-MIB
    INCLUDES        {
                        ciscoGsccpGlobalEntryGroupRev1,
                        ciscoGsccpGttConPcGroup,
                        ciscoGsccpGttMapGroup,
                        ciscoGsccpGttSelGroup,
                        ciscoGsccpNotificationsGroup,
                        ciscoGsccpGttPrefGroupRev1,
                        ciscoGsccpInstTableEntryGroupRev1,
                        ciscoGsccpGttGtaGroupRev2,
                        ciscoGsccpGttAppGroupRev3,
                        ciscoGsccpNotificationsGroupSup1,
                        ciscoGsccpGttErrorsGroup,
                        ciscoGsccpGttPrefGroupSup1
                    }
    VARIATION       cgsccpGttConPcRowStatus
    DESCRIPTION
        "Implemented as read-only."

    ::= { ciscoGsccpCapability 7 }

END
