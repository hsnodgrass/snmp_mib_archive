--
-- WS-INFRA-SYSMSG-MIB.my
-- MIB generated by MG-SOFT Visual MIB Builder Version 6.0  Build 88
-- Thursday, June 01, 2006 at 14:19:35
--

	WS-INFRA-SYSMSG-MIB DEFINITIONS ::= BEGIN
 
		IMPORTS
			OBJECT-GROUP, MODULE-COMPLIANCE			
				FROM SNMPv2-CONF			
			IpAddress, Integer32, OBJECT-TYPE, MODULE-IDENTITY			
				FROM SNMPv2-SMI			
			TruthValue			
				FROM SNMPv2-TC			
			wsInfraSysMsg			
				FROM WS-INFRA-SMI-MIB			
			DoActionNow			
				FROM WS-TYPE-MIB;
	
	
		-- 1.3.6.1.4.1.388.14.1.3.1
		wsInfraSysMsgModule MODULE-IDENTITY 
			LAST-UPDATED "200504191023Z"		-- April 19, 2005 at 10:23 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Description."
			REVISION "200605241551Z"		-- May 24, 2006 at 15:51 GMT
			DESCRIPTION 
				"01a08"
			REVISION "200511031513Z"		-- November 03, 2005 at 15:13 GMT
			DESCRIPTION 
				"01a07"
			REVISION "200507281659Z"		-- July 28, 2005 at 16:59 GMT
			DESCRIPTION 
				"01a06"
			REVISION "200505111421Z"		-- May 11, 2005 at 14:21 GMT
			DESCRIPTION 
				"01a05"
			REVISION "200505091111Z"		-- May 09, 2005 at 11:11 GMT
			DESCRIPTION 
				"01a04"
			REVISION "200505051746Z"		-- May 05, 2005 at 17:46 GMT
			DESCRIPTION 
				"01a03"
			REVISION "200505041736Z"		-- May 04, 2005 at 17:36 GMT
			DESCRIPTION 
				"01a02"
			REVISION "200505041202Z"		-- May 04, 2005 at 12:02 GMT
			DESCRIPTION 
				"v01a01"
			::= { wsInfraSysMsg 1 }

		
	
--
-- Type definitions
--
	
		SysMsgSeverity ::= INTEGER
			{
			emergency(0),
			alert(1),
			critical(2),
			error(3),
			warning(4),
			notice(5),
			info(6),
			debug(7)
			}

	
	
--
-- Node definitions
--
	
		-- 1.3.6.1.4.1.388.14.1.3.1.1
		wsInfraSysMsgEnable OBJECT-TYPE
			SYNTAX TruthValue
			MAX-ACCESS read-write
			STATUS current
			DESCRIPTION
				"Enable/Disables logging module."
			::= { wsInfraSysMsgModule 1 }

		
		-- 1.3.6.1.4.1.388.14.1.3.1.2
		wsInfraSysMsgAggTime OBJECT-TYPE
			SYNTAX Integer32 (0..60)
			UNITS "second"
			MAX-ACCESS read-write
			STATUS current
			DESCRIPTION
				"If multiple messages of the same type are received in 
				sysMsgAggTime second, only the first 
				message will be sent followed by another message saying how 
				many times it was repeated.  The follow-up message mechanism will 
				not be implemented in case of Snmp traps.
				
				0 means this feature is disabled."
			::= { wsInfraSysMsgModule 2 }

		
-- Setting for system message output to buffer (local log file)
		-- 1.3.6.1.4.1.388.14.1.3.1.3
		wsInfraSysMsgBuffer OBJECT IDENTIFIER ::= { wsInfraSysMsgModule 3 }

		
		-- 1.3.6.1.4.1.388.14.1.3.1.3.1
		wsInfraSysMsgBufferEnable OBJECT-TYPE
			SYNTAX TruthValue
			MAX-ACCESS read-write
			STATUS current
			DESCRIPTION
				"Enable system message output to buffer (local log file)"
			::= { wsInfraSysMsgBuffer 1 }

		
		-- 1.3.6.1.4.1.388.14.1.3.1.3.2
		wsInfraSysMsgBufferSeverity OBJECT-TYPE
			SYNTAX SysMsgSeverity
			MAX-ACCESS read-write
			STATUS current
			DESCRIPTION
				"If enabled, the system message of severity level of and below 
				wsInfraSysMsgBufferSeverity will be sent."
			::= { wsInfraSysMsgBuffer 2 }

		
		-- 1.3.6.1.4.1.388.14.1.3.1.3.3
		wsInfraSysMsgBufferClear OBJECT-TYPE
			SYNTAX DoActionNow
			MAX-ACCESS read-write
			STATUS current
			DESCRIPTION
				"Clear buffer (local log file)"
			::= { wsInfraSysMsgBuffer 3 }

		
-- Setting for system message output to remote system log server
		-- 1.3.6.1.4.1.388.14.1.3.1.4
		wsInfraSysMsgRemoteSvr OBJECT IDENTIFIER ::= { wsInfraSysMsgModule 4 }

		
		-- 1.3.6.1.4.1.388.14.1.3.1.4.1
		wsInfraSysMsgRemoteSvrEnable OBJECT-TYPE
			SYNTAX TruthValue
			MAX-ACCESS read-write
			STATUS current
			DESCRIPTION
				"Enable system message output to remote system log server"
			::= { wsInfraSysMsgRemoteSvr 1 }

		
		-- 1.3.6.1.4.1.388.14.1.3.1.4.2
		wsInfraSysMsgRemoteSvrSeverity OBJECT-TYPE
			SYNTAX SysMsgSeverity
			MAX-ACCESS read-write
			STATUS current
			DESCRIPTION
				"If enabled, the system message of severity level of and below 
				wsInfraSysMsgRemoteSvrSeverity will be sent."
			::= { wsInfraSysMsgRemoteSvr 2 }

		
		-- 1.3.6.1.4.1.388.14.1.3.1.4.3
		wsInfraSysMsgRemoteSvrFacility OBJECT-TYPE
			SYNTAX INTEGER
				{
				logLocal0(0),
				logLocal1(1),
				logLocal2(2),
				logLocal3(3),
				logLocal4(4),
				logLocal5(5),
				logLocal6(6),
				logLocal7(7)
				}
			MAX-ACCESS read-write
			STATUS current
			DESCRIPTION
				"Used to specify which switch is logging the message."
			::= { wsInfraSysMsgRemoteSvr 3 }

		
		-- 1.3.6.1.4.1.388.14.1.3.1.4.4
		wsInfraSysMsgRemoteSvrTable OBJECT-TYPE
			SYNTAX SEQUENCE OF WsInfraSysMsgRemoteSvrEntry
			MAX-ACCESS not-accessible
			STATUS current
			DESCRIPTION
				"Table of remote log servers"
			::= { wsInfraSysMsgRemoteSvr 4 }

		
		-- 1.3.6.1.4.1.388.14.1.3.1.4.4.1
		wsInfraSysMsgRemoteSvrEntry OBJECT-TYPE
			SYNTAX WsInfraSysMsgRemoteSvrEntry
			MAX-ACCESS not-accessible
			STATUS current
			DESCRIPTION
				" "
			INDEX { wsInfraSysMsgRemoteSvrIndex }
			::= { wsInfraSysMsgRemoteSvrTable 1 }

		
		WsInfraSysMsgRemoteSvrEntry ::=
			SEQUENCE { 
				wsInfraSysMsgRemoteSvrIndex
					INTEGER,
				wsInfraSysMsgRemoteSvrIp
					IpAddress
			 }

		-- 1.3.6.1.4.1.388.14.1.3.1.4.4.1.1
		wsInfraSysMsgRemoteSvrIndex OBJECT-TYPE
			SYNTAX INTEGER (1..255)
			MAX-ACCESS accessible-for-notify
			STATUS current
			DESCRIPTION
				"Simple index"
			::= { wsInfraSysMsgRemoteSvrEntry 1 }

		
		-- 1.3.6.1.4.1.388.14.1.3.1.4.4.1.2
		wsInfraSysMsgRemoteSvrIp OBJECT-TYPE
			SYNTAX IpAddress
			MAX-ACCESS read-write
			STATUS current
			DESCRIPTION
				"Ip of the syslog server.  Row inactive when Ip = 0.0.0.0"
			::= { wsInfraSysMsgRemoteSvrEntry 2 }

		
-- Setting for system message output to console
		-- 1.3.6.1.4.1.388.14.1.3.1.5
		wsInfraSysMsgConsole OBJECT IDENTIFIER ::= { wsInfraSysMsgModule 5 }

		
		-- 1.3.6.1.4.1.388.14.1.3.1.5.1
		wsInfraSysMsgConsoleEnable OBJECT-TYPE
			SYNTAX TruthValue
			MAX-ACCESS read-write
			STATUS current
			DESCRIPTION
				"Enable system message output to console"
			::= { wsInfraSysMsgConsole 1 }

		
		-- 1.3.6.1.4.1.388.14.1.3.1.5.2
		wsInfraSysMsgConsoleSeverity OBJECT-TYPE
			SYNTAX SysMsgSeverity
			MAX-ACCESS read-write
			STATUS current
			DESCRIPTION
				"If enabled, the system message of severity level of and below 
				wsInfraSysMsgConsoleSeverity will be sent."
			::= { wsInfraSysMsgConsole 2 }

		
		-- 1.3.6.1.4.1.388.14.1.3.1.6
		wsInfraSysMsgMIBConformance OBJECT IDENTIFIER ::= { wsInfraSysMsgModule 6 }

		
		-- 1.3.6.1.4.1.388.14.1.3.1.6.1
		wsInfraSysMsgMIBCompliances OBJECT IDENTIFIER ::= { wsInfraSysMsgMIBConformance 1 }

		
		-- 1.3.6.1.4.1.388.14.1.3.1.6.1.1
		wsInfraSysMsgMIBCompliance MODULE-COMPLIANCE
			STATUS current
			DESCRIPTION 
				"Description."
			MODULE -- this module
				MANDATORY-GROUPS { wsInfraSysMsgMIBGroup }
			::= { wsInfraSysMsgMIBCompliances 1 }

		
		-- 1.3.6.1.4.1.388.14.1.3.1.6.2
		wsInfraSysMsgMIBGroups OBJECT IDENTIFIER ::= { wsInfraSysMsgMIBConformance 2 }

		
		-- 1.3.6.1.4.1.388.14.1.3.1.6.2.1
		wsInfraSysMsgMIBGroup OBJECT-GROUP
			OBJECTS { wsInfraSysMsgEnable, wsInfraSysMsgBufferEnable, wsInfraSysMsgBufferSeverity, wsInfraSysMsgBufferClear, wsInfraSysMsgRemoteSvrEnable, 
				wsInfraSysMsgRemoteSvrSeverity, wsInfraSysMsgRemoteSvrFacility, wsInfraSysMsgConsoleEnable, wsInfraSysMsgConsoleSeverity, wsInfraSysMsgRemoteSvrIndex, 
				wsInfraSysMsgRemoteSvrIp, wsInfraSysMsgAggTime }
			STATUS current
			DESCRIPTION 
				"Description."
			::= { wsInfraSysMsgMIBGroups 1 }

		
	
	END

--
-- WS-INFRA-SYSMSG-MIB.my
--
