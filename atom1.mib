-- MIB created 9/24/97 11:30:14, by
--   SMIC (the next generation) version 1.6.31, December 11, 1994.
-- CHANGE LOG
-- 092497 schiang
-- Removed experimental from IMPORTS
-- Moved atmMIB and atmMIBObjects object identifiers to ATM-TC-MIB
-- Changed to import ifIndex from rfc1213.

ATM-MIB DEFINITIONS ::= BEGIN

-- From file: "atm1.mi2"
-- Compile options "4 G A M"

IMPORTS
    IpAddress
	    FROM RFC1155-SMI 
    Counter32, Integer32
            FROM SNMPv2-SMI-v1
    OBJECT-TYPE
            FROM RFC-1212
    mib-2, ifIndex
            FROM RFC1213-MIB
    DisplayString, RowStatus
            FROM SNMPv2-TC-v1
    InterfaceIndex
            FROM IF-MIB
    atmMIB, atmMIBObjects 
	    FROM ATM-TC-MIB 

    AtmAddr, AtmConnKind, AtmConnCastType, AtmServiceCategory, 
    AtmTrafficDescrParamIndex, AtmVpIdentifier, AtmVcIdentifier, 
    AtmVorXAdminStatus, AtmVorXLastChange, AtmVorXOperStatus, 
    atmNoTrafficDescriptor
            FROM ATM-TC-MIB;

--atmMIB OBJECT IDENTIFIER ::= { experimental 41 }
-- MODULE-IDENTITY
--  LastUpdated
--    9701081122Z
--  OrgName
--    IETF AToM MIB Working Group
--  ContactInfo
--              Kaj Tesink
--      Postal:  Bellcore
--               331 Newman Springs Road
--               Red Bank, NJ 07701
--      Tel:     908-758-5254
--      Fax:     908-758-4177
--      E-mail:  kaj@cc.bellcore.com
--  Descr
--    This is the MIB Module for ATM and AAL5-related
--     objects for managing ATM interfaces, ATM virtual
--     links, ATM cross-connects, AAL5 entities, and
--     and AAL5 connections.
--  RevDate
--    9406072245Z
--  RevDescr
--    RFC1695

atmMIBConformance OBJECT IDENTIFIER ::= { atmMIB 2 }
atmMIBGroups    OBJECT IDENTIFIER ::= { atmMIBConformance 1 }
atmMIBCompliances OBJECT IDENTIFIER ::= { atmMIBConformance 2 }

atmInterfaceConfTable OBJECT-TYPE
    SYNTAX SEQUENCE OF AtmInterfaceConfEntry
    ACCESS not-accessible
    STATUS mandatory
    DESCRIPTION
        "This table contains ATM local interface
         configuration parameters, one entry per ATM
         interface port."
    ::= { atmMIBObjects 2 }

atmInterfaceConfEntry OBJECT-TYPE
    SYNTAX AtmInterfaceConfEntry
    ACCESS not-accessible
    STATUS mandatory
    DESCRIPTION
        "This list contains ATM interface configuration
         parameters and state variables and is indexed
         by ifIndex values of ATM interfaces."
    INDEX { ifIndex }
    ::= { atmInterfaceConfTable 1 }

AtmInterfaceConfEntry ::= SEQUENCE {
    atmInterfaceMaxVpcs INTEGER,
    atmInterfaceMaxVccs INTEGER,
    atmInterfaceConfVpcs INTEGER,
    atmInterfaceConfVccs INTEGER,
    atmInterfaceMaxActiveVpiBits INTEGER,
    atmInterfaceMaxActiveVciBits INTEGER,
    atmInterfaceIlmiVpi AtmVpIdentifier,
    atmInterfaceIlmiVci AtmVcIdentifier,
    atmInterfaceAddressType INTEGER,
    atmInterfaceAdminAddr AtmAddr,
    atmInterfaceMyNeighborIpAddress IpAddress,
    atmInterfaceMyNeighborIfName DisplayString,
    atmInterfaceCurrentMaxVpiBits INTEGER,
    atmInterfaceCurrentMaxVciBits INTEGER,
    atmInterfaceSubscrAddress AtmAddr
    }

atmInterfaceMaxVpcs OBJECT-TYPE
    SYNTAX INTEGER(0..4096)
    ACCESS read-write
    STATUS mandatory
    DESCRIPTION
        "The maximum number of VPCs (PVPCs and SVPCs)
         supported at this ATM interface. At the ATM UNI,
         the maximum number of VPCs (PVPCs and SVPCs)
         ranges from 0 to 256 only."
    ::= { atmInterfaceConfEntry 1 }

atmInterfaceMaxVccs OBJECT-TYPE
    SYNTAX INTEGER(0..65536)
    ACCESS read-write
    STATUS mandatory
    DESCRIPTION
        "The maximum number of VCCs (PVCCs and SVCCs)
         supported at this ATM interface."
    ::= { atmInterfaceConfEntry 2 }

atmInterfaceConfVpcs OBJECT-TYPE
    SYNTAX INTEGER(0..4096)
    ACCESS read-only
    STATUS mandatory
    DESCRIPTION
        "The number of VPCs (PVPC, Soft PVPC and SVPC)
         currently in use at this ATM interface.  It includes
         the number of PVPCs and Soft PVPCs that are configured
         at the interface, plus the number of SVPCs
         that are currently  established at the
         interface.
        
         At the ATM UNI, the configured number of
         VPCs (PVPCs and SVPCs) can range from
         0 to 256 only."
    ::= { atmInterfaceConfEntry 3 }

atmInterfaceConfVccs OBJECT-TYPE
    SYNTAX INTEGER(0..65536)
    ACCESS read-only
    STATUS mandatory
    DESCRIPTION
        "The number of VCCs (PVCC, Soft PVCC and SVCC)
         currently in use at this ATM interface.  It includes
         the number of PVCCs and Soft PVCCs that are configured
         at the interface, plus the number of SVCCs
         that are currently  established at the
         interface."
    ::= { atmInterfaceConfEntry 4 }

atmInterfaceMaxActiveVpiBits OBJECT-TYPE
    SYNTAX INTEGER(0..12)
    ACCESS read-write
    STATUS mandatory
    DESCRIPTION
        "The  maximum number of active VPI bits
         configured for use at the ATM interface.
         At the ATM UNI, the maximum number of active
         VPI bits configured for use ranges from
         0 to 8 only."
    ::= { atmInterfaceConfEntry 5 }

atmInterfaceMaxActiveVciBits OBJECT-TYPE
    SYNTAX INTEGER(0..16)
    ACCESS read-write
    STATUS mandatory
    DESCRIPTION
        "The maximum number of active VCI bits
         configured for use at this ATM interface."
    ::= { atmInterfaceConfEntry 6 }

atmInterfaceIlmiVpi OBJECT-TYPE
    SYNTAX AtmVpIdentifier
--    Rsyntax INTEGER(0..4095)
    ACCESS read-write
    STATUS mandatory
    DESCRIPTION
        "The VPI value of the VCC supporting
         the ILMI at this ATM interface.  If the values of
         atmInterfaceIlmiVpi and atmInterfaceIlmiVci are
         both equal to zero then the ILMI is not
         supported at this ATM interface."
    DEFVAL { 0 }
    ::= { atmInterfaceConfEntry 7 }

atmInterfaceIlmiVci OBJECT-TYPE
    SYNTAX AtmVcIdentifier
--    Rsyntax INTEGER(0..65535)
    ACCESS read-write
    STATUS mandatory
    DESCRIPTION
        "The VCI value of the VCC supporting
         the ILMI at this ATM interface.  If the values of
         atmInterfaceIlmiVpi and atmInterfaceIlmiVci are
         both equal to zero then the ILMI is not
         supported at this ATM interface."
    DEFVAL { 16 }
    ::= { atmInterfaceConfEntry 8 }

atmInterfaceAddressType OBJECT-TYPE
    SYNTAX INTEGER {
        private(1),
        nsapE164(2),
        nativeE164(3),
        other(4)
        }
    ACCESS read-only
    STATUS deprecated
    DESCRIPTION
        "The type of primary ATM address configured
         for use at this ATM interface."
    ::= { atmInterfaceConfEntry 9 }

atmInterfaceAdminAddr OBJECT-TYPE
    SYNTAX AtmAddr
--    Rsyntax OCTET STRING(SIZE(0 | 8 | 20))
    ACCESS read-only
    STATUS deprecated
    DESCRIPTION
        "The primary address assigned for administrative purposes,
         for example, an address associated with the
         service provider side of a public network UNI
         (thus, the value of this address corresponds
         with the value of ifPhysAddress at the host side).
         If this interface has no assigned administrative
         address, or when the address used for
         administrative purposes is the same as that used
         for ifPhysAddress, then this is an octet string of
         zero length."
    ::= { atmInterfaceConfEntry 10 }

atmInterfaceMyNeighborIpAddress OBJECT-TYPE
    SYNTAX IpAddress
    ACCESS read-write
    STATUS mandatory
    DESCRIPTION
        "The IP address of the neighbor system connected to
         the  far end of this interface, to which a Network
         Management Station can send SNMP messages, as IP
         datagrams sent to UDP port 161, in order to access
         network management information concerning the
         operation of that system.  Note that the value
         of this object may be obtained in different ways,
         e.g., by manual configuration, or through ILMI
         interaction with the neighbor system."
    ::= { atmInterfaceConfEntry 11 }

atmInterfaceMyNeighborIfName OBJECT-TYPE
    SYNTAX DisplayString
--    Rsyntax OCTET STRING(SIZE(0..255))
    ACCESS read-write
    STATUS mandatory
    DESCRIPTION
        "The textual name of the interface on the neighbor
         system on the far end of this interface, and to
         which this interface connects.  If the neighbor
         system is manageable through SNMP and supports
         the object ifName, the value of this object must
         be identical with that of ifName for the ifEntry
         of the lowest level physical interface
         for this port.  If this interface does not have a
         textual name, the value of this object is a zero
         length string.  Note that the value of this object
         may be obtained in different ways, e.g., by manual
         configuration, or through ILMI interaction with
         the neighbor system."
    ::= { atmInterfaceConfEntry 12 }

atmInterfaceCurrentMaxVpiBits OBJECT-TYPE
    SYNTAX INTEGER(0..12)
    ACCESS read-only
    STATUS mandatory
    DESCRIPTION
        "The maximum number of VPI Bits that may
         currently be used at this ATM interface.
         The value is the minimum of
         atmInterfaceMaxActiveVpiBits, and the
         atmInterfaceMaxActiveVpiBits of the interface's
         UNI/NNI peer.
         If the interface does not negotiate with
         its peer to determine the number of VPI Bits
         that can be used on the interface, then the
         value of this object must equal
         atmInterfaceMaxActiveVpiBits."
    ::= { atmInterfaceConfEntry 13 }

atmInterfaceCurrentMaxVciBits OBJECT-TYPE
    SYNTAX INTEGER(0..16)
    ACCESS read-only
    STATUS mandatory
    DESCRIPTION
        "The maximum number of VCI Bits that may
         currently be used at this ATM interface.
         The value is the minimum of
         atmInterfaceMaxActiveVciBits, and the
         atmInterfaceMaxActiveVpiBits of the interface's
         UNI/NNI peer.
        
         If the interface does not negotiate with
         its peer to determine the number of VCI Bits
         that can be used on the interface, then the
         value of this object must equal
         atmInterfaceMaxActiveVciBits."
    ::= { atmInterfaceConfEntry 14 }

atmInterfaceSubscrAddress OBJECT-TYPE
    SYNTAX AtmAddr
--    Rsyntax OCTET STRING(SIZE(0 | 8 | 20))
    ACCESS read-write
    STATUS mandatory
    DESCRIPTION
        "The identifier assigned by a service provider
         to the network side of a public network UNI.
         If this interface has no assigned service provider
         address, or for other interfaces this is an octet string
         of zero length."
    ::= { atmInterfaceConfEntry 15 }

atmInterfaceDs3PlcpTable OBJECT-TYPE
    SYNTAX SEQUENCE OF AtmInterfaceDs3PlcpEntry
    ACCESS not-accessible
    STATUS mandatory
    DESCRIPTION
        "This table contains ATM interface DS3 PLCP
         parameters and state variables, one entry per
         ATM interface port."
    ::= { atmMIBObjects 3 }

atmInterfaceDs3PlcpEntry OBJECT-TYPE
    SYNTAX AtmInterfaceDs3PlcpEntry
    ACCESS not-accessible
    STATUS mandatory
    DESCRIPTION
        "This list contains DS3 PLCP parameters and
         state variables at the ATM interface and is
         indexed by the ifIndex value of the ATM interface."
    INDEX { ifIndex }
    ::= { atmInterfaceDs3PlcpTable 1 }

AtmInterfaceDs3PlcpEntry ::= SEQUENCE {
    atmInterfaceDs3PlcpSEFSs Counter32,
    atmInterfaceDs3PlcpAlarmState INTEGER,
    atmInterfaceDs3PlcpUASs Counter32
    }

atmInterfaceDs3PlcpSEFSs OBJECT-TYPE
    SYNTAX Counter32
    ACCESS read-only
    STATUS mandatory
    DESCRIPTION
        "The number of DS3 PLCP Severely Errored Framing
         Second (SEFS). Each SEFS represents a
         one-second interval which contains
         one or more SEF event."
    ::= { atmInterfaceDs3PlcpEntry 1 }

atmInterfaceDs3PlcpAlarmState OBJECT-TYPE
    SYNTAX INTEGER {
        noAlarm(1),
        receivedFarEndAlarm(2),
        incomingLOF(3)
        }
    ACCESS read-only
    STATUS mandatory
    DESCRIPTION
        "This variable indicates if there is an
         alarm present for the DS3 PLCP.  The value
         receivedFarEndAlarm means that the DS3 PLCP
         has received an incoming Yellow
         Signal, the value incomingLOF means that
         the DS3 PLCP has declared a loss of frame (LOF)
         failure condition, and the value noAlarm
         means that there are no alarms present.
         Transition from the failure to the no alarm state
         occurs when no defects (e.g., LOF) are received
         for more than 10 seconds."
    ::= { atmInterfaceDs3PlcpEntry 2 }

atmInterfaceDs3PlcpUASs OBJECT-TYPE
    SYNTAX Counter32
    ACCESS read-only
    STATUS mandatory
    DESCRIPTION
        "The counter associated with the number of
         Unavailable Seconds encountered by the PLCP."
    ::= { atmInterfaceDs3PlcpEntry 3 }

atmInterfaceTCTable OBJECT-TYPE
    SYNTAX SEQUENCE OF AtmInterfaceTCEntry
    ACCESS not-accessible
    STATUS mandatory
    DESCRIPTION
        "This table contains ATM interface TC
         Sublayer parameters and state variables,
         one entry per ATM interface port."
    ::= { atmMIBObjects 4 }

atmInterfaceTCEntry OBJECT-TYPE
    SYNTAX AtmInterfaceTCEntry
    ACCESS not-accessible
    STATUS mandatory
    DESCRIPTION
        "This list contains TC Sublayer parameters
         and state variables at the ATM interface and is
         indexed by the ifIndex value of the ATM interface."
    INDEX { ifIndex }
    ::= { atmInterfaceTCTable 1 }

AtmInterfaceTCEntry ::= SEQUENCE {
    atmInterfaceOCDEvents Counter32,
    atmInterfaceTCAlarmState INTEGER
    }

atmInterfaceOCDEvents OBJECT-TYPE
    SYNTAX Counter32
    ACCESS read-only
    STATUS mandatory
    DESCRIPTION
        "The number of times the Out of Cell
         Delineation (OCD) events occur.  If seven
         consecutive ATM cells have Header Error
         Control (HEC) violations, an OCD event occurs.
         A high number of OCD events may indicate a
         problem with the TC Sublayer."
    ::= { atmInterfaceTCEntry 1 }

atmInterfaceTCAlarmState OBJECT-TYPE
    SYNTAX INTEGER {
        noAlarm(1),
        lcdFailure(2)
        }
    ACCESS read-only
    STATUS mandatory
    DESCRIPTION
        "This variable indicates if there is an
         alarm present for the TC Sublayer.  The value
         lcdFailure(2) indicates that the TC Sublayer
         is currently in the Loss of Cell Delineation
         (LCD) defect maintenance state.  The value
         noAlarm(1) indicates that the TC Sublayer
         is currently not in the LCD defect
         maintenance state."
    ::= { atmInterfaceTCEntry 2 }

atmTrafficDescrParamTable OBJECT-TYPE
    SYNTAX SEQUENCE OF AtmTrafficDescrParamEntry
    ACCESS not-accessible
    STATUS mandatory
    DESCRIPTION
        "This table contains information on ATM traffic
         descriptor type and the associated parameters."
    ::= { atmMIBObjects 5 }

atmTrafficDescrParamEntry OBJECT-TYPE
    SYNTAX AtmTrafficDescrParamEntry
    ACCESS not-accessible
    STATUS mandatory
    DESCRIPTION
        "This list contains ATM traffic descriptor
         type and the associated parameters."
    INDEX { atmTrafficDescrParamIndex }
    ::= { atmTrafficDescrParamTable 1 }

AtmTrafficDescrParamEntry ::= SEQUENCE {
    atmTrafficDescrParamIndex AtmTrafficDescrParamIndex,
    atmTrafficDescrType OBJECT IDENTIFIER,
    atmTrafficDescrParam1 Integer32,
    atmTrafficDescrParam2 Integer32,
    atmTrafficDescrParam3 Integer32,
    atmTrafficDescrParam4 Integer32,
    atmTrafficDescrParam5 Integer32,
    atmTrafficQoSClass INTEGER,
    atmTrafficDescrRowStatus RowStatus,
    atmServiceCategory AtmServiceCategory
    }

atmTrafficDescrParamIndex OBJECT-TYPE
    SYNTAX AtmTrafficDescrParamIndex
--    Rsyntax INTEGER(0..2147483647)
    ACCESS not-accessible
    STATUS mandatory
    DESCRIPTION
        "This object is used by the virtual link
         table (i.e., VPL or VCL table)
         to identify the row of this table.
         When creating a new row in the table
         the value of this index may be obtained
         by retrieving the value of
         atmTrafficDescrParamIndexNext."
    ::= { atmTrafficDescrParamEntry 1 }

atmTrafficDescrType OBJECT-TYPE
    SYNTAX OBJECT IDENTIFIER
    ACCESS read-write
    STATUS mandatory
    DESCRIPTION
        "The value of this object identifies the type
         of ATM traffic descriptor.
         The type may indicate no traffic descriptor or
         traffic descriptor with one or more parameters.
         These parameters are specified as a parameter
         vector, in the corresponding instances of the
         objects:
             atmTrafficDescrParam1
             atmTrafficDescrParam2
             atmTrafficDescrParam3
             atmTrafficDescrParam4
             atmTrafficDescrParam5."
    DEFVAL { atmNoTrafficDescriptor }
    ::= { atmTrafficDescrParamEntry 2 }

atmTrafficDescrParam1 OBJECT-TYPE
    SYNTAX Integer32
    ACCESS read-write
    STATUS mandatory
    DESCRIPTION
        "The first parameter of the ATM traffic descriptor
         used according to the value of
         atmTrafficDescrType."
    DEFVAL { 0 }
    ::= { atmTrafficDescrParamEntry 3 }

atmTrafficDescrParam2 OBJECT-TYPE
    SYNTAX Integer32
    ACCESS read-write
    STATUS mandatory
    DESCRIPTION
        "The second parameter of the ATM traffic descriptor
         used according to the value of
         atmTrafficDescrType."
    DEFVAL { 0 }
    ::= { atmTrafficDescrParamEntry 4 }

atmTrafficDescrParam3 OBJECT-TYPE
    SYNTAX Integer32
    ACCESS read-write
    STATUS mandatory
    DESCRIPTION
        "The third parameter of the ATM traffic descriptor
         used according to the value of atmTrafficDescrType."
    DEFVAL { 0 }
    ::= { atmTrafficDescrParamEntry 5 }

atmTrafficDescrParam4 OBJECT-TYPE
    SYNTAX Integer32
    ACCESS read-write
    STATUS mandatory
    DESCRIPTION
        "The fourth parameter of the ATM traffic descriptor
         used according to the value of
         atmTrafficDescrType."
    DEFVAL { 0 }
    ::= { atmTrafficDescrParamEntry 6 }

atmTrafficDescrParam5 OBJECT-TYPE
    SYNTAX Integer32
    ACCESS read-write
    STATUS mandatory
    DESCRIPTION
        "The fifth parameter of the ATM traffic descriptor
         used according to the value of
         atmTrafficDescrType."
    DEFVAL { 0 }
    ::= { atmTrafficDescrParamEntry 7 }

atmTrafficQoSClass OBJECT-TYPE
    SYNTAX INTEGER(0..255)
    ACCESS read-write
    STATUS deprecated
    DESCRIPTION
        "The value of this object identifies the QoS Class.
         Four Service classes have been
         specified in the ATM Forum UNI Specification:
         Service Class A: Constant bit rate video and
                          Circuit emulation
         Service Class B: Variable bit rate video/audio
         Service Class C: Connection-oriented data
         Service Class D: Connectionless data
         Four QoS classes numbered 1, 2, 3, and 4 have
         been specified with the aim to support service
         classes A, B, C, and D respectively.
         An unspecified QoS Class numbered `0' is used
         for best effort traffic."
    DEFVAL { 0 }
    ::= { atmTrafficDescrParamEntry 8 }

atmTrafficDescrRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create
         a new row or modify or delete an
         existing row in this table."
    DEFVAL { active }
    ::= { atmTrafficDescrParamEntry 9 }

atmServiceCategory OBJECT-TYPE
    SYNTAX AtmServiceCategory
--    Rsyntax INTEGER {
--        other(1),
--        cbr(2),
--        rtVbr(3),
--        nrtVbr(4),
--        abr(5),
--        ubr(6)
--        }
    ACCESS read-write
    STATUS mandatory
    DESCRIPTION
        " The ATM service category."
    DEFVAL { ubr }
    ::= { atmTrafficDescrParamEntry 10 }

atmVplTable OBJECT-TYPE
    SYNTAX SEQUENCE OF AtmVplEntry
    ACCESS not-accessible
    STATUS mandatory
    DESCRIPTION
        "The Virtual Path Link (VPL) table.  A
         bi-directional VPL is modeled as one entry
         in this table."
    ::= { atmMIBObjects 6 }

atmVplEntry OBJECT-TYPE
    SYNTAX AtmVplEntry
    ACCESS not-accessible
    STATUS mandatory
    DESCRIPTION
        "An entry in the VPL table.  This entry is
         used to model a bi-directional VPL.
         To create a VPL at an ATM interface,
         either of the following procedures are used:
        
         Negotiated VPL establishment
        
        (1) The management application creates
           a VPL entry in the atmVplTable
           by setting atmVplRowStatus to createAndWait(5).
           This may fail for the following reasons:
           - The selected VPI value is unavailable,
           - The selected VPI value is in use.
           Otherwise, the agent creates a row and
           reserves the VPI value on that port.
        
        (2) The manager selects an existing row(s) in the
           atmTrafficDescrParamTable,
           thereby, selecting a set of self-consistent
           ATM traffic parameters and the service category
           for receive and transmit directions of the VPL.
        
        (2a) If no suitable row(s) in the
           atmTrafficDescrParamTable exists,
           the manager must create a new row(s)
           in that table.
        
        (2b) The manager characterizes the VPL's traffic
           parameters through setting the
           atmVplReceiveTrafficDescrIndex and the
           atmVplTransmitTrafficDescrIndex values
           in the VPL table, which point to the rows
           containing desired ATM traffic parameter values
           in the atmTrafficDescrParamTable.  The agent
           will check the availability of resources and
           may refuse the request.
           If the transmit and receive service categories
           are inconsistent, the agent should refuse the
           request.
        
        (3) The manager activates the VPL by setting the
           the atmVplRowStatus to active(1).
           If this set is successful, the agent has
           reserved the resources to satisfy the requested
           traffic parameter values and the service category
           for that VPL.
        
        (4) If the VPL terminates a VPC in the ATM host
           or switch, the manager turns on the
           atmVplAdminStatus to up(1) to turn the VPL
           traffic flow on.  Otherwise, the
           atmVpCrossConnectTable  must be used
           to cross-connect the VPL to another VPL(s)
           in an ATM switch or network.
        
         One-Shot VPL Establishment
        
         A VPL may also be established in one step by a
         set-request with all necessary VPL parameter
         values and atmVplRowStatus set to createAndGo(4).
        
         In contrast to the negotiated VPL establishment
         which allows for detailed error checking
         (i.e., set errors are explicitly linked to
         particular resource acquisition failures),
         the one-shot VPL establishment
         performs the setup on one operation but
         does not have the advantage of step-wise
         error checking.
        
         VPL Retirement
        
         A VPL is released by setting atmVplRowStatus to
         destroy(6), and the agent may release all
         associated resources."
    INDEX { ifIndex, atmVplVpi }
    ::= { atmVplTable 1 }

AtmVplEntry ::= SEQUENCE {
    atmVplVpi AtmVpIdentifier,
    atmVplAdminStatus AtmVorXAdminStatus,
    atmVplOperStatus AtmVorXOperStatus,
    atmVplLastChange AtmVorXLastChange,
    atmVplReceiveTrafficDescrIndex AtmTrafficDescrParamIndex,
    atmVplTransmitTrafficDescrIndex AtmTrafficDescrParamIndex,
    atmVplCrossConnectIdentifier INTEGER,
    atmVplRowStatus RowStatus,
    atmVplCastType AtmConnCastType,
    atmVplConnKind AtmConnKind
    }

atmVplVpi OBJECT-TYPE
    SYNTAX AtmVpIdentifier
--    Rsyntax INTEGER(0..4095)
    ACCESS not-accessible
    STATUS mandatory
    DESCRIPTION
        "The VPI value of the VPL."
    ::= { atmVplEntry 1 }

atmVplAdminStatus OBJECT-TYPE
    SYNTAX AtmVorXAdminStatus
--    Rsyntax INTEGER {
--        up(1),
--        down(2)
--        }
    ACCESS read-write
    STATUS mandatory
    DESCRIPTION
        "This object is implemented only for a VPL
         which terminates a VPC (i.e., one which is
         NOT cross-connected to other VPLs).
         Its value specifies the desired
         administrative state of the VPL."
    DEFVAL { down }
    ::= { atmVplEntry 2 }

atmVplOperStatus OBJECT-TYPE
    SYNTAX AtmVorXOperStatus
--    Rsyntax INTEGER {
--        up(1),
--        down(2),
--        unknown(3)
--        }
    ACCESS read-only
    STATUS mandatory
    DESCRIPTION
        "The current operational status of the VPL."
    ::= { atmVplEntry 3 }

atmVplLastChange OBJECT-TYPE
    SYNTAX AtmVorXLastChange
--    Rsyntax TimeTicks
    ACCESS read-only
    STATUS mandatory
    DESCRIPTION
        "The value of sysUpTime at the time this
         VPL entered its current operational state."
    ::= { atmVplEntry 4 }

atmVplReceiveTrafficDescrIndex OBJECT-TYPE
    SYNTAX AtmTrafficDescrParamIndex
--    Rsyntax INTEGER(0..2147483647)
    ACCESS read-write
    STATUS mandatory
    DESCRIPTION
        "The value of this object identifies the row
         in the atmTrafficDescrParamTable which
         applies to the receive direction of the VPL."
    DEFVAL { 0 }
    ::= { atmVplEntry 5 }

atmVplTransmitTrafficDescrIndex OBJECT-TYPE
    SYNTAX AtmTrafficDescrParamIndex
--    Rsyntax INTEGER(0..2147483647)
    ACCESS read-write
    STATUS mandatory
    DESCRIPTION
        "The value of this object identifies the row
         in the atmTrafficDescrParamTable which
         applies to the transmit direction of the VPL."
    DEFVAL { 0 }
    ::= { atmVplEntry 6 }

atmVplCrossConnectIdentifier OBJECT-TYPE
    SYNTAX INTEGER(0..2147483647)
    ACCESS read-only
    STATUS mandatory
    DESCRIPTION
        "This object is implemented only for a VPL
         which is cross-connected to other VPLs
         that belong to the same VPC.  All such
         associated VPLs have the same value of this
         object, and all their cross-connections are
         identified by entries in the
         atmVpCrossConnectTable for which
         atmVpCrossConnectIndex has the same value.
         The value of this object is initialized by the
         agent after the associated entries in the
         atmVpCrossConnectTable have been created."
    ::= { atmVplEntry 7 }

atmVplRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create, delete
         or modify a row in this table.
         To create a new VCL, this object is
         initially set to 'createAndWait' or
         'createAndGo'.  This object should not be
         set to 'active' unless the following columnar
         objects have been set to their desired value
         in this row:
         atmVplReceiveTrafficDescrIndex and
         atmVplTransmitTrafficDescrIndex."
    DEFVAL { active }
    ::= { atmVplEntry 8 }

atmVplCastType OBJECT-TYPE
    SYNTAX AtmConnCastType
--    Rsyntax INTEGER {
--        p2p(1),
--        p2mpRoot(2),
--        p2mpLeaf(3)
--        }
    ACCESS read-write
    STATUS mandatory
    DESCRIPTION
        "The connection topology type."
    DEFVAL { p2p }
    ::= { atmVplEntry 9 }

atmVplConnKind OBJECT-TYPE
    SYNTAX AtmConnKind
--    Rsyntax INTEGER {
--        pvc(1),
--        svcIncoming(2),
--        svcOutgoing(3),
--        spvcInitiator(4),
--        spvcTarget(5)
--        }
    ACCESS read-write
    STATUS mandatory
    DESCRIPTION
        "The use of call control."
    DEFVAL { pvc }
    ::= { atmVplEntry 10 }

atmVclTable OBJECT-TYPE
    SYNTAX SEQUENCE OF AtmVclEntry
    ACCESS not-accessible
    STATUS mandatory
    DESCRIPTION
        "The Virtual Channel Link (VCL) table.  A
         bi-directional VCL is modeled as one entry
         in this table."
    ::= { atmMIBObjects 7 }

atmVclEntry OBJECT-TYPE
    SYNTAX AtmVclEntry
    ACCESS not-accessible
    STATUS mandatory
    DESCRIPTION
        "An entry in the VCL table. This entry is
         used to model a bi-directional VCL.
         To create a VCL at an ATM interface,
         either of the following procedures are used:
        
         Negotiated VCL establishment
        
        (1) The management application creates
           a VCL entry in the atmVclTable
           by setting atmVclRowStatus to createAndWait(5).
           This may fail for the following reasons:
           - The selected VPI/VCI values are unavailable,
           - The selected VPI/VCI values are in use.
           Otherwise, the agent creates a row and
           reserves the VPI/VCI values on that port.
        
        (2) The manager selects an existing row(s) in the
           atmTrafficDescrParamTable,
           thereby, selecting a set of self-consistent
           ATM traffic parameters and the service category
           for receive and transmit directions of the VCL.
        
        (2a) If no suitable row(s) in the
           atmTrafficDescrParamTable exists,
           the manager must create a new row(s)
           in that table.
        
        (2b) The manager characterizes the VCL's traffic
           parameters through setting the
           atmVclReceiveTrafficDescrIndex and the
           atmVclTransmitTrafficDescrIndex values
           in the VCL table, which point to the rows
           containing desired ATM traffic parameter values
           in the atmTrafficDescrParamTable.  The agent
           will check the availability of resources and
           may refuse the request.
           If the transmit and receive service categories
           are inconsistent, the agent should refuse the
           request.
        
        (3) The manager activates the VCL by setting the
           the atmVclRowStatus to active(1) (for
           requirements on this activation see the
           description of atmVclRowStatus).
           If this set is successful, the agent has
           reserved the resources to satisfy the requested
           traffic parameter values and the service category
           for that VCL.
        (4) If the VCL terminates a VCC in the ATM host
           or switch, the manager turns on the
           atmVclAdminStatus to up(1) to turn the VCL
           traffic flow on.  Otherwise, the
           atmVcCrossConnectTable  must be used
           to cross-connect the VCL to another VCL(s)
           in an ATM switch or network.
        
        One-Shot VCL Establishment
        
        A VCL may also be established in one step by a
        set-request with all necessary VCL parameter
        values and atmVclRowStatus set to createAndGo(4).
        
        In contrast to the negotiated VCL establishment
        which allows for detailed error checking
        (i.e., set errors are explicitly linked to
        particular resource acquisition failures),
        the one-shot VCL establishment
        performs the setup on one operation but
        does not have the advantage of step-wise
        error checking.
        
        VCL Retirement
        
        A VCL is released by setting atmVclRowStatus to
        destroy(6), and the agent may release all
        associated resources."
    INDEX { ifIndex, atmVclVpi, atmVclVci }
    ::= { atmVclTable 1 }

AtmVclEntry ::= SEQUENCE {
    atmVclVpi AtmVpIdentifier,
    atmVclVci AtmVcIdentifier,
    atmVclAdminStatus AtmVorXAdminStatus,
    atmVclOperStatus AtmVorXOperStatus,
    atmVclLastChange AtmVorXLastChange,
    atmVclReceiveTrafficDescrIndex AtmTrafficDescrParamIndex,
    atmVclTransmitTrafficDescrIndex AtmTrafficDescrParamIndex,
    atmVccAalType INTEGER,
    atmVccAal5CpcsTransmitSduSize INTEGER,
    atmVccAal5CpcsReceiveSduSize INTEGER,
    atmVccAal5EncapsType INTEGER,
    atmVclCrossConnectIdentifier INTEGER,
    atmVclRowStatus RowStatus,
    atmVclCastType AtmConnCastType,
    atmVclConnKind AtmConnKind
    }

atmVclVpi OBJECT-TYPE
    SYNTAX AtmVpIdentifier
--    Rsyntax INTEGER(0..4095)
    ACCESS not-accessible
    STATUS mandatory
    DESCRIPTION
        "The VPI value of the VCL."
    ::= { atmVclEntry 1 }

atmVclVci OBJECT-TYPE
    SYNTAX AtmVcIdentifier
--    Rsyntax INTEGER(0..65535)
    ACCESS not-accessible
    STATUS mandatory
    DESCRIPTION
        "The VCI value of the VCL."
    ::= { atmVclEntry 2 }

atmVclAdminStatus OBJECT-TYPE
    SYNTAX AtmVorXAdminStatus
--    Rsyntax INTEGER {
--        up(1),
--        down(2)
--        }
    ACCESS read-write
    STATUS mandatory
    DESCRIPTION
        "This object is implemented only for a VCL which
         terminates a VCC (i.e., one which is NOT
         cross-connected to other VCLs). Its value
         specifies the desired administrative state of
         the VCL."
    DEFVAL { down }
    ::= { atmVclEntry 3 }

atmVclOperStatus OBJECT-TYPE
    SYNTAX AtmVorXOperStatus
--    Rsyntax INTEGER {
--        up(1),
--        down(2),
--        unknown(3)
--        }
    ACCESS read-only
    STATUS mandatory
    DESCRIPTION
        "The current operational status of the VCL."
    ::= { atmVclEntry 4 }

atmVclLastChange OBJECT-TYPE
    SYNTAX AtmVorXLastChange
--    Rsyntax TimeTicks
    ACCESS read-only
    STATUS mandatory
    DESCRIPTION
        "The value of sysUpTime at the time this VCL
         entered its current operational state."
    ::= { atmVclEntry 5 }

atmVclReceiveTrafficDescrIndex OBJECT-TYPE
    SYNTAX AtmTrafficDescrParamIndex
--    Rsyntax INTEGER(0..2147483647)
    ACCESS read-write
    STATUS mandatory
    DESCRIPTION
        "The value of this object identifies the row
         in the ATM Traffic Descriptor Table which
         applies to the receive direction of this VCL."
    DEFVAL { 0 }
    ::= { atmVclEntry 6 }

atmVclTransmitTrafficDescrIndex OBJECT-TYPE
    SYNTAX AtmTrafficDescrParamIndex
--    Rsyntax INTEGER(0..2147483647)
    ACCESS read-write
    STATUS mandatory
    DESCRIPTION
        "The value of this object identifies the row
         of the ATM Traffic Descriptor Table which applies
         to the transmit direction of this VCL."
    DEFVAL { 0 }
    ::= { atmVclEntry 7 }

atmVccAalType OBJECT-TYPE
    SYNTAX INTEGER {
        aal1(1),
        aal34(2),
        aal5(3),
        other(4),
        unknown(5)
        }
    ACCESS read-write
    STATUS mandatory
    DESCRIPTION
        "An instance of this object only exists when the
         local VCL end-point is also the VCC end-point,
         and AAL is in use.
         The type of AAL used on this VCC.
         The AAL type includes AAL1, AAL3/4,
         and AAL5. The other(4) may be user-defined
         AAL type.  The unknown type indicates that
         the AAL type cannot be determined."
    DEFVAL { aal5 }
    ::= { atmVclEntry 8 }

atmVccAal5CpcsTransmitSduSize OBJECT-TYPE
    SYNTAX INTEGER(1..65535)
    ACCESS read-write
    STATUS mandatory
    DESCRIPTION
        "An instance of this object only exists when the
         local VCL end-point is also the VCC end-point,
         and AAL5 is in use.
         The maximum AAL5 CPCS SDU size in octets that is
         supported on the transmit direction of this VCC."
    DEFVAL { 9188 }
    ::= { atmVclEntry 9 }

atmVccAal5CpcsReceiveSduSize OBJECT-TYPE
    SYNTAX INTEGER(1..65535)
    ACCESS read-write
    STATUS mandatory
    DESCRIPTION
        "An instance of this object only exists when the
         local VCL end-point is also the VCC end-point,
         and AAL5 is in use.
         The maximum AAL5 CPCS SDU size in octets that is
         supported on the receive direction of this VCC."
    DEFVAL { 9188 }
    ::= { atmVclEntry 10 }

atmVccAal5EncapsType OBJECT-TYPE
    SYNTAX INTEGER {
        vcMultiplexRoutedProtocol(1),
        vcMultiplexBridgedProtocol8023(2),
        vcMultiplexBridgedProtocol8025(3),
        vcMultiplexBridgedProtocol8026(4),
        vcMultiplexLANemulation8023(5),
        vcMultiplexLANemulation8025(6),
        llcEncapsulation(7),
        multiprotocolFrameRelaySscs(8),
        other(9),
        unknown(10)
        }
    ACCESS read-write
    STATUS mandatory
    DESCRIPTION
        "An instance of this object only exists when the
         local VCL end-point is also the VCC end-point,
         and AAL5 is in use.
         The type of data encapsulation used over
         the AAL5 SSCS layer. The definitions reference
         RFC 1483 Multiprotocol Encapsulation
         over ATM AAL5 and to the ATM Forum
         LAN Emulation specification."
    DEFVAL { llcEncapsulation }
    ::= { atmVclEntry 11 }

atmVclCrossConnectIdentifier OBJECT-TYPE
    SYNTAX INTEGER(0..2147483647)
    ACCESS read-only
    STATUS mandatory
    DESCRIPTION
        "This object is implemented only for a VCL
         which is cross-connected to other VCLs
         that belong to the same VCC.  All such
         associated VCLs have the same value of this
         object, and all their cross-connections are
         identified by entries in the
         atmVcCrossConnectTable for which
         atmVcCrossConnectIndex has the same value.
         The value of this object is initialized by the
         agent after the associated entries in the
         atmVcCrossConnectTable have been created."
    ::= { atmVclEntry 12 }

atmVclRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create, delete or
         modify a row in this table.  To create
         a new VCL, this object is initially set
         to 'createAndWait' or 'createAndGo'.
         This object should not be
         set to 'active' unless the following columnar
         objects have been set to their desired value
         in this row:
         atmVclReceiveTrafficDescrIndex,
         atmVclTransmitTrafficDescrIndex.
         In addition, if the local VCL end-point
         is also the VCC end-point:
         atmVccAalType.
         In addition, for AAL5 connections only:
         atmVccAal5CpcsTransmitSduSize,
         atmVccAal5CpcsReceiveSduSize, and
         atmVccAal5EncapsType. (The existence
         of these objects imply the AAL connection type.)"
    DEFVAL { active }
    ::= { atmVclEntry 13 }

atmVclCastType OBJECT-TYPE
    SYNTAX AtmConnCastType
--    Rsyntax INTEGER {
--        p2p(1),
--        p2mpRoot(2),
--        p2mpLeaf(3)
--        }
    ACCESS read-write
    STATUS mandatory
    DESCRIPTION
        "The connection topology type."
    DEFVAL { p2p }
    ::= { atmVclEntry 14 }

atmVclConnKind OBJECT-TYPE
    SYNTAX AtmConnKind
--    Rsyntax INTEGER {
--        pvc(1),
--        svcIncoming(2),
--        svcOutgoing(3),
--        spvcInitiator(4),
--        spvcTarget(5)
--        }
    ACCESS read-write
    STATUS mandatory
    DESCRIPTION
        "The use of call control."
    DEFVAL { pvc }
    ::= { atmVclEntry 15 }

atmVpCrossConnectIndexNext OBJECT-TYPE
    SYNTAX INTEGER(0..2147483647)
    ACCESS read-only
    STATUS mandatory
    DESCRIPTION
        "This object contains an appropriate value to
         be used for atmVpCrossConnectIndex when creating
         entries in the atmVpCrossConnectTable.  The value
         0 indicates that no unassigned entries are
         available. To obtain the atmVpCrossConnectIndex
         value for a new entry, the manager issues a
         management protocol retrieval operation to obtain
         the current value of this object.  After each
         retrieval, the agent should modify the value to
         the next unassigned index."
    ::= { atmMIBObjects 8 }

atmVpCrossConnectTable OBJECT-TYPE
    SYNTAX SEQUENCE OF AtmVpCrossConnectEntry
    ACCESS not-accessible
    STATUS mandatory
    DESCRIPTION
        "The ATM VP Cross Connect table.  A bi-
         directional VP cross-connect which
         cross-connects two VPLs is modeled
         as one entry in this table."
    ::= { atmMIBObjects 9 }

atmVpCrossConnectEntry OBJECT-TYPE
    SYNTAX AtmVpCrossConnectEntry
    ACCESS not-accessible
    STATUS mandatory
    DESCRIPTION
        "An entry in the ATM VP Cross Connect table.
         This entry is used to model a bi-directional
         ATM VP cross-connect which cross-connects
         two VPLs.
        
         Step-wise Procedures to set up a VP Cross-connect
        
         Once the entries in the atmVplTable are created,
         the following procedures are used
         to cross-connect the VPLs together.
        
        (1) The manager obtains a unique
            atmVpCrossConnectIndex by reading the
            atmVpCrossConnectIndexNext object.
        
        (2) Next, the manager creates a set of one
            or more rows in the ATM VP Cross Connect
            Table, one for each cross-connection between
            two VPLs.  Each row is indexed by the ATM
            interface port numbers and VPI values of the
            two ends of that cross-connection.
            This set of rows specifies the topology of the
            VPC cross-connect and is identified by a single
            value of atmVpCrossConnectIndex.
        
         Negotiated VP Cross-Connect Establishment
        
        (2a) The manager creates a row in this table by
            setting atmVpCrossConnectRowStatus to
            createAndWait(5).  The agent checks the
            requested topology and the mutual sanity of
            the ATM traffic parameters and
            service categories, i.e., the row creation
            fails if:
            - the requested topology is incompatible with
              associated values of atmVplCastType,
            - the requested topology is not supported
              by the agent,
            - the traffic/service category parameter values
              associated with the requested row are
              incompatible with those of already existing
              rows for this VP cross-connect.
            [For example, for setting up
            a point-to-point VP cross-connect, the
            ATM traffic parameters in the receive direction
            of a VPL at the low end of the cross-connect
            must equal to the traffic parameters in the
            transmit direction of the other VPL at the
            high end of the cross-connect,
            otherwise, the row creation fails.]
            The agent also checks for internal errors
            in building the cross-connect.
        
            The atmVpCrossConnectIndex values in the
            corresponding atmVplTable rows are filled
            in by the agent at this point.
        
        (2b) The manager promotes the row in the
            atmVpCrossConnectTable by setting
            atmVpCrossConnectRowStatus to active(1).  If
            this set is successful, the agent has reserved
            the resources specified by the ATM traffic
            parameter and Service category values
            for each direction of the VP cross-connect
            in an ATM switch or network.
        
        (3) The manager sets the
            atmVpCrossConnectAdminStatus to up(1) in all
            rows of this VP cross-connect to turn the
            traffic flow on.
        
        
         One-Shot VP Cross-Connect Establishment
        
         A VP cross-connect may also be established in
         one step by a set-request with all necessary
         parameter values and atmVpCrossConnectRowStatus
         set to createAndGo(4).
        
         In contrast to the negotiated VP cross-connect
         establishment which allows for detailed error
         checking (i.e., set errors are explicitly linked
         to particular resource acquisition failures),
         the one-shot VP cross-connect establishment
         performs the setup on one operation but does not
         have the advantage of step-wise error checking.
        
         VP Cross-Connect Retirement
        
         A VP cross-connect identified by a particular
         value of atmVpCrossConnectIndex is released by:
        
        (1) Setting atmVpCrossConnectRowStatus of all
            rows identified by this value of
            atmVpCrossConnectIndex to destroy(6).
            The agent may release all
            associated resources, and the
            atmVpCrossConnectIndex values in the
            corresponding atmVplTable row are removed.
            Note that a situation when only a subset of
            the associated rows are deleted corresponds
            to a VP topology change.
        
        (2) After deletion of the appropriate
            atmVpCrossConnectEntries, the manager may
            set atmVplRowStatus to destroy(6) the
            associated VPLs.  The agent releases
            the resources and removes the associated
            rows in the atmVplTable.
        
         VP Cross-connect Reconfiguration
        
         At the discretion of the agent, a VP
         cross-connect may be reconfigured by
         adding and/or deleting leafs to/from
         the VP topology as per the VP cross-connect
         establishment/retirement procedures.
         Reconfiguration of traffic/service category parameter
         values requires release of the VP cross-connect
         before those parameter values may by changed
         for individual VPLs."
    INDEX { atmVpCrossConnectIndex, atmVpCrossConnectLowIfIndex, atmVpCrossConnectLowVpi, atmVpCrossConnectHighIfIndex, atmVpCrossConnectHighVpi }
    ::= { atmVpCrossConnectTable 1 }

AtmVpCrossConnectEntry ::= SEQUENCE {
    atmVpCrossConnectIndex INTEGER,
    atmVpCrossConnectLowIfIndex InterfaceIndex,
    atmVpCrossConnectLowVpi AtmVpIdentifier,
    atmVpCrossConnectHighIfIndex InterfaceIndex,
    atmVpCrossConnectHighVpi AtmVpIdentifier,
    atmVpCrossConnectAdminStatus AtmVorXAdminStatus,
    atmVpCrossConnectL2HOperStatus AtmVorXOperStatus,
    atmVpCrossConnectH2LOperStatus AtmVorXOperStatus,
    atmVpCrossConnectL2HLastChange AtmVorXLastChange,
    atmVpCrossConnectH2LLastChange AtmVorXLastChange,
    atmVpCrossConnectRowStatus RowStatus
    }

atmVpCrossConnectIndex OBJECT-TYPE
    SYNTAX INTEGER(1..2147483647)
    ACCESS not-accessible
    STATUS mandatory
    DESCRIPTION
        "A unique value to identify this VP cross-connect."
    ::= { atmVpCrossConnectEntry 1 }

atmVpCrossConnectLowIfIndex OBJECT-TYPE
    SYNTAX InterfaceIndex
--    Rsyntax Integer32
    ACCESS not-accessible
    STATUS mandatory
    DESCRIPTION
        "The ifIndex value of the ATM interface for
         this VP cross-connect. The term low implies
         that this ATM interface has the numerically lower
         ifIndex value than the other ATM interface
         identified in the same atmVpCrossConnectEntry."
    ::= { atmVpCrossConnectEntry 2 }

atmVpCrossConnectLowVpi OBJECT-TYPE
    SYNTAX AtmVpIdentifier
--    Rsyntax INTEGER(0..4095)
    ACCESS not-accessible
    STATUS mandatory
    DESCRIPTION
        "The VPI value at the ATM interface
         associated with the VP cross-connect that is
         identified by atmVpCrossConnectLowIfIndex."
    ::= { atmVpCrossConnectEntry 3 }

atmVpCrossConnectHighIfIndex OBJECT-TYPE
    SYNTAX InterfaceIndex
--    Rsyntax Integer32
    ACCESS not-accessible
    STATUS mandatory
    DESCRIPTION
        "The ifIndex value of the ATM interface for
         this VP cross-connect. The term high implies that
         this ATM interface has the numerically higher
         ifIndex value than the  other ATM interface
         identified in the same atmVpCrossConnectEntry."
    ::= { atmVpCrossConnectEntry 4 }

atmVpCrossConnectHighVpi OBJECT-TYPE
    SYNTAX AtmVpIdentifier
--    Rsyntax INTEGER(0..4095)
    ACCESS not-accessible
    STATUS mandatory
    DESCRIPTION
        "The VPI value at the ATM interface
         associated with the VP cross-connect that is
         identified by atmVpCrossConnectHighIfIndex."
    ::= { atmVpCrossConnectEntry 5 }

atmVpCrossConnectAdminStatus OBJECT-TYPE
    SYNTAX AtmVorXAdminStatus
--    Rsyntax INTEGER {
--        up(1),
--        down(2)
--        }
    ACCESS read-write
    STATUS mandatory
    DESCRIPTION
        "The desired administrative status of this
         bi-directional VP cross-connect."
    DEFVAL { down }
    ::= { atmVpCrossConnectEntry 6 }

atmVpCrossConnectL2HOperStatus OBJECT-TYPE
    SYNTAX AtmVorXOperStatus
--    Rsyntax INTEGER {
--        up(1),
--        down(2),
--        unknown(3)
--        }
    ACCESS read-only
    STATUS mandatory
    DESCRIPTION
        "The operational status of the VP cross-connect
         in one direction; (i.e., from the low to
         high direction)."
    ::= { atmVpCrossConnectEntry 7 }

atmVpCrossConnectH2LOperStatus OBJECT-TYPE
    SYNTAX AtmVorXOperStatus
--    Rsyntax INTEGER {
--        up(1),
--        down(2),
--        unknown(3)
--        }
    ACCESS read-only
    STATUS mandatory
    DESCRIPTION
        "The operational status of the VP cross-connect
         in one direction; (i.e., from the high to
         low direction)."
    ::= { atmVpCrossConnectEntry 8 }

atmVpCrossConnectL2HLastChange OBJECT-TYPE
    SYNTAX AtmVorXLastChange
--    Rsyntax TimeTicks
    ACCESS read-only
    STATUS mandatory
    DESCRIPTION
        "The value of sysUpTime at the time this
         VP cross-connect entered its current operational
         state in the low to high direction."
    ::= { atmVpCrossConnectEntry 9 }

atmVpCrossConnectH2LLastChange OBJECT-TYPE
    SYNTAX AtmVorXLastChange
--    Rsyntax TimeTicks
    ACCESS read-only
    STATUS mandatory
    DESCRIPTION
        "The value of sysUpTime at the time this
        VP cross-connect entered its current operational
        in the high to low direction."
    ::= { atmVpCrossConnectEntry 10 }

atmVpCrossConnectRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this entry in the
         atmVpCrossConnectTable.  This object is used to
         create a cross-connect for cross-connecting
         VPLs which are created using the atmVplTable
         or to change or delete an existing cross-connect.
         This object must be initially set
         to `createAndWait' or 'createAndGo'.
         To turn on a VP cross-connect,
         the atmVpCrossConnectAdminStatus
         is set to `up'."
    DEFVAL { active }
    ::= { atmVpCrossConnectEntry 11 }

atmVcCrossConnectIndexNext OBJECT-TYPE
    SYNTAX INTEGER(0..2147483647)
    ACCESS read-only
    STATUS mandatory
    DESCRIPTION
        "This object contains an appropriate value to
         be used for atmVcCrossConnectIndex when creating
         entries in the atmVcCrossConnectTable.  The value
         0 indicates that no unassigned entries are
         available. To obtain the atmVpCrossConnectIndex
         value for a new entry, the manager issues a
         management protocol retrieval operation to obtain
         the current value of this object.  After each
         retrieval, the agent should modify the value to
         the next unassigned index."
    ::= { atmMIBObjects 10 }

atmVcCrossConnectTable OBJECT-TYPE
    SYNTAX SEQUENCE OF AtmVcCrossConnectEntry
    ACCESS not-accessible
    STATUS mandatory
    DESCRIPTION
        "The ATM VC Cross Connect table.  A bi-
         directional VC cross-connect which
         cross-connects two end points (i.e., VCLs)
         is modeled as one entry in this table."
    ::= { atmMIBObjects 11 }

atmVcCrossConnectEntry OBJECT-TYPE
    SYNTAX AtmVcCrossConnectEntry
    ACCESS not-accessible
    STATUS mandatory
    DESCRIPTION
        "An entry in the ATM VC Cross Connect table.
         This entry is used to model a bi-directional ATM
         VC cross-connect cross-connecting two end points.
        
         Step-wise Procedures to set up a VC Cross-connect
        
         Once the entries in the atmVclTable are created,
         the following procedures are used
         to cross-connect the VCLs together to
         form a VCC segment.
        
        (1) The manager obtains a unique
            atmVcCrossConnectIndex by reading the
            atmVcCrossConnectIndexNext object.
        
        (2) Next, the manager creates a set of one
            or more rows in the ATM VC Cross Connect
            Table, one for each cross-connection between
            two VCLs.  Each row is indexed by the ATM
            interface port numbers and VPI/VCI values of
            the two ends of that cross-connection.
            This set of rows specifies the topology of the
            VCC cross-connect and is identified by a single
            value of atmVcCrossConnectIndex.
        
         Negotiated VC Cross-Connect Establishment
        
        (2a) The manager creates a row in this table by
            setting atmVcCrossConnectRowStatus to
            createAndWait(5).  The agent checks the
            requested topology and the mutual sanity of
            the ATM traffic parameters and
            service categories, i.e., the row creation
            fails if:
            - the requested topology is incompatible with
              associated values of atmVclCastType,
            - the requested topology is not supported
              by the agent,
            - the traffic/service category parameter values
              associated with the requested row are
              incompatible with those of already existing
              rows for this VC cross-connect.
            [For example, for setting up
            a point-to-point VC cross-connect, the
            ATM traffic parameters in the receive direction
            of a VCL at the low end of the cross-connect
            must equal to the traffic parameters in the
            transmit direction of the other VCL at the
            high end of the cross-connect,
            otherwise, the row creation fails.]
            The agent also checks for internal errors
            in building the cross-connect.
        
            The atmVcCrossConnectIndex values in the
            corresponding atmVclTable rows are filled
            in by the agent at this point.
        
        (2b) The manager promotes the row in the
            atmVcCrossConnectTable by setting
            atmVcCrossConnectRowStatus to active(1).  If
            this set is successful, the agent has reserved
            the resources specified by the ATM traffic
            parameter and Service category values
            for each direction of the VC cross-connect
            in an ATM switch or network.
        
        (3) The manager sets the
            atmVcCrossConnectAdminStatus to up(1)
            in all rows of this VC cross-connect to
            turn the traffic flow on.
        
        
         One-Shot VC Cross-Connect Establishment
        
         A VC cross-connect may also be established in
         one step by a set-request with all necessary
         parameter values and atmVcCrossConnectRowStatus
         set to createAndGo(4).
        
         In contrast to the negotiated VC cross-connect
         establishment which allows for detailed error
         checking i.e., set errors are explicitly linked to
         particular resource acquisition failures), the
         one-shot VC cross-connect establishment
         performs the setup on one operation but does
         not have the advantage of step-wise error
         checking.
        
         VC Cross-Connect Retirement
        
         A VC cross-connect identified by a particular
         value of atmVcCrossConnectIndex is released by:
        
        (1) Setting atmVcCrossConnectRowStatus of all rows
            identified by this value of
            atmVcCrossConnectIndex to destroy(6).
            The agent may release all
            associated resources, and the
            atmVcCrossConnectIndex values in the
            corresponding atmVclTable row are removed.
            Note that a situation when only a subset of
            the associated rows are deleted corresponds
            to a VC topology change.
        
        (2) After deletion of the appropriate
            atmVcCrossConnectEntries, the manager may
            set atmVclRowStatus to destroy(6) the
            associated VCLs.  The agent releases
            the resources and removes the associated
            rows in the atmVclTable.
        
         VC Cross-Connect Reconfiguration
        
         At the discretion of the agent, a VC
         cross-connect may be reconfigured by
         adding and/or deleting leafs to/from
         the VC topology as per the VC cross-connect
         establishment/retirement procedures.
         Reconfiguration of traffic/service category parameter
         values requires release of the VC cross-connect
         before those parameter values may by changed
         for individual VCLs."
    INDEX { atmVcCrossConnectIndex, atmVcCrossConnectLowIfIndex, atmVcCrossConnectLowVpi, atmVcCrossConnectLowVci, atmVcCrossConnectHighIfIndex, atmVcCrossConnectHighVpi, atmVcCrossConnectHighVci }
    ::= { atmVcCrossConnectTable 1 }

AtmVcCrossConnectEntry ::= SEQUENCE {
    atmVcCrossConnectIndex INTEGER,
    atmVcCrossConnectLowIfIndex InterfaceIndex,
    atmVcCrossConnectLowVpi AtmVpIdentifier,
    atmVcCrossConnectLowVci AtmVcIdentifier,
    atmVcCrossConnectHighIfIndex InterfaceIndex,
    atmVcCrossConnectHighVpi AtmVpIdentifier,
    atmVcCrossConnectHighVci AtmVcIdentifier,
    atmVcCrossConnectAdminStatus AtmVorXAdminStatus,
    atmVcCrossConnectL2HOperStatus AtmVorXOperStatus,
    atmVcCrossConnectH2LOperStatus AtmVorXOperStatus,
    atmVcCrossConnectL2HLastChange AtmVorXLastChange,
    atmVcCrossConnectH2LLastChange AtmVorXLastChange,
    atmVcCrossConnectRowStatus RowStatus
    }

atmVcCrossConnectIndex OBJECT-TYPE
    SYNTAX INTEGER(1..2147483647)
    ACCESS not-accessible
    STATUS mandatory
    DESCRIPTION
        "A unique value to identify this VC cross-connect."
    ::= { atmVcCrossConnectEntry 1 }

atmVcCrossConnectLowIfIndex OBJECT-TYPE
    SYNTAX InterfaceIndex
--    Rsyntax Integer32
    ACCESS not-accessible
    STATUS mandatory
    DESCRIPTION
        "The ifIndex value of the ATM interface for this
         VC cross-connect. The term low implies
         that this ATM interface has the numerically lower
         ifIndex value than the other ATM interface
         identified in the same atmVcCrossConnectEntry."
    ::= { atmVcCrossConnectEntry 2 }

atmVcCrossConnectLowVpi OBJECT-TYPE
    SYNTAX AtmVpIdentifier
--    Rsyntax INTEGER(0..4095)
    ACCESS not-accessible
    STATUS mandatory
    DESCRIPTION
        "The VPI value at the ATM interface
         associated with the VC cross-connect that is
         identified by atmVcCrossConnectLowIfIndex."
    ::= { atmVcCrossConnectEntry 3 }

atmVcCrossConnectLowVci OBJECT-TYPE
    SYNTAX AtmVcIdentifier
--    Rsyntax INTEGER(0..65535)
    ACCESS not-accessible
    STATUS mandatory
    DESCRIPTION
        "The VCI value at the ATM interface
         associated with this VC cross-connect that is
         identified by atmVcCrossConnectLowIfIndex."
    ::= { atmVcCrossConnectEntry 4 }

atmVcCrossConnectHighIfIndex OBJECT-TYPE
    SYNTAX InterfaceIndex
--    Rsyntax Integer32
    ACCESS not-accessible
    STATUS mandatory
    DESCRIPTION
        "The ifIndex value for the ATM interface for
         this VC cross-connect. The term high implies
         that this ATM interface has the numerically higher
         ifIndex value than the other ATM interface
         identified in the same atmVcCrossConnectEntry."
    ::= { atmVcCrossConnectEntry 5 }

atmVcCrossConnectHighVpi OBJECT-TYPE
    SYNTAX AtmVpIdentifier
--    Rsyntax INTEGER(0..4095)
    ACCESS not-accessible
    STATUS mandatory
    DESCRIPTION
        "The VPI value at the ATM interface
         associated with the VC cross-connect that is
         identified by atmVcCrossConnectHighIfIndex."
    ::= { atmVcCrossConnectEntry 6 }

atmVcCrossConnectHighVci OBJECT-TYPE
    SYNTAX AtmVcIdentifier
--    Rsyntax INTEGER(0..65535)
    ACCESS not-accessible
    STATUS mandatory
    DESCRIPTION
        "The VCI value at the ATM interface
         associated with the VC cross-connect that is
         identified by atmVcCrossConnectHighIfIndex."
    ::= { atmVcCrossConnectEntry 7 }

atmVcCrossConnectAdminStatus OBJECT-TYPE
    SYNTAX AtmVorXAdminStatus
--    Rsyntax INTEGER {
--        up(1),
--        down(2)
--        }
    ACCESS read-write
    STATUS mandatory
    DESCRIPTION
        "The desired administrative status of this
         bi-directional VC cross-connect."
    DEFVAL { down }
    ::= { atmVcCrossConnectEntry 8 }

atmVcCrossConnectL2HOperStatus OBJECT-TYPE
    SYNTAX AtmVorXOperStatus
--    Rsyntax INTEGER {
--        up(1),
--        down(2),
--        unknown(3)
--        }
    ACCESS read-only
    STATUS mandatory
    DESCRIPTION
        "The current operational status of the
         VC cross-connect in one direction; (i.e.,
         from the low to high direction)."
    ::= { atmVcCrossConnectEntry 9 }

atmVcCrossConnectH2LOperStatus OBJECT-TYPE
    SYNTAX AtmVorXOperStatus
--    Rsyntax INTEGER {
--        up(1),
--        down(2),
--        unknown(3)
--        }
    ACCESS read-only
    STATUS mandatory
    DESCRIPTION
        "The current operational status of the
         VC cross-connect in one direction; (i.e.,
         from the high to low direction)."
    ::= { atmVcCrossConnectEntry 10 }

atmVcCrossConnectL2HLastChange OBJECT-TYPE
    SYNTAX AtmVorXLastChange
--    Rsyntax TimeTicks
    ACCESS read-only
    STATUS mandatory
    DESCRIPTION
        "The value of sysUpTime at the time this
         VC cross-connect entered its current
         operational state in low to high direction."
    ::= { atmVcCrossConnectEntry 11 }

atmVcCrossConnectH2LLastChange OBJECT-TYPE
    SYNTAX AtmVorXLastChange
--    Rsyntax TimeTicks
    ACCESS read-only
    STATUS mandatory
    DESCRIPTION
        "The value of sysUpTime at the time this
         VC cross-connect entered its current
         operational state in high to low direction."
    ::= { atmVcCrossConnectEntry 12 }

atmVcCrossConnectRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this entry in the
         atmVcCrossConnectTable.  This object is used to
         create a new cross-connect for cross-connecting
         VCLs which are created using the atmVclTable
         or to change or delete existing cross-connect.
         This object must be initially set to
         `createAndWait' or 'createAndGo'.
         To turn on a VC cross-connect,
         the atmVcCrossConnectAdminStatus
         is set to `up'."
    DEFVAL { active }
    ::= { atmVcCrossConnectEntry 13 }

aal5VccTable OBJECT-TYPE
    SYNTAX SEQUENCE OF Aal5VccEntry
    ACCESS not-accessible
    STATUS mandatory
    DESCRIPTION
        "This table contains AAL5 VCC performance
         parameters."
    ::= { atmMIBObjects 12 }

aal5VccEntry OBJECT-TYPE
    SYNTAX Aal5VccEntry
    ACCESS not-accessible
    STATUS mandatory
    DESCRIPTION
        "This list contains the AAL5 VCC
         performance parameters."
    INDEX { ifIndex, aal5VccVpi, aal5VccVci }
    ::= { aal5VccTable 1 }

Aal5VccEntry ::= SEQUENCE {
    aal5VccVpi AtmVpIdentifier,
    aal5VccVci AtmVcIdentifier,
    aal5VccCrcErrors Counter32,
    aal5VccSarTimeOuts Counter32,
    aal5VccOverSizedSDUs Counter32
    }

aal5VccVpi OBJECT-TYPE
    SYNTAX AtmVpIdentifier
--    Rsyntax INTEGER(0..4095)
    ACCESS not-accessible
    STATUS mandatory
    DESCRIPTION
        "The VPI value of the AAL5 VCC at the
         interface identified by the ifIndex."
    ::= { aal5VccEntry 1 }

aal5VccVci OBJECT-TYPE
    SYNTAX AtmVcIdentifier
--    Rsyntax INTEGER(0..65535)
    ACCESS not-accessible
    STATUS mandatory
    DESCRIPTION
        "The VCI value of the AAL5 VCC at the
         interface identified by the ifIndex."
    ::= { aal5VccEntry 2 }

aal5VccCrcErrors OBJECT-TYPE
    SYNTAX Counter32
    ACCESS read-only
    STATUS mandatory
    DESCRIPTION
        "The number of AAL5 CPCS PDUs received with
         CRC-32 errors on this AAL5 VCC at the
         interface associated with an AAL5 entity."
    ::= { aal5VccEntry 3 }

aal5VccSarTimeOuts OBJECT-TYPE
    SYNTAX Counter32
    ACCESS read-only
    STATUS mandatory
    DESCRIPTION
        "The number of partially re-assembled AAL5
         CPCS PDUs which were discarded
         on this AAL5 VCC at the interface associated
         with an AAL5 entity because they
         were not fully re-assembled within the
         required time period.  If the re-assembly
         timer is not supported, then this object
         contains a zero value."
    ::= { aal5VccEntry 4 }

aal5VccOverSizedSDUs OBJECT-TYPE
    SYNTAX Counter32
    ACCESS read-only
    STATUS mandatory
    DESCRIPTION
        "The number of AAL5 CPCS PDUs discarded
         on this AAL5 VCC at the interface
         associated with an AAL5 entity because the
         AAL5 SDUs were too large."
    ::= { aal5VccEntry 5 }

atmTrafficDescrParamIndexNext OBJECT-TYPE
    SYNTAX INTEGER(0..2147483647)
    ACCESS read-only
    STATUS mandatory
    DESCRIPTION
        "This object contains an appropriate value to
         be used for atmTrafficDescrParamIndex when
         creating entries in the
         atmTrafficDescrParamTable.
         The value 0 indicates that no unassigned
         entries are available. To obtain the
         atmTrafficDescrParamIndex value for a new
         entry, the manager issues a management
         protocol retrieval operation to obtain the
         current value of this object.  After each
         retrieval, the agent should modify the value
         to the next unassigned index."
    ::= { atmMIBObjects 13 }

atmInterfaceDs3PlcpGroup OBJECT IDENTIFIER ::= { atmMIBGroups 3 }
-- OBJECT-GROUP
--  Status
--    mandatory
--  Descr
--    A collection of objects providing information
--     about DS3 PLCP layer at an ATM interface.
--  objects
--    atmInterfaceDs3PlcpSEFSs, atmInterfaceDs3PlcpAlarmState, 
--    atmInterfaceDs3PlcpUASs

atmInterfaceTCGroup OBJECT IDENTIFIER ::= { atmMIBGroups 4 }
-- OBJECT-GROUP
--  Status
--    mandatory
--  Descr
--    A collection of objects providing information
--     about TC sublayer at an ATM interface.
--  objects
--    atmInterfaceOCDEvents, atmInterfaceTCAlarmState

aal5VccGroup OBJECT IDENTIFIER ::= { atmMIBGroups 9 }
-- OBJECT-GROUP
--  Status
--    mandatory
--  Descr
--    A collection of objects providing
--     AAL5 configuration and performance statistics
--     of a VCC.
--  objects
--    atmVccAal5CpcsTransmitSduSize, atmVccAal5CpcsReceiveSduSize, 
--    atmVccAal5EncapsType, aal5VccCrcErrors, aal5VccSarTimeOuts, 
--    aal5VccOverSizedSDUs

atmInterfaceConfGroup2 OBJECT IDENTIFIER ::= { atmMIBGroups 10 }
-- OBJECT-GROUP
--  Status
--    mandatory
--  Descr
--    A collection of objects providing configuration
--     information about an ATM interface.
--  objects
--    atmInterfaceMaxVpcs, atmInterfaceMaxVccs, 
--    atmInterfaceConfVpcs, atmInterfaceConfVccs, 
--    atmInterfaceMaxActiveVpiBits, atmInterfaceMaxActiveVciBits, 
--    atmInterfaceIlmiVpi, atmInterfaceIlmiVci, 
--    atmInterfaceMyNeighborIpAddress, atmInterfaceMyNeighborIfName, 
--    atmInterfaceCurrentMaxVpiBits, atmInterfaceCurrentMaxVciBits, 
--    atmInterfaceSubscrAddress

atmTrafficDescrGroup2 OBJECT IDENTIFIER ::= { atmMIBGroups 11 }
-- OBJECT-GROUP
--  Status
--    mandatory
--  Descr
--    A collection of objects providing information
--     about ATM traffic descriptor type and
--     the associated parameters.
--  objects
--    atmTrafficDescrType, atmTrafficDescrParam1, 
--    atmTrafficDescrParam2, atmTrafficDescrParam3, 
--    atmTrafficDescrParam4, atmTrafficDescrParam5, 
--    atmTrafficDescrRowStatus, atmServiceCategory, 
--    atmTrafficDescrParamIndexNext

atmVpcTerminationGroup2 OBJECT IDENTIFIER ::= { atmMIBGroups 12 }
-- OBJECT-GROUP
--  Status
--    mandatory
--  Descr
--    A collection of objects providing information
--     about a VPL at an ATM interface which
--     terminates a VPC (i.e., one which is NOT
--     cross-connected to other VPLs).
--  objects
--    atmVplOperStatus, atmVplAdminStatus, atmVplLastChange, 
--    atmVplReceiveTrafficDescrIndex, 
--    atmVplTransmitTrafficDescrIndex, atmVplRowStatus, 
--    atmVplCastType, atmVplConnKind

atmVccTerminationGroup2 OBJECT IDENTIFIER ::= { atmMIBGroups 13 }
-- OBJECT-GROUP
--  Status
--    mandatory
--  Descr
--    A collection of objects providing information
--     about a VCL at an ATM interface
--     which terminates a VCC (i.e., one which is
--     NOT cross-connected to other VCLs).
--  objects
--    atmVclOperStatus, atmVclAdminStatus, atmVclLastChange, 
--    atmVclReceiveTrafficDescrIndex, 
--    atmVclTransmitTrafficDescrIndex, atmVccAalType, 
--    atmVclRowStatus, atmVclCastType, atmVclConnKind

atmVplCrossConnectGroup OBJECT IDENTIFIER ::= { atmMIBGroups 14 }
-- OBJECT-GROUP
--  Status
--    mandatory
--  Descr
--    A collection of objects providing
--     information about the VPLs that
--     are cross-connected together.
--  objects
--    atmVplReceiveTrafficDescrIndex, 
--    atmVplTransmitTrafficDescrIndex, atmVplOperStatus, 
--    atmVplRowStatus, atmVplCastType, atmVplConnKind

atmVpPvcCrossConnectGroup OBJECT IDENTIFIER ::= { atmMIBGroups 15 }
-- OBJECT-GROUP
--  Status
--    mandatory
--  Descr
--    A collection of objects providing
--     information about a VP cross-connect
--     for PVCs. These objects are not used
--     for Soft PVCs or SVCs.
--  objects
--    atmVpCrossConnectAdminStatus, atmVpCrossConnectL2HOperStatus, 
--    atmVpCrossConnectH2LOperStatus, 
--    atmVpCrossConnectL2HLastChange, 
--    atmVpCrossConnectH2LLastChange, atmVpCrossConnectRowStatus, 
--    atmVplCrossConnectIdentifier, atmVpCrossConnectIndexNext

atmVclCrossConnectGroup OBJECT IDENTIFIER ::= { atmMIBGroups 16 }
-- OBJECT-GROUP
--  Status
--    mandatory
--  Descr
--    A collection of objects providing
--     information about the VCLs that
--     are cross-connected together.
--  objects
--    atmVclReceiveTrafficDescrIndex, 
--    atmVclTransmitTrafficDescrIndex, atmVclOperStatus, 
--    atmVclRowStatus, atmVclCastType, atmVclConnKind

atmVcPvcCrossConnectGroup OBJECT IDENTIFIER ::= { atmMIBGroups 17 }
-- OBJECT-GROUP
--  Status
--    mandatory
--  Descr
--    A collection of objects providing
--     information about a VC cross-connect
--     for PVCs. These objects are not used
--     for Soft PVCs or SVCs.
--  objects
--    atmVcCrossConnectAdminStatus, atmVcCrossConnectL2HOperStatus, 
--    atmVcCrossConnectH2LOperStatus, 
--    atmVcCrossConnectL2HLastChange, 
--    atmVcCrossConnectH2LLastChange, atmVcCrossConnectRowStatus, 
--    atmVclCrossConnectIdentifier, atmVcCrossConnectIndexNext

atmInterfaceConfGroup OBJECT IDENTIFIER ::= { atmMIBGroups 1 }
-- OBJECT-GROUP
--  Status
--    deprecated
--  Descr
--    A collection of objects providing configuration
--     information about an ATM interface.
--  objects
--    atmInterfaceMaxVpcs, atmInterfaceMaxVccs, 
--    atmInterfaceConfVpcs, atmInterfaceConfVccs, 
--    atmInterfaceMaxActiveVpiBits, atmInterfaceMaxActiveVciBits, 
--    atmInterfaceIlmiVpi, atmInterfaceIlmiVci, 
--    atmInterfaceAddressType, atmInterfaceAdminAddr, 
--    atmInterfaceMyNeighborIpAddress, atmInterfaceMyNeighborIfName

atmTrafficDescrGroup OBJECT IDENTIFIER ::= { atmMIBGroups 2 }
-- OBJECT-GROUP
--  Status
--    deprecated
--  Descr
--    A collection of objects providing information
--     about ATM traffic descriptor type and
--     the associated parameters.
--  objects
--    atmTrafficDescrType, atmTrafficDescrParam1, 
--    atmTrafficDescrParam2, atmTrafficDescrParam3, 
--    atmTrafficDescrParam4, atmTrafficDescrParam5, 
--    atmTrafficQoSClass, atmTrafficDescrRowStatus

atmVpcTerminationGroup OBJECT IDENTIFIER ::= { atmMIBGroups 5 }
-- OBJECT-GROUP
--  Status
--    deprecated
--  Descr
--    A collection of objects providing
--     information about a VPL at an ATM interface
--     which terminates a VPC
--     (i.e., one which is NOT cross-connected
--     to other VPLs).
--  objects
--    atmVplOperStatus, atmVplAdminStatus, atmVplLastChange, 
--    atmVplReceiveTrafficDescrIndex, 
--    atmVplTransmitTrafficDescrIndex, atmVplRowStatus

atmVccTerminationGroup OBJECT IDENTIFIER ::= { atmMIBGroups 6 }
-- OBJECT-GROUP
--  Status
--    deprecated
--  Descr
--    A collection of objects providing information
--     about a VCL at an ATM interface
--     which terminates a VCC (i.e., one which is
--     NOT cross-connected to other VCLs).
--  objects
--    atmVclOperStatus, atmVclAdminStatus, atmVclLastChange, 
--    atmVclReceiveTrafficDescrIndex, 
--    atmVclTransmitTrafficDescrIndex, atmVccAalType, 
--    atmVclRowStatus

atmVpCrossConnectGroup OBJECT IDENTIFIER ::= { atmMIBGroups 7 }
-- OBJECT-GROUP
--  Status
--    deprecated
--  Descr
--    A collection of objects providing
--     information about a VP cross-connect
--     and the associated VPLs that are
--     cross-connected together.
--  objects
--    atmVplReceiveTrafficDescrIndex, 
--    atmVplTransmitTrafficDescrIndex, atmVplOperStatus, 
--    atmVplRowStatus, atmVpCrossConnectAdminStatus, 
--    atmVpCrossConnectL2HOperStatus, 
--    atmVpCrossConnectH2LOperStatus, 
--    atmVpCrossConnectL2HLastChange, 
--    atmVpCrossConnectH2LLastChange, atmVpCrossConnectRowStatus, 
--    atmVplCrossConnectIdentifier, atmVpCrossConnectIndexNext

atmVcCrossConnectGroup OBJECT IDENTIFIER ::= { atmMIBGroups 8 }
-- OBJECT-GROUP
--  Status
--    deprecated
--  Descr
--    A collection of objects providing
--     information about a VC cross-connect
--     and the associated VCLs that are
--     cross-connected together.
--  objects
--    atmVclReceiveTrafficDescrIndex, 
--    atmVclTransmitTrafficDescrIndex, atmVclOperStatus, 
--    atmVclRowStatus, atmVcCrossConnectAdminStatus, 
--    atmVcCrossConnectL2HOperStatus, 
--    atmVcCrossConnectH2LOperStatus, 
--    atmVcCrossConnectL2HLastChange, 
--    atmVcCrossConnectH2LLastChange, atmVcCrossConnectRowStatus, 
--    atmVclCrossConnectIdentifier, atmVcCrossConnectIndexNext

atmMIBCompliance2 OBJECT IDENTIFIER ::= { atmMIBCompliances 2 }
-- MODULE-COMPLIANCE
--  Status
--    mandatory
--  Descr
--    The compliance statement for SNMP entities
--     including networks which have ATM and
--     AAL5 interfaces.
--  Module
--    >>current<<
--   MandGroup
--    atmInterfaceConfGroup2
--   MandGroup
--    atmTrafficDescrGroup2
--   ObjVar
--    atmInterfaceMaxVpcs
--   ObjVar
--    atmInterfaceMaxVccs
--   ObjVar
--    atmInterfaceMaxActiveVpiBits
--   ObjVar
--    atmInterfaceMaxActiveVciBits
--   ObjVar
--    atmInterfaceIlmiVpi
--   ObjVar
--    atmInterfaceIlmiVci
--   ObjVar
--    atmInterfaceMyNeighborIpAddress
--   ObjVar
--    atmInterfaceMyNeighborIfName
--   ObjVar
--    atmInterfaceSubscrAddress
--   ObjVar
--    atmTrafficDescrParamIndexNext
--   ObjVar
--    atmTrafficDescrType
--   ObjVar
--    atmTrafficDescrParam1
--   ObjVar
--    atmTrafficDescrParam2
--   ObjVar
--    atmTrafficDescrParam3
--   ObjVar
--    atmTrafficDescrParam4
--   ObjVar
--    atmTrafficDescrParam5
--   ObjVar
--    atmServiceCategory
--   ObjVar
--    atmTrafficDescrRowStatus
--   OptGroup
--    atmInterfaceDs3PlcpGroup
--   OptGroup
--    atmInterfaceTCGroup
--   OptGroup
--    atmVpcTerminationGroup2
--   OptGroup
--    atmVplCrossConnectGroup
--   OptGroup
--    atmVpPvcCrossConnectGroup
--   ObjVar
--    atmVplAdminStatus
--   ObjVar
--    atmVplReceiveTrafficDescrIndex
--   ObjVar
--    atmVplTransmitTrafficDescrIndex
--   ObjVar
--    atmVplRowStatus
--   ObjVar
--    atmVplCastType
--   ObjVar
--    atmVplConnKind
--   ObjVar
--    atmVpCrossConnectAdminStatus
--   ObjVar
--    atmVpCrossConnectRowStatus
--   OptGroup
--    atmVccTerminationGroup2
--   OptGroup
--    atmVclCrossConnectGroup
--   OptGroup
--    atmVcPvcCrossConnectGroup
--   ObjVar
--    atmVclAdminStatus
--   ObjVar
--    atmVclReceiveTrafficDescrIndex
--   ObjVar
--    atmVclTransmitTrafficDescrIndex
--   ObjVar
--    atmVccAalType
--   ObjVar
--    atmVclRowStatus
--   ObjVar
--    atmVclCastType
--   ObjVar
--    atmVclConnKind
--   ObjVar
--    atmVcCrossConnectAdminStatus
--   ObjVar
--    atmVcCrossConnectRowStatus
--   OptGroup
--    aal5VccGroup
--   ObjVar
--    atmVccAal5CpcsTransmitSduSize
--   ObjVar
--    atmVccAal5CpcsReceiveSduSize
--   ObjVar
--    atmVccAal5EncapsType

atmMIBCompliance OBJECT IDENTIFIER ::= { atmMIBCompliances 1 }
-- MODULE-COMPLIANCE
--  Status
--    deprecated
--  Descr
--    The compliance statement for SNMP entities
--     including networks which have ATM and
--     AAL5 interfaces.
--  Module
--    >>current<<
--   MandGroup
--    atmInterfaceConfGroup
--   MandGroup
--    atmTrafficDescrGroup
--   ObjVar
--    atmInterfaceMaxVpcs
--   ObjVar
--    atmInterfaceMaxVccs
--   ObjVar
--    atmInterfaceMaxActiveVpiBits
--   ObjVar
--    atmInterfaceMaxActiveVciBits
--   ObjVar
--    atmInterfaceIlmiVpi
--   ObjVar
--    atmInterfaceIlmiVci
--   ObjVar
--    atmInterfaceMyNeighborIpAddress
--   ObjVar
--    atmInterfaceMyNeighborIfName
--   ObjVar
--    atmTrafficDescrType
--   ObjVar
--    atmTrafficDescrParam1
--   ObjVar
--    atmTrafficDescrParam2
--   ObjVar
--    atmTrafficDescrParam3
--   ObjVar
--    atmTrafficDescrParam4
--   ObjVar
--    atmTrafficDescrParam5
--   ObjVar
--    atmTrafficQoSClass
--   ObjVar
--    atmTrafficDescrRowStatus
--   OptGroup
--    atmInterfaceDs3PlcpGroup
--   OptGroup
--    atmInterfaceTCGroup
--   OptGroup
--    atmVpcTerminationGroup
--   OptGroup
--    atmVpCrossConnectGroup
--   ObjVar
--    atmVplAdminStatus
--   ObjVar
--    atmVplReceiveTrafficDescrIndex
--   ObjVar
--    atmVplTransmitTrafficDescrIndex
--   ObjVar
--    atmVplRowStatus
--   ObjVar
--    atmVpCrossConnectAdminStatus
--   ObjVar
--    atmVpCrossConnectRowStatus
--   OptGroup
--    atmVccTerminationGroup
--   OptGroup
--    atmVcCrossConnectGroup
--   ObjVar
--    atmVclAdminStatus
--   ObjVar
--    atmVclReceiveTrafficDescrIndex
--   ObjVar
--    atmVclTransmitTrafficDescrIndex
--   ObjVar
--    atmVccAalType
--   ObjVar
--    atmVclRowStatus
--   ObjVar
--    atmVcCrossConnectAdminStatus
--   ObjVar
--    atmVcCrossConnectRowStatus
--   OptGroup
--    aal5VccGroup
--   ObjVar
--    atmVccAal5CpcsTransmitSduSize
--   ObjVar
--    atmVccAal5CpcsReceiveSduSize
--   ObjVar
--    atmVccAal5EncapsType


END
