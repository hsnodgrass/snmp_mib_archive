WAN-TRAP-MIB DEFINITIONS ::= BEGIN

        IMPORTS
        extremenetworks, extremeAgent   FROM EXTREME-BASE-MIB
                sysUpTime, sysDescr             FROM RFC1213-MIB
                dsx1LineIndex, dsx1IfIndex,
        dsx1LineStatus                  FROM RFC1406-MIB
                dsx3LineIndex, dsx3IfIndex,
        dsx3LineStatus                  FROM RFC1407-MIB
        TRAP-TYPE                       FROM RFC-1215
        OBJECT-TYPE                     FROM SNMPv2-SMI;
--
-- Traps for WAN Blade
--
        wanDsx1LineStatusChange TRAP-TYPE
                ENTERPRISE  extremenetworks
                VARIABLES { sysUpTime,
                            sysDescr,
                            dsx1LineIndex,
                            dsx1IfIndex,
                    dsx1LineStatus }
                DESCRIPTION
                "Signifies that the DS1 line status change for 
                the specified interface has been detected."
        ::= 100
        
        wanDsx1LossOfMasterClock TRAP-TYPE
                ENTERPRISE  extremenetworks
                VARIABLES { sysUpTime,
                            sysDescr,
                    dsx1LineIndex,
                            dsx1IfIndex,
                    dsx1LineStatus }
                DESCRIPTION
                "Signifies that the wanDsx1LossOfMasterClock event for 
                the specified interface has been detected."
        ::= 101
        
        wanDsx1NoLossOfMasterClock TRAP-TYPE
                ENTERPRISE  extremenetworks
                VARIABLES { sysUpTime,
                            sysDescr,
                    dsx1LineIndex,
                            dsx1IfIndex,
                    dsx1LineStatus }
                DESCRIPTION
                "Signifies that the wanDsx1NoLossOfMasterClock event for 
                the specified interface has been detected."
        ::= 102
        
        wanDsx3LineStatusChange TRAP-TYPE
                ENTERPRISE  extremenetworks
                VARIABLES { sysUpTime,
                            sysDescr,
                            dsx3LineIndex,
                            dsx3IfIndex,
                    dsx3LineStatus }
                DESCRIPTION
                "Signifies that the T3 line status change for 
                the specified interface has been detected."
        ::= 103
        
        wanDsx3LossOfMasterClock TRAP-TYPE
                ENTERPRISE  extremenetworks
                VARIABLES { sysUpTime,
                            sysDescr,
                    dsx3LineIndex,
                            dsx3IfIndex,
                    dsx3LineStatus }
                DESCRIPTION
                "Signifies that the wanDsx3LossOfMasterClock event for 
                the specified interface has been detected."
        ::= 104
        
        wanDsx3NoLossOfMasterClock TRAP-TYPE
                ENTERPRISE  extremenetworks
                VARIABLES { sysUpTime,
                            sysDescr,
                    dsx3LineIndex,
                            dsx3IfIndex,
                    dsx3LineStatus }
                DESCRIPTION
                "Signifies that the wanDsx3NoLossOfMasterClock event for 
                the specified interface has been detected."
        ::= 105
        
        
END

-- ################################################################################
