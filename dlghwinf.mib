-- ****************************************************************************
--
--                     Dialogic Hardware Information
--         Management Information Base for SNMP Network Management
--
--
--      Copyright 1997, Dialogic Corporation.
--      All Rights Reserved.
--
--      The information in this document is subject to change without notice.
--
--      The Dialogic Enterprise number is 3028.
--      The ASN.1 prefix to, and including the Dialogic Enterprise is:
--           1.3.6.1.4.1.3028
--
-- ****************************************************************************

DLGHWINF-MIB DEFINITIONS ::= BEGIN

    IMPORTS
        Counter                 FROM RFC1155-SMI
        OBJECT-TYPE             FROM RFC1155-SMI
        TRAP-TYPE               FROM RFC1155-SMI
        DisplayString           FROM RFC1213-MIB
        sysName                 FROM RFC1213-MIB;
--      dialogic                FROM DLGC-GLOBAL-REG
--      dlgHardwareInfo         FROM DLGC-GLOBAL-REG;

	dialogic	      OBJECT IDENTIFIER ::= { enterprises 3028 }
    dlgHardware	      OBJECT IDENTIFIER ::= { dialogic 1 }
    dlgHardwareInfo    OBJECT IDENTIFIER ::= { dlgHardware 1 }		
    dlgHiMibRev       OBJECT IDENTIFIER ::= { dlgHardwareInfo 1 }
    dlgHiComponent    OBJECT IDENTIFIER ::= { dlgHardwareInfo 2 }
    dlgHiInterface    OBJECT IDENTIFIER ::= { dlgHiComponent 1 }
    dlgHiIdent        OBJECT IDENTIFIER ::= { dlgHiComponent 2 }
    dlgHiOsCommon     OBJECT IDENTIFIER ::= { dlgHiInterface 1 }

-- ****************************************************************************
-- HardwareInfo MIB Revision
-- =========================
--
-- The dialogic enterprise             (1.3.6.1.4.1.3028)
--       dlgHardware Group             (1.3.6.1.4.1.3028.1)
--        dlgHardwareInfo Group        (1.3.6.1.4.1.3028.1.1)
--         dlgHiMibRev Group           (1.3.6.1.4.1.3028.1.1.1)
--
--
--     An Agent conforming to this document will return a mibRevMajor
--     of one (1) and a mibRevMinor of zero (0).
--
--
-- ****************************************************************************

    dlgHiMibRevMajor OBJECT-TYPE
       SYNTAX  INTEGER (1..65535)
       ACCESS  read-only
       STATUS  mandatory
       DESCRIPTION
           "The Major Revision level.

            A change in the major revision level represents a major change
            in the architecture of the MIB.  A change in the major revision
            level may indicate a significant change in the information
            supported and/or the meaning of the supported information,
            correct interpretation of data may require a MIB document with
            the same major revision level."
       ::= { dlgHiMibRev 1 }

       dlgHiMibRevMinor OBJECT-TYPE
       SYNTAX  INTEGER (0..65535)
       ACCESS  read-only
       STATUS  mandatory
       DESCRIPTION
           "The Minor Revision level.

            A change in the minor revision level may represent some minor
            additional support. no changes to any pre-existing information
            has occurred."
       ::= { dlgHiMibRev 2 }

       dlgHiMibCondition OBJECT-TYPE
           SYNTAX  INTEGER {
               other(1),
               ok(2),           -- default
               degraded(3),
               failed(4)
               }
           ACCESS  read-only
           STATUS  mandatory
           DESCRIPTION
               "The overall condition.

                This object represents the overall status of the Dialogic
                Hardware Information system represented by this MIB."
           ::= { dlgHiMibRev 3 }

-- ****************************************************************************
--    HardwareInfo OS Common
--    ======================
--
-- The dialogic enterprise             (1.3.6.1.4.1.3028)
--       dlgHardware Group             (1.3.6.1.4.1.3028.1)
--        dlgHardwareInfo Group        (1.3.6.1.4.1.3028.1.1)
--         dlgHiComponent Group        (1.3.6.1.4.1.3028.1.1.2)
--          dlgHiInterface Group       (1.3.6.1.4.1.3028.1.1.2.1)
--           dlgHiOsCommon Group       (1.3.6.1.4.1.3028.1.1.2.1.1)
--
--
-- ****************************************************************************

    dlgHiOsCommonPollFreq OBJECT-TYPE
        SYNTAX  INTEGER (0..65535)
        ACCESS  read-write
        STATUS  mandatory
        DESCRIPTION
            "The Agent's polling frequency.

             The frequency, in seconds, at which the Agent requests
             information from the device driver.  A frequency of zero
             indicates that the Agent retrieves the information upon
             request of a management station, it does not poll the device
             driver at a specific interval.

             If the poll frequency is zero (0) all attempts to write to this
             object will fail.  If the poll frequency is non-zero,
             setting this value will change the polling frequency of the
             Agent.  Setting the poll frequency to zero will always
             fail, an agent may also choose to fail any request to change
             the poll frequency to a value that would severely impact system
             performance."
           ::= { dlgHiOsCommon 1 }

    dlgHiOsCommonNumberOfModules OBJECT-TYPE
        SYNTAX  INTEGER
        ACCESS  read-only
        STATUS  mandatory
        DESCRIPTION
            "The number of modules in the OS Common Module table."
           ::= { dlgHiOsCommon 2 }


-- ****************************************************************************
--    HardwareInfo OS Common Module
--    =============================
--
-- The dialogic enterprise              (1.3.6.1.4.1.3028)
--      dlgHardware Group               (1.3.6.1.4.1.3028.1)
--        dlgHardwareInfo Group         (1.3.6.1.4.1.3028.1.1)
--         dlgHiComponent Group         (1.3.6.1.4.1.3028.1.1.2)
--          dlgHiInterface Group        (1.3.6.1.4.1.3028.1.1.2.1)
--           dlgHiOsCommon Group        (1.3.6.1.4.1.3028.1.1.2.1.1)
--            dlgHiOsCommonModuleTable  (1.3.6.1.4.1.3028.1.1.2.1.1.3)
--
-- The OSCommonModuleTable contains information about the software modules
-- which interface to the Dialogic cards in the system 
--
-- ****************************************************************************

    dlgHiOsCommonModuleTable OBJECT-TYPE
        SYNTAX  SEQUENCE OF DlgHiOsCommonModuleEntry
        ACCESS  not-accessible
        STATUS  mandatory
        DESCRIPTION
            "A table of software modules that provide an interface to the
             device this MIB describes."
        ::= { dlgHiOsCommon 3 }

    dlgHiOsCommonModuleEntry OBJECT-TYPE
        SYNTAX  DlgHiOsCommonModuleEntry
        ACCESS  not-accessible
        STATUS  mandatory
        DESCRIPTION
            "A description of a software modules that provide an interface
             to the device this MIB describes."
        INDEX   { dlgHiOsCommonModuleIndex }
        ::= { dlgHiOsCommonModuleTable 1 }

        DlgHiOsCommonModuleEntry ::= SEQUENCE {
            dlgHiOsCommonModuleIndex       INTEGER,
            dlgHiOsCommonModuleName        DisplayString,
            dlgHiOsCommonModuleVersion     DisplayString,
            dlgHiOsCommonModuleDate        OCTET STRING,
            dlgHiOsCommonModulePurpose     DisplayString
        }

    dlgHiOsCommonModuleIndex OBJECT-TYPE
        SYNTAX  INTEGER (0..255)
        ACCESS  read-only
        STATUS  mandatory
        DESCRIPTION
            "A unique index for this module description."
        ::= { dlgHiOsCommonModuleEntry 1 }

    dlgHiOsCommonModuleName OBJECT-TYPE
        SYNTAX  DisplayString (SIZE (0..255))
        ACCESS  read-only
        STATUS  mandatory
        DESCRIPTION
            "The module name."
        ::= { dlgHiOsCommonModuleEntry 2 }

    dlgHiOsCommonModuleVersion OBJECT-TYPE
        SYNTAX  DisplayString (SIZE (0..5))
        ACCESS  read-only
        STATUS  mandatory
        DESCRIPTION
            "The module version in XX.YY format.

            Where XX is the major version number and YY is the minor version
            number.  This field will be a null (size 0) string if the agent
            cannot provide the module version."
        ::= { dlgHiOsCommonModuleEntry 3 }

    dlgHiOsCommonModuleDate OBJECT-TYPE
        SYNTAX  OCTET STRING (SIZE (7))
        ACCESS  read-only
        STATUS  mandatory
        DESCRIPTION
            "The module date.

             field  octets  contents                  range
             =====  ======  =======                  =====
               1      1-2   year                      0..65536
               2       3    month                     1..12
               3       4    day                       1..31
               4       5    hour                      0..23
               5       6    minute                    0..59
               6       7    second                    0..60
                            (use 60 for leap-second)


            This field will be set to year = 0 if the agent cannot provide
            the module date.  The hour, minute, and second field will be set
            to zero (0) if they are not relevant."
        ::= { dlgHiOsCommonModuleEntry 4 }

    dlgHiOsCommonModulePurpose OBJECT-TYPE
        SYNTAX  DisplayString (SIZE (0..255))
        ACCESS  read-only
        STATUS  mandatory
        DESCRIPTION
            "The purpose of the module described in this entry."
        ::= { dlgHiOsCommonModuleEntry 5 }

-- ****************************************************************************
--    HardwareInfo Ident Group
--    ========================
--
-- The dialogic enterprise              (1.3.6.1.4.1.3028)
--      dlgHardware Group               (1.3.6.1.4.1.3028.1)
--        dlgHardwareInfo Group         (1.3.6.1.4.1.3028.1.1)
--         dlgHiComponent Group         (1.3.6.1.4.1.3028.1.1.2)
--          dlgHiIdent Group            (1.3.6.1.4.1.3028.1.1.2.2)
--
--
--  The Ident group contains basic indentification information about the
--  Dialogic cards in the system.
--
-- ****************************************************************************

    dlgHiIdentNumberOfDevices OBJECT-TYPE
       SYNTAX  INTEGER
       ACCESS  read-only
       STATUS  mandatory
       DESCRIPTION
           "Number of Dialogic device in the system.

            A device may be a physical card, a channel on a card 
            or an embedded component on a card"
       ::= { dlgHiIdent 2 }

    dlgHiIdentServiceStatus OBJECT-TYPE
       SYNTAX  INTEGER {
           other(1),
           started(2),
           stop-pending(3),
           stopped(4),
           start-pending(5)
           }
       ACCESS  read-write
       STATUS  mandatory
       DESCRIPTION
           "Dialogic Service Status

            This is the overall status of the Dialogic system service.
	    The following values are defined:

            other(1)
              The service status is unknown.

            started(2)
              The service status is running - cards are started. Setting the
              variable to this value will fail.

            stop-pending(3)
              The service is in the act of stopping. Setting the
              variable to this value when the current condition is started(2)
              will cause the service to begin stopping, otherwise it will
              fail.

            stopped(4)
              The service status is stopped - cards are stopped. Setting the
              variable to this value will fail.

            start-pending(5)
              The service is in the act of starting. Setting the
              variable to this value when the current condition is stopped(4)
              will cause the service to begin starting, othewise it will
              fail."
       ::= { dlgHiIdent 3 }

    dlgHiIdentServiceChangeDate OBJECT-TYPE
        SYNTAX  OCTET STRING (SIZE (7))
        ACCESS  read-only
        STATUS  mandatory
        DESCRIPTION
            "The date and time the service was last started or stopped.

             field  octets  contents                  range
             =====  ======  =======                  =====
               1      1-2   year                      0..65536
               2       3    month                     1..12
               3       4    day                       1..31
               4       5    hour                      0..23
               5       6    minute                    0..59
               6       7    second                    0..60
                            (use 60 for leap-second)


            This field will be set to year = 0 if the agent cannot provide
            the module date.  The hour, minute, and second field will be set
            to zero (0) if they are not relevant."
       ::= { dlgHiIdent 4 }

   dlgHiIdentTrapMask OBJECT-TYPE
       SYNTAX  INTEGER 
       ACCESS  read-write
       STATUS  mandatory
       DESCRIPTION
           "Trap Enable mask.

            This variable is a bit mask which can  be used to enable or 
            disable certain enterprise specific traps.

            A '1' is used to enable the trap, a '0' disables it.

            Bit 0 - (1) enables Traps upon Dialogic Service Status
                        transitions to the Stopped or Started State.
            Bit 1 - (1) enables Traps when a specific Card Condition
                        transitions to the Failed State."
       ::= { dlgHiIdent 5 }


-- ****************************************************************************
--    HardwareInfo Ident Table
--    ========================
--
-- The dialogic enterprise              (1.3.6.1.4.1.3028)
--      dlgHardware Group               (1.3.6.1.4.1.3028.1)
--        dlgHardwareInfo Group         (1.3.6.1.4.1.3028.1.1)
--         dlgHiComponent Group         (1.3.6.1.4.1.3028.1.1.2)
--          dlgHiIdent Group            (1.3.6.1.4.1.3028.1.1.2.2)
--           dlgHiIdentTable            (1.3.6.1.4.1.3028.1.1.2.2.1)
--
--
--  The Ident table contains basic indentification information about the
--  Dialogic cards in the system.
--
-- ****************************************************************************

    dlgHiIdentTable OBJECT-TYPE
        SYNTAX  SEQUENCE OF DlgHiIdentEntry
        ACCESS  not-accessible
        STATUS  mandatory
        DESCRIPTION
           "Dialogic card Identification Table."
        ::= { dlgHiIdent 1 }

    dlgHiIdentEntry OBJECT-TYPE
        SYNTAX  DlgHiIdentEntry
        ACCESS  not-accessible
        STATUS  mandatory
        DESCRIPTION
           "Dialogic card Identification Table Entry."
        INDEX   { dlgHiIdentIndex }
        ::= { dlgHiIdentTable 1 }

        DlgHiIdentEntry ::= SEQUENCE
        {
              dlgHiIdentIndex          INTEGER,
              dlgHiIdentModel          DisplayString,
              dlgHiIdentType           INTEGER,
              dlgHiIdentFuncDescr      DisplayString,
              dlgHiIdentSerNum         DisplayString,
              dlgHiIdentFWName         DisplayString,
              dlgHiIdentFWVers         DisplayString,
              dlgHiIdentMemBaseAddr    INTEGER,
              dlgHiIdentIOBaseAddr     INTEGER,
              dlgHiIdentIrq            INTEGER,
              dlgHiIdentBoardID        INTEGER,
              dlgHiIdentPCISlotID      INTEGER,
              dlgHiIdentOperStatus     INTEGER,
              dlgHiIdentAdminStatus    INTEGER,
              dlgHiIdentErrorMessage   DisplayString,
              dlgHiIdentDeviceChangeDate  OCTET STRING,
              dlgHiIdentSpecific       OBJECT IDENTIFIER
        }

    dlgHiIdentIndex OBJECT-TYPE
        SYNTAX  INTEGER (0..65535)
        ACCESS  read-only
        STATUS  mandatory
        DESCRIPTION
            "An index that uniquely specifies each device."
        ::= { dlgHiIdentEntry 1 }


    dlgHiIdentModel OBJECT-TYPE
        SYNTAX  DisplayString (SIZE (0..32))
        ACCESS  read-only
        STATUS  mandatory
        DESCRIPTION
           "Dialogic card Model.

            This is the Dialogic cards model name and can be used for 
            identification purposes."
        ::= { dlgHiIdentEntry 2 }

    dlgHiIdentType OBJECT-TYPE
        SYNTAX  INTEGER {
                     other(1),         -- none of the following
                     release4span(2),  -- Proline/2V up to D/600SC-2E1 cards
                     dm3(3),           -- DM3 based 
                     gammaCP(4),       -- Gamma CP/x series
                     antares(5)
                }
        ACCESS  read-only
        STATUS  mandatory
        DESCRIPTION
           "Dialogic card type.

            This indicates which family of cards this device belongs to.

            other(1)         -- none of the following

            release4span(2)  -- Proline/2V up to D/600SC-2E1 cards

            dm3(3)           -- DM3 based card

            gammaCP(4)       -- Gamma CP/x series

            antares(5)       -- Antares based card"

        ::= { dlgHiIdentEntry 3 }

    dlgHiIdentFuncDescr OBJECT-TYPE
        SYNTAX  DisplayString (SIZE(0..128))
        ACCESS  read-only
        STATUS  mandatory
        DESCRIPTION
           "Dialogic card Function Description.
 
            This provides a description of the functionality provided by the
            Dialogic card. If the functional description of the card is 
            unavailable, then this string will be of length zero (0)."
        ::= { dlgHiIdentEntry 4 }


    dlgHiIdentSerNum OBJECT-TYPE
        SYNTAX  DisplayString (SIZE (0..12))
        ACCESS  read-only
        STATUS  mandatory
        DESCRIPTION
           "Dialogic card Serial Number.

            This is the Dialogic card serial number and can be used for 
            identification purposes. On many cards the serial number 
            appears on the edge connector, visible from the back of the
            PC"
        ::= { dlgHiIdentEntry 5 }

    dlgHiIdentFWName OBJECT-TYPE
        SYNTAX  DisplayString (SIZE (0..128))
        ACCESS  read-only
        STATUS  mandatory
        DESCRIPTION
           "Dialogic Firmware Name.

            This is the name of the firmware downloaded to this
            Dialogic card. If the firmware name is unavailable, then this
	    string will be of length zero (0)."
        ::= { dlgHiIdentEntry 6 }

    dlgHiIdentFWVers OBJECT-TYPE
        SYNTAX  DisplayString (SIZE (0..64))
        ACCESS  read-only
        STATUS  mandatory
        DESCRIPTION
           "Dialogic Firmware Version.

            This is the version of the firmware downloaded to this
            Dialogic card. If the Dialogic firmware version is unavailable, 
            then this string will be of length zero (0)."
        ::= { dlgHiIdentEntry 7 }


    dlgHiIdentMemBaseAddr OBJECT-TYPE
        SYNTAX  INTEGER
        ACCESS  read-only
        STATUS  mandatory
        DESCRIPTION
            "Dialogic card Base Memory Address.

             This is the Memory address where the Dialogic card has been 
             installed on the system. If the Dialogic card does not use
             a system memory then a value of zero (0) is returned"
        ::= { dlgHiIdentEntry 8 }

    dlgHiIdentIOBaseAddr OBJECT-TYPE
        SYNTAX  INTEGER
        ACCESS  read-only
        STATUS  mandatory
        DESCRIPTION
            "Dialogic card Base I/O Port Address.

             This is the I/O Port address where the Dialogic card has been 
             installed on the system. If the Dialogic card does not use
             a system I/O Port then a value of zero (0) is returned"
        ::= { dlgHiIdentEntry 9 }

    dlgHiIdentIrq OBJECT-TYPE
        SYNTAX  INTEGER
        ACCESS  read-only
        STATUS  mandatory
        DESCRIPTION
            "Dialogic card IRQ (Interrupt) Level.

             This is the Interrupt Level used by the Dialogic card  
             installed on the system. If the Dialogic card does not use
             an Interrupt then a value of zero (0) is returned"
        ::= { dlgHiIdentEntry 10 }

    dlgHiIdentBoardID OBJECT-TYPE
        SYNTAX  INTEGER
        ACCESS  read-only
        STATUS  mandatory
        DESCRIPTION
            "Dialogic card Board ID.

             This is the Unique Board ID set by the thumbwheel on certain
             Dialogic cards. This may be used for identification purposes.
             If the Dialogic card does not have a Unique Board ID setting
             then a value of negative one (-1) is returned"
        ::= { dlgHiIdentEntry 11 }

    dlgHiIdentPCISlotID OBJECT-TYPE
        SYNTAX  INTEGER
        ACCESS  read-only
        STATUS  mandatory
        DESCRIPTION
            "Dialogic card PCI Slot ID.

             This is a PCI slot identifier where the Dialogic card is 
             installed. This may be used for identification purposes.
             If the Dialogic card is not a PCI card or if this info is 
             not available then a value of zero (0) is returned"
        ::= { dlgHiIdentEntry 12 }

    dlgHiIdentOperStatus OBJECT-TYPE
        SYNTAX  INTEGER {
            other(1),
            ok(2),
            degraded(3),
            failed(4)
            }
        ACCESS  read-only
        STATUS  mandatory
        DESCRIPTION
           "Dialogic card Operational Status.

            This is the overall condition of the Dialogic card.
	    The following values are defined

            other(1)
              The card does not support card condition monitoring.

            ok(2)
              The card is operating normally.  No user action is required.

            degraded(3)
              The card is degraded.  The card may need to be reset.

            failed(4)
              The card has failed.  The card should be reset"
        ::= { dlgHiIdentEntry 13 }

    dlgHiIdentAdminStatus OBJECT-TYPE
        SYNTAX  INTEGER {
            other(1),
            started(2),
            stop-pending(3),
            stopped(4),
            start-pending(5),
            disabled(6),
            diagnose(7)
            }
        ACCESS  read-write
        STATUS  mandatory
        DESCRIPTION
           "Dialogic card Admin Status.

            This is the Administrative Status of the Dialogic card.
	    The following values are defined

            other(1)
              The card's admin status in unavailable.

            started(2)
              The card has been started.

            stop-pending(3)
              The card is in the process of stopping

            stopped(4)
              The card is stopped.

            start-pending(5)
              The card is in the process of starting

            disabled(6)
              The card is disabled.

            diagnose(7)
             The card is being diagnosed."
        ::= { dlgHiIdentEntry 14 }

    dlgHiIdentErrorMessage OBJECT-TYPE
        SYNTAX  DisplayString (SIZE (0..96))
        ACCESS  read-only
        STATUS  mandatory
        DESCRIPTION
           "Dialogic Card Error Message.

            This value represents the error message associated with 
            a failing Dialogic card."
        ::= { dlgHiIdentEntry 15 }

    dlgHiIdentDeviceChangeDate OBJECT-TYPE
        SYNTAX  OCTET STRING (SIZE (7))
        ACCESS  read-only
        STATUS  mandatory
        DESCRIPTION
            "The date and time the boards operational status last changed.

             field  octets  contents                  range
             =====  ======  =======                  =====
               1      1-2   year                      0..65536
               2       3    month                     1..12
               3       4    day                       1..31
               4       5    hour                      0..23
               5       6    minute                    0..59
               6       7    second                    0..60
                            (use 60 for leap-second)


            This field will be set to year = 0 if the agent cannot provide
            the module date.  The hour, minute, and second field will be set
            to zero (0) if they are not relevant."
       ::= { dlgHiIdentEntry 16 }

    dlgHiIdentSpecific OBJECT-TYPE
        SYNTAX  OBJECT IDENTIFIER
        ACCESS  read-only
        STATUS  mandatory
        DESCRIPTION
                "A reference to MIB definitions specific to the
                 particular board type specified in the row of 
                 the table

                 If this information is not present, its value should 
                 be set to the OBJECT IDENTIFIER { 0 0 }, which is a 
                 syntatically valid object identifier, and any conformant
                 implementation of ASN.1 and BER must be able to
                 generate and recognize this value."
         ::= { dlgHiIdentEntry 17 }

-- ****************************************************************************
--  HardwareInfo Trap Definitions
--  =============================
--
--  The user may disable these traps by setting dlgHiIdentTrapMask
--
-- **************************************************************************

    dlgHiServiceChanged TRAP-TYPE
        ENTERPRISE dialogic
        VARIABLES  { sysName,
                     dlgHiIdentServiceStatus }
        DESCRIPTION
            "The Dialogic service condition has been changed

             Description: 

              The dlgHiIdentServiceChanged trap indicates that the 
              Dialogic service has transitioned to either the 
              started or stopped state. This may occur by performing 
              a set on the dlgHiIdentServiceStatus variable or by
              controlling the service directly on the machine which
              generated the trap.

             Action:

              This trap is informational. A management console may
              want to update any current device table views since
              attributes of the device may change when the Dialogic
              service is started or stopped"

        --#TYPE "Service Condition Change"
        --#SUMMARY "Status is now %d."
        --#ARGUMENTS {2}
        --#SEVERITY INFORMATIONAL
        --#TIMEINDEX 99
        ::= 1001


    dlgHiCardStatusChanged TRAP-TYPE
        ENTERPRISE dialogic
        VARIABLES  { sysName,
                     dlgHiIdentIndex, 
                     dlgHiIdentOperStatus, 
                     dlgHiIdentAdminStatus,
                     dlgHiIdentModel,
                     dlgHiIdentSerNum,
                     dlgHiIdentErrorMessage
                   }
        DESCRIPTION
            "The condition of a Dialogic card has changed to failed or ok

             Description: 

              The dlgHiIdentCardStatusChanged trap indicates that  
              a device in the device table has transitioned from 
              the ok state to the failed state or vice versa. 
              In general this indicates that on-board firmware has 
              crashed and is no longer responding or that the board 
              has gone bad. 
              Should the board recover from the failed state, the 
              state will be transitioned back to the ok state and 
              a trap will be generated to indicate the board is okay 
              again.
              
 
             Action:

              If the state has transitioned to the failed then
              shutdown any active applications and reset the 
              Dialogic service. This will cause the on-board firmware
              to be re-downloaded. If the problem persists you should
              run the device diagnostics on the card to make sure
              it is okay."

        --#TYPE "Card Status Change"
        --#SUMMARY "Status is now %d."
        --#ARGUMENTS {7}
        --#SEVERITY MAJOR
        --#TIMEINDEX 99

        ::= 1002


END
