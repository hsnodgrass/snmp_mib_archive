-- SECTION 1: Top Level Definition


CENTILLION-BRIDGE-MIB DEFINITIONS ::= BEGIN


-- Centillion Bridge MIB Release 2.0.0
-- Revision 03/20/96

-- Copyright 1994-96 Bay Networks, Inc.
-- All rights reserved.
-- This Bay Networks SNMP Management Information Base Specification
-- (Specification) embodies Bay Networks' confidential and
-- proprietary intellectual property. Bay Networks retains all
-- title and ownership in the Specification, including any
-- revisions.

-- This Specification is supplied "AS IS," and Bay Networks makes
-- no warranty, either express or implied, as to the use,
-- operation, condition, or performance of the Specification.


-- Imports

IMPORTS
	Counter, TimeTicks
		FROM RFC1155-SMI
	OBJECT-TYPE
		FROM RFC-1212
	extensions, EnableIndicator
		FROM CENTILLION-ROOT-MIB;


-- Textual Conventions

-- All representations of MAC addresses in this MIB Module
-- use, as a textual convention (i.e. this convention does
-- not affect their encoding), the data type:

MacAddress ::= OCTET STRING (SIZE (6))

-- a 6 octet address in the "canonical" order defined
-- by IEEE 802.1a, i.e., as if it were transmitted
-- least significant bit first, even though 802.5 (in
-- contrast to other n802.x protocols) requires MAC
-- addresses to be transmitted most significant bit first.
--
-- 16-bit addresses, if needed, are represented by setting
-- their upper 4 octets to all 0's, i.e., AAFF would be
-- represented as 00000000AAFF.


-- Similarly, all representations of Bridge-Id in this MIB
-- Module use, as a textual convention (i.e. this
-- convention does not affect their encoding), the data
-- type:

BridgeId ::= OCTET STRING (SIZE (8))

-- the Bridge-Identifier as used in the Spanning Tree
-- Protocol to uniquely identify a bridge.  Its first two
-- octets (in network byte order) contain a priority
-- value and its last 6 octets contain the MAC address
-- used to refer to a bridge in a unique fashion
-- (typically, the numerically smallest MAC address
-- of all ports on the bridge).
-- Several objects in this MIB module represent values of
-- timers used by the Spanning Tree Protocol.  In this
-- MIB, these timers have values in units of hundreths of
-- a second (i.e. 1/100 secs).
-- These timers, when stored in a Spanning Tree Protocol's
-- BPDU, are in units of 1/256 seconds.  Note, however,
-- that 802.1D-1990 specifies a settable granularity of
-- no more than 1 second for these timers.  To avoid
-- ambiguity, a data type is defined here as a textual
-- convention and all representation of these timers
-- in this MIB module are defined using this data type.  An
-- algorithm is also defined for converting between the
-- different units, to ensure a timer's value is not
-- distorted by multiple conversions.
-- The data type is:

Timeout ::= INTEGER -- a STP timer in units of 1/100 seconds

-- To convert a Timeout value into a value in units of
-- 1/256 seconds, the following algorithm should be used:
--
--      b  = floor( (n * 256) / 100)
--
-- where:
--      floor   =  quotient [ignore remainder]
--      n is the value in 1/100 second units
--      b is the value in 1/256 second units
--
-- To convert the value from 1/256 second units back to
-- 1/100 seconds, the following algorithm should be used:
--
--      n = ceiling( (b * 100) / 256)
--
-- where:
--      ceiling =  quotient [if remainder is 0], or
--                 quotient + 1 [if remainder is non-zero]
--      n is the value in 1/100 second units
--      b is the value in 1/256 second units
--
-- Note: it is important that the arithmetic operations are
-- done in the order specified (i.e., multiply first, divide
-- second).


-- Groups

cndot1dBridge   OBJECT IDENTIFIER ::= { extensions 17 }

cndot1dBase     OBJECT IDENTIFIER ::= { cndot1dBridge 1 }
cndot1dStp      OBJECT IDENTIFIER ::= { cndot1dBridge 2 }
cndot1dSr       OBJECT IDENTIFIER ::= { cndot1dBridge 3 }
cndot1dTp	OBJECT IDENTIFIER ::= { cndot1dBridge 4 }


-- SECTION 2:

--
-- The cndot1dBase group
--
-- Implementation of the cndot1dBase group is mandatory for all
-- bridges.
--

cndot1dBaseBridgeAddress OBJECT-TYPE
	SYNTAX  MacAddress
	ACCESS  read-only
	STATUS  mandatory
	DESCRIPTION
		"The MAC address used by this bridge when it must
		be referred to in a unique fashion.   It is
		recommended that this be the numerically smallest
		MAC address of all ports that belong to this
		bridge.  However it is only required to be unique.
		When concatenated with cndot1dStpPriority a unique
		BridgeIdentifier is formed which is used in the
		Spanning Tree Protocol."
	REFERENCE
		"IEEE 802.1D-1990: Sections 6.4.1.1.3 and 3.12.5"
	::= { cndot1dBase 1 }

cndot1dBaseNumPorts OBJECT-TYPE
	SYNTAX  INTEGER
	ACCESS  read-only
	STATUS  mandatory
	DESCRIPTION
		"The number of ports controlled by this bridging
		entity."
	REFERENCE
		"IEEE 802.1D-1990: Section 6.4.1.1.3"
	::= { cndot1dBase 2 }

cndot1dBaseType OBJECT-TYPE
	SYNTAX  INTEGER {
		unknown(1),
		transparent-only(2),
		sourceroute-only(3),
		srt(4)
		}
	ACCESS  read-only
	STATUS  mandatory
	DESCRIPTION
		"Indicates what type of bridging is being performed
		If a bridge is actually performing a
		certain type of bridging this will be indicated by
		entries in the port table for the given type."
	::= { cndot1dBase 3 }


-- The Generic Bridge Port Table

cndot1dBasePortTable OBJECT-TYPE
	SYNTAX  SEQUENCE OF Cndot1dBasePortEntry
	ACCESS  not-accessible
	STATUS  mandatory
	DESCRIPTION
		"A table that contains generic information about
		every port that is associated with this bridge.
		Transparent, source-route, and srt ports are
		included."
	::= { cndot1dBase 4 }

cndot1dBasePortEntry OBJECT-TYPE
	SYNTAX  Cndot1dBasePortEntry
	ACCESS  not-accessible
	STATUS  mandatory
	DESCRIPTION
		"A list of information for each port of the
		bridge."
	REFERENCE
		"IEEE 802.1D-1990: Section 6.4.2, 6.6.1"
	INDEX  { cndot1dBasePort }
	::= { cndot1dBasePortTable 1 }


Cndot1dBasePortEntry ::= SEQUENCE {
	cndot1dBasePort
		INTEGER,
	cndot1dBasePortIfIndex
		INTEGER,
	cndot1dBasePortCircuit
		OBJECT IDENTIFIER
	}

cndot1dBasePort OBJECT-TYPE
	SYNTAX  INTEGER
	ACCESS  read-only
	STATUS  mandatory
	DESCRIPTION
		"The port number of the port for which this entry
		contains bridge management information."
	::= { cndot1dBasePortEntry 1 }

cndot1dBasePortIfIndex OBJECT-TYPE
	SYNTAX  INTEGER
	ACCESS  read-only
	STATUS  mandatory
	DESCRIPTION
		"The value of the instance of the ifIndex object,
		defined in MIB-II, for the interface corresponding
		to this port."
	::= { cndot1dBasePortEntry 2 }

cndot1dBasePortCircuit OBJECT-TYPE
	SYNTAX  OBJECT IDENTIFIER
	ACCESS  read-only
	STATUS  mandatory
	DESCRIPTION
		"For a port which (potentially) has the same value
		of cndot1dBasePortVirtualRing as another port on the
		same bridge, this object contains the name of an
		object instance unique to this port.  For example,
		in the case where multiple ports correspond one-
		to-one with multiple X.25 virtual circuits, this
		value might identify an (e.g., the first) object
		instance associated with the X.25 virtual circuit
		corresponding to this port.

		For a port which has a unique value of
		dot1dBasePortIfIndex, this object can have the
		value { 0 0 }."
	::= { cndot1dBasePortEntry 3 }


-- The cndot1dStp group
--
-- Implementation of the cndot1dStp group is optional.  It is
-- implemented by those bridges that support the Spanning Tree
-- Protocol.
--

cndot1dStpProtocolSpecification OBJECT-TYPE
	SYNTAX  INTEGER {
		unknown(1),
		decLb100(2),
		ieee8021d(3)
		}
	ACCESS  read-only
	STATUS  mandatory
	DESCRIPTION
		"An indication of what version of the Spanning
		Tree Protocol is being run.  The value
		'decLb100(2)' indicates the DEC LANbridge 100
		Spanning Tree protocol.  IEEE 802.1d
		implementations will return 'ieee8021d(3)'.  If
		future versions of the IEEE Spanning Tree Protocol
		are released that are incompatible with the
		current version a new value will be defined."
	::= { cndot1dStp 1 }

cndot1dStpPriority OBJECT-TYPE
	SYNTAX  INTEGER (0..65535)
	ACCESS  read-write
	STATUS  mandatory
	DESCRIPTION
		"The value of the write-able portion of the Bridge
		ID, i.e., the first two octets of the (8 octet
		long) Bridge ID.  The other (last) 6 octets of the
		Bridge ID are given by the value of
		cndot1dBaseBridgeAddress."
	REFERENCE
		"IEEE 802.1D-1990: Section 4.5.3.7"
	::= { cndot1dStp 2 }

cndot1dStpTimeSinceTopologyChange OBJECT-TYPE
	SYNTAX  TimeTicks
	ACCESS  read-only
	STATUS  mandatory
	DESCRIPTION
		"The time (in hundredths of a second) since the
		last time a topology change was detected by the
		bridge entity."
	REFERENCE
		"IEEE 802.1D-1990: Section 6.8.1.1.3"
	::= { cndot1dStp 3 }

cndot1dStpTopChanges OBJECT-TYPE
	SYNTAX  Counter
	ACCESS  read-only
	STATUS  mandatory
	DESCRIPTION
		"The total number of topology changes detected by
		this bridge since the management entity was last
		reset or initialized."
	REFERENCE
		"IEEE 802.1D-1990: Section 6.8.1.1.3"
	::= { cndot1dStp 4 }

cndot1dStpDesignatedRoot OBJECT-TYPE
	SYNTAX  BridgeId
	ACCESS  read-only
	STATUS  mandatory
	DESCRIPTION
		"The bridge identifier of the root of the spanning
		tree as determined by the Spanning Tree Protocol
		as executed by this node.  This value is used as
		the Root Identifier parameter in all Configuration
		Bridge PDUs originated by this node."
	REFERENCE
		"IEEE 802.1D-1990: Section 4.5.3.1"
	::= { cndot1dStp 5 }

cndot1dStpRootCost OBJECT-TYPE
	SYNTAX  INTEGER
	ACCESS  read-only
	STATUS  mandatory
	DESCRIPTION
		"The cost of the path to the root as seen from
		this bridge."
	REFERENCE
		"IEEE 802.1D-1990: Section 4.5.3.2"
	::= { cndot1dStp 6 }

cndot1dStpRootPort OBJECT-TYPE
	SYNTAX  INTEGER
	ACCESS  read-only
	STATUS  mandatory
	DESCRIPTION
		"The port number of the port which offers the
		lowest cost path from this bridge to the root
		bridge."
	REFERENCE
		"IEEE 802.1D-1990: Section 4.5.3.3"
	::= { cndot1dStp 7 }

cndot1dStpMaxAge OBJECT-TYPE
	SYNTAX  Timeout
	ACCESS  read-only
	STATUS  mandatory
	DESCRIPTION
		"The maximum age of Spanning Tree Protocol
		information learned from the network on any port
		before it is discarded, in units of hundredths of
		a second.  This is the actual value that this
		bridge is currently using."
	REFERENCE
	"IEEE 802.1D-1990: Section 4.5.3.4"
	::= { cndot1dStp 8 }

cndot1dStpHelloTime OBJECT-TYPE
	SYNTAX  Timeout
	ACCESS  read-only
	STATUS  mandatory
	DESCRIPTION
		"The amount of time between the transmission of
		Configuration bridge PDUs by this node on any port
		when it is the root of the spanning tree or trying
		to become so, in units of hundredths of a second.
		This is the actual value that this bridge is
		currently using."
	REFERENCE
		"IEEE 802.1D-1990: Section 4.5.3.5"
	::= { cndot1dStp 9 }

cndot1dStpHoldTime OBJECT-TYPE
	SYNTAX  INTEGER
	ACCESS  read-only
	STATUS  mandatory
	DESCRIPTION
		"This time value determines the interval length
		during which no more than two Configuration bridge
		PDUs shall be transmitted by this node, in units
		of hundredths of a second."
	REFERENCE
	"IEEE 802.1D-1990: Section 4.5.3.14"
	::= { cndot1dStp 10 }

cndot1dStpForwardDelay OBJECT-TYPE
	SYNTAX  Timeout
	ACCESS  read-only
	STATUS  mandatory
	DESCRIPTION
		"This time value, measured in units of hundredths
		of a second, controls how fast a port changes its
		spanning state when moving towards the Forwarding
		state.  The value determines how long the port
		stays in each of the Listening and Learning
		states, which precede the Forwarding state.  This
		value is also used, when a topology change has
		been detected and is underway, to age all dynamic
		entries in the Forwarding Database.  [Note that
		this value is the one that this bridge is
		currently using, in contrast to
		cndot1dStpBridgeForwardDelay which is the value that
		this bridge and all others would start using
		if/when this bridge were to become the root.]"
	REFERENCE
		"IEEE 802.1D-1990: Section 4.5.3.6"
	::= { cndot1dStp 11 }

cndot1dStpBridgeMaxAge OBJECT-TYPE
	SYNTAX  Timeout (600..4000)
	ACCESS  read-write
	STATUS  mandatory
	DESCRIPTION
		"The value that all bridges use for MaxAge when
		this bridge is acting as the root.  Note that
		802.1D-1990 specifies that the range for this
		parameter is related to the value of
		cndot1dStpBridgeHelloTime. The granularity of this
		timer is specified by 802.1D-1990 to be 1 second.
		An agent may return a badValue error if a set is
		attempted to a value which is not a whole number
		of seconds."
	REFERENCE
		"IEEE 802.1D-1990: Section 4.5.3.8"
	::= { cndot1dStp 12 }

cndot1dStpBridgeHelloTime OBJECT-TYPE
	SYNTAX  Timeout (100..1000)
	ACCESS  read-write
	STATUS  mandatory
	DESCRIPTION
		"The value that all bridges use for HelloTime when
		this bridge is acting as the root.  The
		granularity of this timer is specified by 802.1D-
		1990 to be 1 second.  An agent may return a
		badValue error if a set is attempted to a value
		which is not a whole number of seconds."
	REFERENCE
		"IEEE 802.1D-1990: Section 4.5.3.9"
	::= { cndot1dStp 13 }

cndot1dStpBridgeForwardDelay OBJECT-TYPE
	SYNTAX  Timeout (400..3000)
	ACCESS  read-write
	STATUS  mandatory
	DESCRIPTION
		"The value that all bridges use for ForwardDelay
		when this bridge is acting as the root.  Note that
		802.1D-1990 specifies that the range for this
		parameter is related to the value of
		cndot1dStpBridgeMaxAge.  The granularity of this
		timer is specified by 802.1D-1990 to be 1 second.
		An agent may return a badValue error if a set is
		attempted to a value which is not a whole number
		of seconds."
	REFERENCE
		"IEEE 802.1D-1990: Section 4.5.3.10"
	::= { cndot1dStp 14 }


-- The Spanning Tree Port Table

cndot1dStpPortTable OBJECT-TYPE
	SYNTAX  SEQUENCE OF Cndot1dStpPortEntry
	ACCESS  not-accessible
	STATUS  mandatory
	DESCRIPTION
		"A table that contains port-specific information
		for the Spanning Tree Protocol."
	::= { cndot1dStp 15 }

cndot1dStpPortEntry OBJECT-TYPE
	SYNTAX  Cndot1dStpPortEntry
	ACCESS  not-accessible
	STATUS  mandatory
	DESCRIPTION
		"A list of information maintained by every port
		about the Spanning Tree Protocol state for that
		port."
	INDEX   { cndot1dStpPort }
	::= { cndot1dStpPortTable 1 }

Cndot1dStpPortEntry ::= SEQUENCE {
	cndot1dStpPort
		INTEGER,
	cndot1dStpPortPriority
		INTEGER,
	cndot1dStpPortState
		INTEGER,
	cndot1dStpPortEnable
		INTEGER,
	cndot1dStpPortPathCost
		INTEGER,
	cndot1dStpPortDesignatedRoot
		BridgeId,
	cndot1dStpPortDesignatedCost
		INTEGER,
	cndot1dStpPortDesignatedBridge
		BridgeId,
	cndot1dStpPortDesignatedPort
		OCTET STRING,
	cndot1dStpPortForwardTransitions
		Counter
	}

cndot1dStpPort OBJECT-TYPE
	SYNTAX  INTEGER (1..65535)
	ACCESS  read-only
	STATUS  mandatory
	DESCRIPTION
		"The port number of the port for which this entry
		contains Spanning Tree Protocol management
		information."
	REFERENCE
		"IEEE 802.1D-1990: Section 6.8.2.1.2"
	::= { cndot1dStpPortEntry 1 }

cndot1dStpPortPriority OBJECT-TYPE
	SYNTAX  INTEGER (0..255)
	ACCESS  read-write
	STATUS  mandatory
	DESCRIPTION
		"The value of the priority field which is
		contained in the first (in network byte order)
		octet of the (2 octet long) Port ID.  The other
		octet of the Port ID is given by the value of
		cndot1dStpPort."
	REFERENCE
		"IEEE 802.1D-1990: Section 4.5.5.1"
	::= { cndot1dStpPortEntry 2 }

cndot1dStpPortState OBJECT-TYPE
	SYNTAX  INTEGER {
		disabled(1),
		blocking(2),
		listening(3),
		learning(4),
		forwarding(5),
		broken(6)
		}
	ACCESS  read-only
	STATUS  mandatory
	DESCRIPTION
		"The port's current state as defined by
		application of the Spanning Tree Protocol.  This
		state controls what action a port takes on
		reception of a frame.  If the bridge has detected
		a port that is malfunctioning it will place that
		port into the broken(6) state.  For ports which
		are disabled (see cndot1dStpPortEnable), this object
		will have a value of disabled(1)."
	REFERENCE
		"IEEE 802.1D-1990: Section 4.5.5.2"
	::= { cndot1dStpPortEntry 3 }

cndot1dStpPortEnable OBJECT-TYPE
	SYNTAX  INTEGER {
		enabled(1),
		disabled(2)
		}
	ACCESS  read-write
	STATUS  mandatory
	DESCRIPTION
		"The enabled/disabled status of the port."
	REFERENCE
		"IEEE 802.1D-1990: Section 4.5.5.2"
	::= { cndot1dStpPortEntry 4 }

cndot1dStpPortPathCost OBJECT-TYPE
	SYNTAX  INTEGER (1..65535)
	ACCESS  read-write
	STATUS  mandatory
	DESCRIPTION
		"The contribution of this port to the path cost of
		paths towards the spanning tree root which include
		this port.  802.1D-1990 recommends that the
		default value of this parameter be in inverse
		proportion to the speed of the attached LAN."
	REFERENCE
		"IEEE 802.1D-1990: Section 4.5.5.3"
	::= { cndot1dStpPortEntry 5 }

cndot1dStpPortDesignatedRoot OBJECT-TYPE
	SYNTAX  BridgeId
	ACCESS  read-only
	STATUS  mandatory
	DESCRIPTION
		"The unique Bridge Identifier of the Bridge
		recorded as the Root in the Configuration BPDUs
		transmitted by the Designated Bridge for the
		segment to which the port is attached."
	REFERENCE
		"IEEE 802.1D-1990: Section 4.5.5.4"
	::= { cndot1dStpPortEntry 6 }

cndot1dStpPortDesignatedCost OBJECT-TYPE
	SYNTAX  INTEGER
	ACCESS  read-only
	STATUS  mandatory
	DESCRIPTION
		"The path cost of the Designated Port of the
		segment connected to this port.  This value is
		compared to the Root Path Cost field in received
		bridge PDUs."
	REFERENCE
		"IEEE 802.1D-1990: Section 4.5.5.5"
	::= { cndot1dStpPortEntry 7 }

cndot1dStpPortDesignatedBridge OBJECT-TYPE
	SYNTAX  BridgeId
	ACCESS  read-only
	STATUS  mandatory
	DESCRIPTION
		"The Bridge Identifier of the bridge which this
		port considers to be the Designated Bridge for
		this port's segment."
	REFERENCE
		"IEEE 802.1D-1990: Section 4.5.5.6"
	::= { cndot1dStpPortEntry 8 }

cndot1dStpPortDesignatedPort OBJECT-TYPE
	SYNTAX  OCTET STRING (SIZE (2))
	ACCESS  read-only
	STATUS  mandatory
	DESCRIPTION
		"The Port Identifier of the port on the Designated
		Bridge for this port's segment."
	REFERENCE
		"IEEE 802.1D-1990: Section 4.5.5.7"
	::= { cndot1dStpPortEntry 9 }

cndot1dStpPortForwardTransitions OBJECT-TYPE
	SYNTAX  Counter
	ACCESS  read-only
	STATUS  mandatory
	DESCRIPTION
		"The number of times this port has transitioned
		from the Learning state to the Forwarding state."
	::= { cndot1dStpPortEntry 10 }


-- the dot1Tp group

-- Implementation of the dot1Tp group is optional. It is implemented
-- by those bridges that support the transparent bridging mode.
-- A transparent or SRT bridge will implement this group.

-- Currently, Centillion Networks utilizes other proprietary
-- MIBS to support the information is this group with the
-- exception of those object defined here. The proprietary objects
-- in this group follow the standard object identifiers to allow
-- future implementation of the TP group.

cndot1dTpSrFrameForward OBJECT-TYPE
	SYNTAX	EnableIndicator
	ACCESS	read-write
	STATUS	mandatory
	DESCRIPTION
		"Indicates whether the system will forward source
		routed frames if running in transparent bridging
		mode. If this value is disabled(1), the system will
		drop all source-routed frames. The default value
		is disabled(1)."
	::= { cndot1dTp 5 }


END
