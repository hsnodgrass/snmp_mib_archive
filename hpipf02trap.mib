-- ****************************************************************************
--
--                  Integrity Server Trap SNMP MIB
--         Management Information Base for SNMP Network Management
--
--
--      Copyright 1993,2003-2004 Hewlett-Packard Development Company, L.P.
--
--      Hewlett-Packard Company shall not be liable for technical or
--      editorial errors or omissions contained herein. The information in
--      this document is provided "as is" without warranty of any kind and
--      is subject to change without notice. The warranties for HP products
--      are set forth in the express limited warranty statements
--      accompanying such products. Nothing herein should be construed as
--      constituting an additional warranty.
--
--      Confidential computer software. Valid license from HP required for
--      possession, use or copying. Consistent with FAR 12.211 and 12.212,
--      Commercial Computer Software, Computer Software Documentation, and
--      Technical Data for Commercial Items are licensed to the U.S.
--      Government under vendor's standard commercial license.
--
--      The Hewlett-Packard Enterprise number is 11.
--      The ASN.1 prefix to, and including the Hewlett-Packard Enterprise is:
--           1.3.6.1.4.1.11
--
-- ****************************************************************************
--
--
-- * $Date:	11-24-2008$
-- * $Revision:	3.3$
--
--   IPF Trap MIB Revision
--  =========================
--
--      MIB Rev of 1.0 is for ORCA time frame
--              - This is the initial release of this MIB.
--      2.0 - Event Data Now taken from new E0 data base
--      2.1 - Add new Hondo events
--      2.2 - Add new events for support of Eiger, Oly
--      2.3 - Add new events for PFM, other new E0 events, and new 02 events
--      2.4 - Add new events for E0 events, and 3 new temperature 02 events
--      2.5 - Add new events for E0 events Rusa , ARc
--      2.6 - Add new events for E0 events COD, HPVM
--      2.7 - Add new events for E0 events RuSa-E, Merlion
--      2.8 - Add new events for E0 events Tahiti
--      2.9 - Add new events for E0 events Tahiti
--      3.0 - Add new events for E0 events to support Windows Server 2008
--      3.1 - Add new events for E0 events to support Bora Bora
--      3.2 - Add new events for E0 events to support Bora Bora
--      3.3 - Add new events for E0 events to support Bora Bora
--
-- ****************************************************************************

HPIPF02TRAP-MIB DEFINITIONS ::= BEGIN

IMPORTS
enterprises    FROM RFC1155-SMI
DisplayString  FROM RFC1213-MIB
OBJECT-TYPE    FROM RFC-1212
TRAP-TYPE      FROM RFC-1215;

hp                          OBJECT IDENTIFIER ::= { enterprises 11 }
nm                          OBJECT IDENTIFIER ::= { hp 2 }
hpnsa                       OBJECT IDENTIFIER ::= { nm 23 }
hpIpfE0Events               OBJECT IDENTIFIER ::= { hpnsa 35 }
hpIpf02Events               OBJECT IDENTIFIER ::= { hpnsa 45 }

-- The following are objects defined for HP IPF Event Traps

hpIpfEvtDetailStr OBJECT-TYPE
    SYNTAX DisplayString
    ACCESS read-only
    STATUS mandatory
    DESCRIPTION
      "This string provides a detailed description of the Event along with variable information."
    ::= { hpIpf02Events 1 }


-- Traps

hpTempHighWarning752 TRAP-TYPE
     ENTERPRISE hpIpf02Events
     VARIABLES { hpIpfEvtDetailStr }
     DESCRIPTION
        "One of the temperature sensors crossed its lower non-critical threshold."

     --#SUMMARY "Temperature sensor crossed lower non-critical threshold"
     --#ARGUMENTS {}
     --#SEVERITY WARNING
     --#TIMEINDEX 100
     --#STATE OPERATIONAL
::= 752


hpTempHighCritical753 TRAP-TYPE
     ENTERPRISE hpIpf02Events
     VARIABLES { hpIpfEvtDetailStr }
     DESCRIPTION
        "One of the temperature sensors crossed its upper critical threshold."

     --#SUMMARY "A temperature inside the server went far outside the factory specified range"
     --#ARGUMENTS {}
     --#SEVERITY CRITICAL
     --#TIMEINDEX 100
     --#STATE OPERATIONAL
::= 753


hpTempHighNonRecoverable754 TRAP-TYPE
     ENTERPRISE hpIpf02Events
     VARIABLES { hpIpfEvtDetailStr }
     DESCRIPTION
        "One of the temperature sensors crossed its upper non-recoverable threshold."

     --#SUMMARY "Temperature sensor crossed upper non-recoverable threshold."
     --#ARGUMENTS {}
     --#SEVERITY CRITICAL
     --#TIMEINDEX 100
     --#STATE OPERATIONAL
::= 754


hpTemperature4 TRAP-TYPE
     ENTERPRISE hpIpf02Events
     VARIABLES { hpIpfEvtDetailStr }
     DESCRIPTION
        "One of the temperature sensors crossed its upper non-critical threshold."

     --#SUMMARY "A temperature inside the server has gone outside the factory specified range."
     --#ARGUMENTS {}
     --#SEVERITY WARNING
     --#TIMEINDEX 100
     --#STATE OPERATIONAL
::= 4


hpTemperature5 TRAP-TYPE
     ENTERPRISE hpIpf02Events
     VARIABLES { hpIpfEvtDetailStr }
     DESCRIPTION
        "One of the temperature sensors crossed its upper critical threshold."

     --#SUMMARY "A temperature inside the server has gone far outside the factory specified range."
     --#ARGUMENTS {}
     --#SEVERITY CRITICAL
     --#TIMEINDEX 100
     --#STATE OPERATIONAL
::= 5


hpTemperature6 TRAP-TYPE
     ENTERPRISE hpIpf02Events
     VARIABLES { hpIpfEvtDetailStr }
     DESCRIPTION
        "One of the temperature sensors crossed its upper non-recoverable threshold."

     --#SUMMARY "Temperature sensor crossed upper non-recoverable threshold"
     --#ARGUMENTS {}
     --#SEVERITY CRITICAL
     --#TIMEINDEX 100
     --#STATE OPERATIONAL
::= 6


hpTemperature755 TRAP-TYPE
     ENTERPRISE hpIpf02Events
     VARIABLES { hpIpfEvtDetailStr }
     DESCRIPTION
        "A temperature inside the server has gone outside the factory specified range."

     --#SUMMARY "One of the temperature sensors crossed its upper non-critical threshold."
     --#ARGUMENTS {}
     --#SEVERITY WARNING
     --#TIMEINDEX 100
     --#STATE OPERATIONAL
::= 755


hpTemperature756 TRAP-TYPE
     ENTERPRISE hpIpf02Events
     VARIABLES { hpIpfEvtDetailStr }
     DESCRIPTION
        "One of the temperature sensors crossed its upper critical threshold."

     --#SUMMARY "A temperature inside the server went far outside the factory specified range."
     --#ARGUMENTS {}
     --#SEVERITY CRITICAL
     --#TIMEINDEX 100
     --#STATE OPERATIONAL
::= 756


hpEnvironment8 TRAP-TYPE
     ENTERPRISE hpIpf02Events
     VARIABLES { hpIpfEvtDetailStr }
     DESCRIPTION
        "One of the voltage sensors crossed its lower critical threshold."

     --#SUMMARY "A measured voltage in the server has gone far outside the factory specified lower voltage range."
     --#ARGUMENTS {}
     --#SEVERITY CRITICAL
     --#TIMEINDEX 100
     --#STATE OPERATIONAL
::= 8


hpEnvironment9 TRAP-TYPE
     ENTERPRISE hpIpf02Events
     VARIABLES { hpIpfEvtDetailStr }
     DESCRIPTION
        "One of the voltage sensors crossed its lower non-recoverable threshold."

     --#SUMMARY "Voltage sensor crossed lower non-recoverable threshold"
     --#ARGUMENTS {}
     --#SEVERITY CRITICAL
     --#TIMEINDEX 100
     --#STATE OPERATIONAL
::= 9


hpEnvironment10 TRAP-TYPE
     ENTERPRISE hpIpf02Events
     VARIABLES { hpIpfEvtDetailStr }
     DESCRIPTION
        "One of the voltage sensors crossed its upper non-critical threshold."

     --#SUMMARY "A measured voltage in the server has gone outside the factory specified upper voltage range."
     --#ARGUMENTS {}
     --#SEVERITY WARNING
     --#TIMEINDEX 100
     --#STATE OPERATIONAL
::= 10


hpEnvironment12 TRAP-TYPE
     ENTERPRISE hpIpf02Events
     VARIABLES { hpIpfEvtDetailStr }
     DESCRIPTION
        "One of the voltage sensors crossed its upper non-recoverable threshold - Check all boards with this voltage"

     --#SUMMARY "Voltage sensor crossed upper non-recoverable threshold"
     --#ARGUMENTS {}
     --#SEVERITY CRITICAL
     --#TIMEINDEX 100
     --#STATE OPERATIONAL
::= 12


hpEnvironment704 TRAP-TYPE
     ENTERPRISE hpIpf02Events
     VARIABLES { hpIpfEvtDetailStr }
     DESCRIPTION
        "Voltage fault - Check all boards with this voltage"

     --#SUMMARY "Voltage insufficient"
     --#ARGUMENTS {}
     --#SEVERITY WARNING
     --#TIMEINDEX 100
     --#STATE OPERATIONAL
::= 704


hpEnvironment728 TRAP-TYPE
     ENTERPRISE hpIpf02Events
     VARIABLES { hpIpfEvtDetailStr }
     DESCRIPTION
        "Voltage degraded to critical level from less severe - Check all boards with this voltage"

     --#SUMMARY "Voltage reached critical level"
     --#ARGUMENTS {}
     --#SEVERITY CRITICAL
     --#TIMEINDEX 100
     --#STATE OPERATIONAL
::= 728


hpEnvironment705 TRAP-TYPE
     ENTERPRISE hpIpf02Events
     VARIABLES { hpIpfEvtDetailStr }
     DESCRIPTION
        "Voltage degraded to non-recoverable level from less severe - Check all boards with this voltage"

     --#SUMMARY "Voltage reached critical level"
     --#ARGUMENTS {}
     --#SEVERITY CRITICAL
     --#TIMEINDEX 100
     --#STATE OPERATIONAL
::= 705


hpEnvironment706 TRAP-TYPE
     ENTERPRISE hpIpf02Events
     VARIABLES { hpIpfEvtDetailStr }
     DESCRIPTION
        "Voltage becomes non-recoverable from either critical level or less severe level - Check all boards with this voltage"

     --#SUMMARY "Power Pod Voltage Fault"
     --#ARGUMENTS {}
     --#SEVERITY CRITICAL
     --#TIMEINDEX 100
     --#STATE OPERATIONAL
::= 706


hpEnvironment707 TRAP-TYPE
     ENTERPRISE hpIpf02Events
     VARIABLES { hpIpfEvtDetailStr }
     DESCRIPTION
        "Voltage absent"

     --#SUMMARY "Voltage absent"
     --#ARGUMENTS {}
     --#SEVERITY WARNING
     --#TIMEINDEX 100
     --#STATE OPERATIONAL
::= 707


hpFan710 TRAP-TYPE
     ENTERPRISE hpIpf02Events
     VARIABLES { hpIpfEvtDetailStr }
     DESCRIPTION
        "Fan speed lags"

     --#SUMMARY "Fan speed lags"
     --#ARGUMENTS {}
     --#SEVERITY WARNING
     --#TIMEINDEX 100
     --#STATE OPERATIONAL
::= 710


hpChassis26 TRAP-TYPE
     ENTERPRISE hpIpf02Events
     VARIABLES { hpIpfEvtDetailStr }
     DESCRIPTION
        "The chassis has been opened."

     --#SUMMARY "The server's built-in sensors have detected an open chassis door."
     --#ARGUMENTS {}
     --#SEVERITY WARNING
     --#TIMEINDEX 100
     --#STATE OPERATIONAL
::= 26


hpBmcFirmware730 TRAP-TYPE
     ENTERPRISE hpIpf02Events
     VARIABLES { hpIpfEvtDetailStr }
     DESCRIPTION
        "The BMC firmware did not detect the system firmware boot."

     --#SUMMARY "The BMC firmware did not detect the system firmware boot"
     --#ARGUMENTS {}
     --#SEVERITY CRITICAL
     --#TIMEINDEX 100
     --#STATE OPERATIONAL
::= 730


hpRedundantPower720 TRAP-TYPE
     ENTERPRISE hpIpf02Events
     VARIABLES { hpIpfEvtDetailStr }
     DESCRIPTION
        "Power supply failed or disconnected"

     --#SUMMARY "Power supply failure"
     --#ARGUMENTS {}
     --#SEVERITY WARNING
     --#TIMEINDEX 100
     --#STATE OPERATIONAL
::= 720


hpRedundantPower732 TRAP-TYPE
     ENTERPRISE hpIpf02Events
     VARIABLES { hpIpfEvtDetailStr }
     DESCRIPTION
        "The Power supply's sensors detect possible problems"

     --#SUMMARY "The power supply sensors detect a possible problem"
     --#ARGUMENTS {}
     --#SEVERITY WARNING
     --#TIMEINDEX 100
     --#STATE OPERATIONAL
::= 732


hpRedundantPower722 TRAP-TYPE
     ENTERPRISE hpIpf02Events
     VARIABLES { hpIpfEvtDetailStr }
     DESCRIPTION
        "Power supply AC lost"

     --#SUMMARY "Power supply AC lost"
     --#ARGUMENTS {}
     --#SEVERITY WARNING
     --#TIMEINDEX 100
     --#STATE OPERATIONAL
::= 722


hpRedundantPower757 TRAP-TYPE
     ENTERPRISE hpIpf02Events
     VARIABLES { hpIpfEvtDetailStr }
     DESCRIPTION
        "The Power Supply AC voltage was lost or is out of range."

     --#SUMMARY "The AC voltage to the power supply was lost or is out of range."
     --#ARGUMENTS {}
     --#SEVERITY WARNING
     --#TIMEINDEX 100
     --#STATE OPERATIONAL
::= 757


hpRedundantPower758 TRAP-TYPE
     ENTERPRISE hpIpf02Events
     VARIABLES { hpIpfEvtDetailStr }
     DESCRIPTION
        "The AC voltage connected to the power supply is out of range."

     --#SUMMARY "The power supply AC voltage is out of range."
     --#ARGUMENTS {}
     --#SEVERITY WARNING
     --#TIMEINDEX 100
     --#STATE OPERATIONAL
::= 758


hpPowerSupply731 TRAP-TYPE
     ENTERPRISE hpIpf02Events
     VARIABLES { hpIpfEvtDetailStr }
     DESCRIPTION
        "A/C Failed, disconnected, or out of range"

     --#SUMMARY "A/C Power failed, disconnected, or out of range"
     --#ARGUMENTS {}
     --#SEVERITY CRITICAL
     --#TIMEINDEX 100
     --#STATE OPERATIONAL
::= 731


hpPowerSupply726 TRAP-TYPE
     ENTERPRISE hpIpf02Events
     VARIABLES { hpIpfEvtDetailStr }
     DESCRIPTION
        "A/C Failed, disconnected, or out of range"

     --#SUMMARY "Power failure in power supply"
     --#ARGUMENTS {}
     --#SEVERITY CRITICAL
     --#TIMEINDEX 100
     --#STATE OPERATIONAL
::= 726


hpSystemHW733 TRAP-TYPE
     ENTERPRISE hpIpf02Events
     VARIABLES { hpIpfEvtDetailStr }
     DESCRIPTION
        "Cooling unit warning"

     --#SUMMARY "Cooling unit warning"
     --#ARGUMENTS {}
     --#SEVERITY WARNING
     --#TIMEINDEX 100
     --#STATE OPERATIONAL
::= 733


hpSystemHW734 TRAP-TYPE
     ENTERPRISE hpIpf02Events
     VARIABLES { hpIpfEvtDetailStr }
     DESCRIPTION
        "Cooling unit failure"

     --#SUMMARY "Cooling unit failure"
     --#ARGUMENTS {}
     --#SEVERITY CRITICAL
     --#TIMEINDEX 100
     --#STATE OPERATIONAL
::= 734


hpECCMemory518 TRAP-TYPE
     ENTERPRISE hpIpf02Events
     VARIABLES { hpIpfEvtDetailStr }
     DESCRIPTION
        "Uncorrectable multi-bit ECC error has occurred in memory module"

     --#SUMMARY "Uncorrectable multi-bit ECC error has occurred"
     --#ARGUMENTS {}
     --#SEVERITY CRITICAL
     --#TIMEINDEX 100
     --#STATE OPERATIONAL
::= 518


hpSystemFW700 TRAP-TYPE
     ENTERPRISE hpIpf02Events
     VARIABLES { hpIpfEvtDetailStr }
     DESCRIPTION
        "System firmware error"

     --#SUMMARY "Generic trap for Critical or Fatal type E0 event from system firmware"
     --#ARGUMENTS {}
     --#SEVERITY CRITICAL
     --#TIMEINDEX 100
     --#STATE OPERATIONAL
::= 700


hpSystemHW744 TRAP-TYPE
     ENTERPRISE hpIpf02Events
     VARIABLES { hpIpfEvtDetailStr }
     DESCRIPTION
        "System event log almost full"

     --#SUMMARY "System event log almost full"
     --#ARGUMENTS {}
     --#SEVERITY WARNING
     --#TIMEINDEX 100
     --#STATE OPERATIONAL
::= 744


hpSystemHW735 TRAP-TYPE
     ENTERPRISE hpIpf02Events
     VARIABLES { hpIpfEvtDetailStr }
     DESCRIPTION
        "BMC entering special mode"

     --#SUMMARY "BMC entering special mode"
     --#ARGUMENTS {}
     --#SEVERITY WARNING
     --#TIMEINDEX 100
     --#STATE OPERATIONAL
::= 735


hpSystemHW729 TRAP-TYPE
     ENTERPRISE hpIpf02Events
     VARIABLES { hpIpfEvtDetailStr }
     DESCRIPTION
        "System shut-down or reset caused by sensor reading. "

     --#SUMMARY "System shut-down or reset caused by sensor reading"
     --#ARGUMENTS {}
     --#SEVERITY CRITICAL
     --#TIMEINDEX 100
     --#STATE OPERATIONAL
::= 729


hpSystemHW745 TRAP-TYPE
     ENTERPRISE hpIpf02Events
     VARIABLES { hpIpfEvtDetailStr }
     DESCRIPTION
        "TOC interrupt (crash dump)"

     --#SUMMARY "TOC interrupt (crash dump)"
     --#ARGUMENTS {}
     --#SEVERITY CRITICAL
     --#TIMEINDEX 100
     --#STATE OPERATIONAL
::= 745


hpSystemHW746 TRAP-TYPE
     ENTERPRISE hpIpf02Events
     VARIABLES { hpIpfEvtDetailStr }
     DESCRIPTION
        "INIT Initiated"

     --#SUMMARY "INIT Initiated"
     --#ARGUMENTS {}
     --#SEVERITY CRITICAL
     --#TIMEINDEX 100
     --#STATE OPERATIONAL
::= 746


hpSystemHW751 TRAP-TYPE
     ENTERPRISE hpIpf02Events
     VARIABLES { hpIpfEvtDetailStr }
     DESCRIPTION
        "PCI parity error detected"

     --#SUMMARY "PCI parity error detected"
     --#ARGUMENTS {}
     --#SEVERITY WARNING
     --#TIMEINDEX 100
     --#STATE OPERATIONAL
::= 751


hpSystemHW747 TRAP-TYPE
     ENTERPRISE hpIpf02Events
     VARIABLES { hpIpfEvtDetailStr }
     DESCRIPTION
        "PCI system error detected"

     --#SUMMARY "PCI system error detected"
     --#ARGUMENTS {}
     --#SEVERITY WARNING
     --#TIMEINDEX 100
     --#STATE OPERATIONAL
::= 747


hpSystemFW699 TRAP-TYPE
     ENTERPRISE hpIpf02Events
     VARIABLES { hpIpfEvtDetailStr }
     DESCRIPTION
        "Machine Check Initiated"

     --#SUMMARY "Machine Check Initiated"
     --#ARGUMENTS {}
     --#SEVERITY CRITICAL
     --#TIMEINDEX 100
     --#STATE OPERATIONAL
::= 699


hpSystemHW113 TRAP-TYPE
     ENTERPRISE hpIpf02Events
     VARIABLES { hpIpfEvtDetailStr }
     DESCRIPTION
        "A SCSI cable has been removed from the hot swap cage."

     --#SUMMARY "Hot Swap Cage: SCSI cable removed"
     --#ARGUMENTS {}
     --#SEVERITY WARNING
     --#TIMEINDEX 100
     --#STATE OPERATIONAL
::= 113


hpSystemHW748 TRAP-TYPE
     ENTERPRISE hpIpf02Events
     VARIABLES { hpIpfEvtDetailStr }
     DESCRIPTION
        "OS run-time critical shutdown"

     --#SUMMARY "OS run-time critical shutdown"
     --#ARGUMENTS {}
     --#SEVERITY CRITICAL
     --#TIMEINDEX 100
     --#STATE OPERATIONAL
::= 748


hpSystemHW749 TRAP-TYPE
     ENTERPRISE hpIpf02Events
     VARIABLES { hpIpfEvtDetailStr }
     DESCRIPTION
        "ACPI state S5 (soft-off, entered by override)"

     --#SUMMARY "ACPI state S5 (soft-off, entered by override)"
     --#ARGUMENTS {}
     --#SEVERITY WARNING
     --#TIMEINDEX 100
     --#STATE OPERATIONAL
::= 749


hpSystemHW736 TRAP-TYPE
     ENTERPRISE hpIpf02Events
     VARIABLES { hpIpfEvtDetailStr }
     DESCRIPTION
        "Watchdog timer expired - hard reset"

     --#SUMMARY "Watchdog timer expired - hard reset"
     --#ARGUMENTS {}
     --#SEVERITY CRITICAL
     --#TIMEINDEX 100
     --#STATE OPERATIONAL
::= 736


hpSystemHW737 TRAP-TYPE
     ENTERPRISE hpIpf02Events
     VARIABLES { hpIpfEvtDetailStr }
     DESCRIPTION
        "Watchdog timer expired - power-off"

     --#SUMMARY "Watchdog timer expired - power-off"
     --#ARGUMENTS {}
     --#SEVERITY CRITICAL
     --#TIMEINDEX 100
     --#STATE OPERATIONAL
::= 737


hpSystemHW738 TRAP-TYPE
     ENTERPRISE hpIpf02Events
     VARIABLES { hpIpfEvtDetailStr }
     DESCRIPTION
        "Watchdog timer expired - power-cycle"

     --#SUMMARY "Watchdog timer expired - power-cycle"
     --#ARGUMENTS {}
     --#SEVERITY CRITICAL
     --#TIMEINDEX 100
     --#STATE OPERATIONAL
::= 738


hpSystemHW739 TRAP-TYPE
     ENTERPRISE hpIpf02Events
     VARIABLES { hpIpfEvtDetailStr }
     DESCRIPTION
        "Missing FRU device"

     --#SUMMARY "Missing FRU device"
     --#ARGUMENTS {}
     --#SEVERITY CRITICAL
     --#TIMEINDEX 100
     --#STATE OPERATIONAL
::= 739


hpSystemHW740 TRAP-TYPE
     ENTERPRISE hpIpf02Events
     VARIABLES { hpIpfEvtDetailStr }
     DESCRIPTION
        "Missing Entity"

     --#SUMMARY "Missing Entity"
     --#ARGUMENTS {}
     --#SEVERITY CRITICAL
     --#TIMEINDEX 100
     --#STATE OPERATIONAL
::= 740




END
