--
-- Name:       Citrix Common MIB Header
-- Purpose:    Common Object Definitions for the Citrix enterprise MIBs
-- File:       CITRIX.MIB
-- Enterprise: 1.3.6.1.4.1
--
-- Copyright 1999 - 2009 Citrix Systems, Inc.  All Rights Reserved
--

CITRIX-COMMON-MIB DEFINITIONS ::= BEGIN

-- Imports

IMPORTS
    enterprises             FROM RFC1155-SMI;    

-- Citrix enterprise ID
    citrix                  OBJECT IDENTIFIER ::= { enterprises 3845 }

-- Product Root Node
    product		    OBJECT IDENTIFIER ::= { citrix 3 }

-- Product Types
    server		    OBJECT IDENTIFIER ::= { product 1 }
    managementUtilities     OBJECT IDENTIFIER ::= { product 2 }
    productManagementGroup  OBJECT IDENTIFIER ::= { product 3 }

-- Server Products
    metaframe		    OBJECT IDENTIFIER ::= { server 1 }

-- Management Utilities
    metaframeManager        OBJECT IDENTIFIER ::= { managementUtilities 1 }

-- Product Management Group
    rm                      OBJECT IDENTIFIER ::= { productManagementGroup 1 }

END
