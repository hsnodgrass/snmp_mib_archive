-- ****************************************************************************
--
--                           SCSI Devices
--         Management Information Base for SNMP Network Management
--
--
--      Copyright 1992,2007 Hewlett-Packard Development Company, L.P.
--
--      Hewlett-Packard Company shall not be liable for technical or
--      editorial errors or omissions contained herein. The information in
--      this document is provided "as is" without warranty of any kind and
--      is subject to change without notice. The warranties for HP products
--      are set forth in the express limited warranty statements
--      accompanying such products. Nothing herein should be construed as
--      constituting an additional warranty.
--
--      Confidential computer software. Valid license from HP required for
--      possession, use or copying. Consistent with FAR 12.211 and 12.212,
--      Commercial Computer Software, Computer Software Documentation, and
--      Technical Data for Commercial Items are licensed to the U.S.
--      Government under vendor's standard commercial license.
--
--      Refer to the READMIB.RDM file for more information about the
--      organization of the information in the Compaq Enterprise.
--
--      The Compaq Enterprise number is 232.
--      The ASN.1 prefix to, and including the Compaq Enterprise is:
--           1.3.6.1.4.1.232
--
-- ****************************************************************************

CPQSCSI-MIB DEFINITIONS ::= BEGIN

    IMPORTS
        compaq                  FROM CPQHOST-MIB
        enterprises             FROM RFC1155-SMI
        Counter                 FROM RFC1155-SMI
        Gauge                   FROM RFC1155-SMI
        DisplayString           FROM RFC1213-MIB
        OBJECT-TYPE             FROM RFC-1212
        TRAP-TYPE               FROM RFC-1215
        sysName                 FROM RFC1213-MIB
        cpqHoTrapFlags          FROM CPQHOST-MIB;

--  compaq            OBJECT IDENTIFIER ::= { enterprises 232 }
    cpqScsi           OBJECT IDENTIFIER ::= { compaq 5 }
    cpqScsiMibRev     OBJECT IDENTIFIER ::= { cpqScsi 1 }
    cpqScsiComponent  OBJECT IDENTIFIER ::= { cpqScsi 2 }
    cpqScsiTrap       OBJECT IDENTIFIER ::= { cpqScsi 3 }
    cpqTapeComponent  OBJECT IDENTIFIER ::= { cpqScsi 4 }
    cpqSasComponent   OBJECT IDENTIFIER ::= { cpqScsi 5 }

    cpqScsiInterface  OBJECT IDENTIFIER ::= { cpqScsiComponent 1 }
    cpqScsiCntlr      OBJECT IDENTIFIER ::= { cpqScsiComponent 2 }
    cpqScsiLogDrv     OBJECT IDENTIFIER ::= { cpqScsiComponent 3 }
    cpqScsiPhyDrv     OBJECT IDENTIFIER ::= { cpqScsiComponent 4 }
    cpqScsiTarget     OBJECT IDENTIFIER ::= { cpqScsiComponent 5 }
    cpqScsiCd         OBJECT IDENTIFIER ::= { cpqScsiComponent 6 }

    cpqScsiOsNetWare  OBJECT IDENTIFIER ::= { cpqScsiInterface 1 }
    cpqScsiOsCommon   OBJECT IDENTIFIER ::= { cpqScsiInterface 4 }

    cpqTapePhyDrv     OBJECT IDENTIFIER ::= { cpqTapeComponent 1 }
    cpqTapeCounters   OBJECT IDENTIFIER ::= { cpqTapeComponent 2 }
    cpqTapeLibrary    OBJECT IDENTIFIER ::= { cpqTapeComponent 3 }

    cpqSasHba         OBJECT IDENTIFIER ::= { cpqSasComponent 1 }
    cpqSasPhyDrv      OBJECT IDENTIFIER ::= { cpqSasComponent 2 }
    cpqSasLogDrv      OBJECT IDENTIFIER ::= { cpqSasComponent 3 }
    cpqSasTapeDrv     OBJECT IDENTIFIER ::= { cpqSasComponent 4 }

-- The following groups have been deprecated
    cpqSbScsiBus      OBJECT IDENTIFIER ::= { compaq 7 }
    cpqSbScsiMibRev   OBJECT IDENTIFIER ::= { cpqSbScsiBus 1 }
    cpqSbDevice       OBJECT IDENTIFIER ::= { cpqSbScsiBus 2 }


-- ****************************************************************************
--   SCSI MIB Revision
--   =================
--
-- The compaq enterprise               (1.3.6.1.4.1.232)
--      cpqScsi Group                  (1.3.6.1.4.1.232.5)
--       cpqScsiMibRev Group           (1.3.6.1.4.1.232.5.1)
--
--
--      A Storage Agent conforming to this document will return a
--      cpqScsiMibRevMajor of one (1) and a cpqScsiMibRevMinor of
--      thirty eight (38).
--
--
--    Implementation of the MibRev group is mandatory for all agents
--    supporting the Compaq SCSI MIB.
--
-- ****************************************************************************

    cpqScsiMibRevMajor OBJECT-TYPE
       SYNTAX  INTEGER (1..65535)
       ACCESS  read-only
       STATUS  mandatory
       DESCRIPTION
           "The Major Revision level.

            A change in the major revision level represents a major change
            in the architecture of the MIB.  A change in the major revision
            level may indicate a significant change in the information
            supported and/or the meaning of the supported information,
            correct interpretation of data may require a MIB document with
            the same major revision level."
       ::= { cpqScsiMibRev 1 }

       cpqScsiMibRevMinor OBJECT-TYPE
       SYNTAX  INTEGER (0..65535)
       ACCESS  read-only
       STATUS  mandatory
       DESCRIPTION
           "The Minor Revision level.

            A change in the minor revision level may represent some minor
            additional support; no changes to any pre-existing information
            has occurred."
       ::= { cpqScsiMibRev 2 }

       cpqScsiMibCondition OBJECT-TYPE
           SYNTAX  INTEGER {
               other(1),
               ok(2),
               degraded(3),
               failed(4)
               }
           ACCESS  read-only
           STATUS  mandatory
           DESCRIPTION
               "The overall condition.

                This object represents the overall status of the SCSI system
                represented by this MIB."
           ::= { cpqScsiMibRev 3 }

-- ****************************************************************************
--    SCSI NetWare Driver Information
--    ===============================
--
-- The compaq enterprise               (1.3.6.1.4.1.232)
--      cpqScsi Group                  (1.3.6.1.4.1.232.5)
--       cpqScsiComponent Group        (1.3.6.1.4.1.232.5.2)
--        cpqScsiInterface Group       (1.3.6.1.4.1.232.5.2.1)
--         cpqScsiOsNetWare Group      (1.3.6.1.4.1.232.5.2.1.1)
--
--  Implementation of the osNetWare group is mandatory for all agents that
--  support the SCSI MIB in a osNetWare 3x host operating
--  environment.
--
-- ****************************************************************************

    cpqScsiNw3xDriverName OBJECT-TYPE
        SYNTAX  DisplayString (SIZE (0..40))
        ACCESS  read-only
        STATUS  deprecated
        DESCRIPTION
            "SCSI Drive Device Driver Name.

            This is the name of the NetWare v3.1x SCSI device driver.  It
            can be used for identification purposes."
        ::= { cpqScsiOsNetWare 1 }

    cpqScsiNw3xDriverVers OBJECT-TYPE
        SYNTAX  DisplayString (SIZE (0..5))
        ACCESS  read-only
        STATUS  deprecated
        DESCRIPTION
           "SCSI Drive Device Driver Version.

            This is the version of the NetWare v3.1x SCSI device driver.
            It can be used for identification purposes."
       ::= { cpqScsiOsNetWare 2 }

    cpqScsiNw3xDriverPollType OBJECT-TYPE
        SYNTAX  INTEGER
        {
           other(1),
           polled(2),
           demand(3)
        }
        ACCESS  read-only
        STATUS  deprecated
        DESCRIPTION
           "SCSI Drive Device Driver Poll Type.

            The SNMP instrument agent collects information from the
            device driver in two ways:

            other(1)
              The management agent does not recognize this poll type.
              You may need to upgrade your software.

            polled(2)
              Indicates that the information is periodically requested and
              stored by the server based agent and is available when
              requested.

            demand(3)
              Indicates that the information is collected at the time of the
              request."
       ::= { cpqScsiOsNetWare 3 }

    cpqScsiNw3xDriverPollTime OBJECT-TYPE
        SYNTAX  INTEGER (1..300)
        ACCESS  read-only
        STATUS  deprecated
        DESCRIPTION
           "SCSI Drive Device Driver Poll Time.

            If the nw3xDriverPollType is polled(2) this value shows
            how frequently, in seconds, the instrument agent requests
            information from the device driver.

            To change the poll time, you need to unload and then reload the
            instrument agent using the following commands:

               UNLOAD CPQDSKSA
               LOAD CPQDSKSA /U<time>

            The parameter /U specifies the frequency of updates in seconds.
            The variable <time> represents the number of seconds that the
            NLM should wait before collecting new data.  The minimum is one
            second and the maximum value is 300 seconds (five minutes)."
       ::= { cpqScsiOsNetWare 4 }

-- ****************************************************************************
--    SCSI NetWare Controller Information
--    ===================================
--
-- The compaq enterprise               (1.3.6.1.4.1.232)
--      cpqScsi Group                  (1.3.6.1.4.1.232.5)
--       cpqScsiComponent Group        (1.3.6.1.4.1.232.5.2)
--        cpqScsiInterface Group       (1.3.6.1.4.1.232.5.2.1)
--         cpqScsiOsNetWare Group      (1.3.6.1.4.1.232.5.2.1.1)
--          cpqScsiNw3xCntlrInfoTable  (1.3.6.1.4.1.232.5.2.1.1.5)
--
-- ****************************************************************************

    cpqScsiNw3xCntlrInfoTable OBJECT-TYPE
        SYNTAX  SEQUENCE OF CpqScsiNw3xCntlrInfoEntry
        ACCESS  not-accessible
        STATUS  deprecated
        DESCRIPTION
           "SCSI Controller Information Table."
        ::= { cpqScsiOsNetWare 5 }

    cpqScsiNw3xCntlrInfoEntry OBJECT-TYPE
        SYNTAX  CpqScsiNw3xCntlrInfoEntry
        ACCESS  not-accessible
        STATUS  deprecated
        DESCRIPTION
           "SCSI Controller Information Table Entry."
        INDEX   { cpqScsiNw3xCntlrIndex, cpqScsiNw3xBusIndex }
        ::= { cpqScsiNw3xCntlrInfoTable 1 }

        CpqScsiNw3xCntlrInfoEntry ::= SEQUENCE
        {
             cpqScsiNw3xCntlrIndex      INTEGER,
             cpqScsiNw3xBusIndex        INTEGER,
             cpqScsiNw3xXptDesc         DisplayString,
             cpqScsiNw3xXptVers         DisplayString,
             cpqScsiNw3xSimDesc         DisplayString,
             cpqScsiNw3xSimVers         DisplayString,
             cpqScsiNw3xHbaDesc         DisplayString
        }

    cpqScsiNw3xCntlrIndex OBJECT-TYPE
        SYNTAX  INTEGER (0..255)
        ACCESS  read-only
        STATUS  deprecated
        DESCRIPTION
           "SCSI Controller Index.

            The controller index indicates to which SCSI adapter instance
            this table entry belongs.  The controller index is the physical
            slot in the computer system where the adapter is located."
        ::= { cpqScsiNw3xCntlrInfoEntry 1 }

    cpqScsiNw3xBusIndex OBJECT-TYPE
        SYNTAX  INTEGER (0..255)
        ACCESS  read-only
        STATUS  deprecated
        DESCRIPTION
           "SCSI Bus Index.

            The bus index indicates to which SCSI bus instance on an
            adapter this table entry belongs.  The instances start
            at one and increment for each SCSI bus on an adapter."
        ::= { cpqScsiNw3xCntlrInfoEntry 2 }

    cpqScsiNw3xXptDesc OBJECT-TYPE
        SYNTAX  DisplayString (SIZE (0..40))
        ACCESS  read-only
        STATUS  deprecated
        DESCRIPTION
           "SCSI XPT Description.

            This is a description of the Transport Layer (XPT) module,
            CPQSXPT.DSK.  The Transport Layer manages requests from the
            device driver and routes them to the appropriate SCSI Interface
            Module (SIM).  This architecture is based on the ANSI SCSI-2
            Common Access Method (CAM) specification."
        ::= { cpqScsiNw3xCntlrInfoEntry 3 }

    cpqScsiNw3xXptVers OBJECT-TYPE
        SYNTAX  DisplayString (SIZE (0..5))
        ACCESS  read-only
        STATUS  deprecated
        DESCRIPTION
           "SCSI XPT Version.

            This is the version of the Transport Layer (XPT) module,
            CPQSXPT.DSK.  The Transport Layer manages requests from the
            device driver and routes them to the appropriate SCSI Interface
            Module (SIM).  This architecture is based on the ANSI SCSI-2
            Common Access Method (CAM) specification."
        ::= { cpqScsiNw3xCntlrInfoEntry 4 }

    cpqScsiNw3xSimDesc OBJECT-TYPE
        SYNTAX  DisplayString (SIZE (0..40))
        ACCESS  read-only
        STATUS  deprecated
        DESCRIPTION
           "SCSI SIM Description.

            This is a description of the SCSI Interface Module (SIM).
            Each type of controller model has a specific SIM designed for it.
            The SIM accepts requests from the Transport Layer and delivers
            them to the physical device.  This architecture is based on the
            ANSI SCSI-2 Common Access Method (CAM) specification."
        ::= { cpqScsiNw3xCntlrInfoEntry 5 }

    cpqScsiNw3xSimVers OBJECT-TYPE
        SYNTAX  DisplayString (SIZE (0..5))
        ACCESS  read-only
        STATUS  deprecated
        DESCRIPTION
           "SCSI SIM Version.

            This is the version of the SCSI Interface Module (SIM).
            Each type of controller model has a specific SIM designed for it.
            The SIM accepts requests from the Transport Layer and delivers
            them to the physical device.  This architecture is based on the
            ANSI SCSI-2 Common Access Method (CAM) specification."
        ::= { cpqScsiNw3xCntlrInfoEntry 6 }

    cpqScsiNw3xHbaDesc OBJECT-TYPE
        SYNTAX  DisplayString (SIZE (0..16))
        ACCESS  read-only
        STATUS  deprecated
        DESCRIPTION
           "SCSI HBA Description.

            This is a description of the SCSI Host Bus Adapter (HBA).
            An HBA represents one instance of a SCSI bus in the SCSI
            Interface Module (SIM).  This architecture is based on the
            ANSI SCSI-2 Common Access Method (CAM) specification."
        ::= { cpqScsiNw3xCntlrInfoEntry 7 }

-- ****************************************************************************
--    SCSI NetWare Logical Drive Statistics
--    =====================================
--
-- The compaq enterprise               (1.3.6.1.4.1.232)
--      cpqScsi Group                  (1.3.6.1.4.1.232.5)
--       cpqScsiComponent Group        (1.3.6.1.4.1.232.5.2)
--        cpqScsiInterface Group       (1.3.6.1.4.1.232.5.2.1)
--         cpqScsiOsNetWare Group      (1.3.6.1.4.1.232.5.2.1.1)
--          cpqScsiLogDrvStatTable     (1.3.6.1.4.1.232.5.2.1.1.6)
--
-- ****************************************************************************

    cpqScsiLogDrvStatTable OBJECT-TYPE
        SYNTAX  SEQUENCE OF CpqScsiLogDrvStatEntry
        ACCESS  not-accessible
        STATUS  deprecated
        DESCRIPTION
           "SCSI Logical Drive Statistics Table."
        ::= { cpqScsiOsNetWare 6 }

    cpqScsiLogDrvStatEntry OBJECT-TYPE
        SYNTAX  CpqScsiLogDrvStatEntry
        ACCESS  not-accessible
        STATUS  deprecated
        DESCRIPTION
           "SCSI Device Driver Statistics Table Entry."
        INDEX   { cpqScsiNw3xStatCntlrIndex, cpqScsiNw3xStatBusIndex,
                 cpqScsiNw3xStatLogDrvIndex }
        ::= { cpqScsiLogDrvStatTable 1 }

        CpqScsiLogDrvStatEntry ::= SEQUENCE
        {
              cpqScsiNw3xStatCntlrIndex  INTEGER,
              cpqScsiNw3xStatBusIndex    INTEGER,
              cpqScsiNw3xStatLogDrvIndex INTEGER,
              cpqScsiNw3xTotalReads      Counter,
              cpqScsiNw3xTotalWrites     Counter,
              cpqScsiNw3xCorrReads       Counter,
              cpqScsiNw3xCorrWrites      Counter,
              cpqScsiNw3xFatalReads      Counter,
              cpqScsiNw3xFatalWrites     Counter
        }

    cpqScsiNw3xStatCntlrIndex OBJECT-TYPE
        SYNTAX  INTEGER (0..255)
        ACCESS  read-only
        STATUS  deprecated
        DESCRIPTION
           "SCSI Controller Index.

            The controller index indicates to which SCSI adapter instance
            this table entry belongs.  The controller index is the physical
            slot in the computer system where the adapter is located."
        ::= { cpqScsiLogDrvStatEntry 1 }

    cpqScsiNw3xStatBusIndex OBJECT-TYPE
        SYNTAX  INTEGER (0..225)
        ACCESS  read-only
        STATUS  deprecated
        DESCRIPTION
           "SCSI Bus Index.

            The bus index indicates to which SCSI bus instance on an
            adapter this table entry belongs.  The instances start
            at one and increment for each SCSI bus on a card."
        ::= { cpqScsiLogDrvStatEntry 2 }

    cpqScsiNw3xStatLogDrvIndex OBJECT-TYPE
        SYNTAX  INTEGER (0..225)
        ACCESS  read-only
        STATUS  deprecated
        DESCRIPTION
           "SCSI Logical Drive Index.

            The logical drive index indicates to which logical drive
            instance on a SCSI bus this table entry belongs.  The logical
            drive index starts at one and increments for each logical drive
            on the SCSI bus."
        ::= { cpqScsiLogDrvStatEntry 3 }

    cpqScsiNw3xTotalReads OBJECT-TYPE
        SYNTAX  Counter
        ACCESS  read-only
        STATUS  deprecated
        DESCRIPTION
           "SCSI Logical Drive Total Reads.

            This shows the total number of reads performed by the device
            driver to this logical drive.  This number is reset each time the
            device driver is loaded for this logical drive."
        ::= { cpqScsiLogDrvStatEntry 4 }

    cpqScsiNw3xTotalWrites OBJECT-TYPE
        SYNTAX  Counter
        ACCESS  read-only
        STATUS  deprecated
        DESCRIPTION
           "SCSI Logical Drive Total Writes.

            This shows the total number of writes performed by the device
            driver to this logical drive.  This number is reset each time the
            device driver is loaded for this logical drive."
        ::= { cpqScsiLogDrvStatEntry 5 }

    cpqScsiNw3xCorrReads OBJECT-TYPE
        SYNTAX  Counter
        ACCESS  read-only
        STATUS  deprecated
        DESCRIPTION
           "SCSI Logical Drive Corrected Reads.

            This is the total number of read commands sent to the specified
            logical drive which had to be corrected by fault tolerance.
            This number is reset each time the device driver is loaded for
            this logical drive."
        ::= { cpqScsiLogDrvStatEntry 6 }

    cpqScsiNw3xCorrWrites OBJECT-TYPE
        SYNTAX  Counter
        ACCESS  read-only
        STATUS  deprecated
        DESCRIPTION
           "SCSI Logical Drive Corrected Writes.

            This is the total number of write commands sent to the specified
            logical drive which had to be corrected by fault tolerance.
            This number is reset each time the device driver is loaded for
            this logical drive."
        ::= { cpqScsiLogDrvStatEntry 7 }

    cpqScsiNw3xFatalReads OBJECT-TYPE
        SYNTAX  Counter
        ACCESS  read-only
        STATUS  deprecated
        DESCRIPTION
           "SCSI Logical Drive Fatal Reads.

            This is the total number of read commands sent to the specified
            logical drive which failed.  This number is reset each time the
            device driver is loaded for this logical drive."
        ::= { cpqScsiLogDrvStatEntry 8 }

    cpqScsiNw3xFatalWrites OBJECT-TYPE
        SYNTAX  Counter
        ACCESS  read-only
        STATUS  deprecated
        DESCRIPTION
           "SCSI Logical Drive Fatal Writes.

            This is the total number of write commands sent to the specified
            logical drive which failed.  This number is reset each time the
            device driver is loaded for this logical drive."
        ::= { cpqScsiLogDrvStatEntry 9 }

-- ****************************************************************************
--    SCSI NetWare Volume Map Table
--    =============================
--
-- The compaq enterprise               (1.3.6.1.4.1.232)
--      cpqScsi Group                  (1.3.6.1.4.1.232.5)
--       cpqScsiComponent Group        (1.3.6.1.4.1.232.5.2)
--        cpqScsiInterface Group       (1.3.6.1.4.1.232.5.2.1)
--         cpqScsiOsNetWare Group      (1.3.6.1.4.1.232.5.2.1.1)
--          cpqScsiVolMapTable         (1.3.6.1.4.1.232.5.2.1.1.7)
--
-- ****************************************************************************

    cpqScsiVolMapTable OBJECT-TYPE
        SYNTAX  SEQUENCE OF CpqScsiVolMapEntry
        ACCESS  not-accessible
        STATUS  deprecated
        DESCRIPTION
           "SCSI Drive Volume Map Table."
        ::= { cpqScsiOsNetWare 7 }

    cpqScsiVolMapEntry OBJECT-TYPE
        SYNTAX  CpqScsiVolMapEntry
        ACCESS  not-accessible
        STATUS  deprecated
        DESCRIPTION
           "SCSI Drive Volume Map Table Entry."
        INDEX   { cpqScsiNw3xVolCntlrIndex, cpqScsiNw3xVolBusIndex,
                 cpqScsiNw3xVolLogDrvIndex }
        ::= { cpqScsiVolMapTable 1 }

        CpqScsiVolMapEntry ::= SEQUENCE
        {
              cpqScsiNw3xVolCntlrIndex   INTEGER,
              cpqScsiNw3xVolBusIndex     INTEGER,
              cpqScsiNw3xVolLogDrvIndex  INTEGER,
              cpqScsiNw3xVolMap          OCTET STRING
        }

    cpqScsiNw3xVolCntlrIndex OBJECT-TYPE
        SYNTAX  INTEGER (0..225)
        ACCESS  read-only
        STATUS  deprecated
        DESCRIPTION
           "SCSI Cntlr Index.

            The controller index indicates to which SCSI adapter instance
            this table entry belongs.  The controller index is the physical
            slot in the computer system where the adapter is located."
        ::= { cpqScsiVolMapEntry 1 }

    cpqScsiNw3xVolBusIndex OBJECT-TYPE
        SYNTAX  INTEGER (0..225)
        ACCESS  read-only
        STATUS  deprecated
        DESCRIPTION
           "SCSI Bus Index.

            The bus index indicates to which SCSI bus instance on an
            adapter this table entry belongs.  The instances start
            at one and increment for each SCSI bus on a card."
        ::= { cpqScsiVolMapEntry 2 }

    cpqScsiNw3xVolLogDrvIndex OBJECT-TYPE
        SYNTAX  INTEGER (0..225)
        ACCESS  read-only
        STATUS  deprecated
        DESCRIPTION
           "SCSI Logical Drive Index.

            The logical drive index indicates to which logical drive
            instance on a SCSI bus this table entry belongs.  The logical
            drive index starts at one and increments for each logical
            drive on the SCSI bus."
        ::= { cpqScsiVolMapEntry 3 }

    cpqScsiNw3xVolMap OBJECT-TYPE
        SYNTAX  OCTET STRING (SIZE (0..255))
        ACCESS  read-only
        STATUS  deprecated
        DESCRIPTION
           "SCSI Drive Volume Map.

            This is a data structure containing the volume mappings for this
            logical drive.  There are 8 entries in a NetWare volume mapping.
            An entry can be null indicating no mapping exists.
            Each entry has the following format.

               BYTE    Name[16]
               BYTE    Segment"
        ::= { cpqScsiVolMapEntry 4 }

-- ****************************************************************************
--    SCSI OS Common
--    ==============
--
-- The compaq enterprise               (1.3.6.1.4.1.232)
--      cpqScsi Group                  (1.3.6.1.4.1.232.5)
--       cpqScsiComponent Group        (1.3.6.1.4.1.232.5.2)
--        cpqScsiInterface Group       (1.3.6.1.4.1.232.5.2.1)
--         cpqScsiOsCommon Group       (1.3.6.1.4.1.232.5.2.1.4)
--
--
--  The cpqScsiOsCommon group describes the SCSI common OS interface.
--  This information describes the interface modules general OS interface
--  architectural information.
--
--  Implementation of the cpqScsiOsCommon group is mandatory for all
--  agents that support the SCSI MIB.
--
-- ****************************************************************************

    cpqScsiOsCommonPollFreq OBJECT-TYPE
        SYNTAX  INTEGER (0..65535)
        ACCESS  read-write
        STATUS  mandatory
        DESCRIPTION
            "The agent's polling frequency.

             The frequency, in seconds, at which the agent requests
             information from the device driver.  A frequency of zero
             indicates that the agent retrieves the information upon
             request of a management station, it does not poll the device
             driver at a specific interval.

             If the poll frequency is zero (0) all attempts to write to this
             object will fail.  If the poll frequency is non-zero,
             setting this value will change the polling frequency of the
             agent.  Setting the poll frequency to zero will always
             fail, an agent may also choose to fail any request to change
             the poll frequency to a value that would severely impact system
             performance."
           ::= { cpqScsiOsCommon 1 }

-- ****************************************************************************
--    SCSI OS Common Module
--    =====================
--
-- The compaq enterprise               (1.3.6.1.4.1.232)
--      cpqScsi Group                  (1.3.6.1.4.1.232.5)
--       cpqScsiComponent Group        (1.3.6.1.4.1.232.5.2)
--        cpqScsiInterface Group       (1.3.6.1.4.1.232.5.2.1)
--         cpqScsiOsCommon Group       (1.3.6.1.4.1.232.5.2.1.4)
--          cpqScsiOsCommonModuleTable (1.3.6.1.4.1.232.5.2.1.4.2) deprecated
--
-- ****************************************************************************

    cpqScsiOsCommonModuleTable OBJECT-TYPE
        SYNTAX  SEQUENCE OF CpqScsiOsCommonModuleEntry
        ACCESS  not-accessible
        STATUS  deprecated
        DESCRIPTION
            "A table of software modules that provide an interface to the
             device this MIB describes."
        ::= { cpqScsiOsCommon 2 }

    cpqScsiOsCommonModuleEntry OBJECT-TYPE
        SYNTAX  CpqScsiOsCommonModuleEntry
        ACCESS  not-accessible
        STATUS  deprecated
        DESCRIPTION
            "A description of a software modules that provide an interface
             to the device this MIB describes."
        INDEX   { cpqScsiOsCommonModuleIndex }
        ::= { cpqScsiOsCommonModuleTable 1 }

        CpqScsiOsCommonModuleEntry ::= SEQUENCE {
            cpqScsiOsCommonModuleIndex       INTEGER,
            cpqScsiOsCommonModuleName        DisplayString,
            cpqScsiOsCommonModuleVersion     DisplayString,
            cpqScsiOsCommonModuleDate        OCTET STRING,
            cpqScsiOsCommonModulePurpose     DisplayString
        }

    cpqScsiOsCommonModuleIndex OBJECT-TYPE
        SYNTAX  INTEGER (0..255)
        ACCESS  read-only
        STATUS  deprecated
        DESCRIPTION
            "A unique index for this module description."
        ::= { cpqScsiOsCommonModuleEntry 1 }

    cpqScsiOsCommonModuleName OBJECT-TYPE
        SYNTAX  DisplayString (SIZE (0..255))
        ACCESS  read-only
        STATUS  deprecated
        DESCRIPTION
            "The module name."
        ::= { cpqScsiOsCommonModuleEntry 2 }

    cpqScsiOsCommonModuleVersion OBJECT-TYPE
        SYNTAX  DisplayString (SIZE (0..5))
        ACCESS  read-only
        STATUS  deprecated
        DESCRIPTION
            "The module version in XX.YY format.

            Where XX is the major version number and YY is the minor version
            number.  This field will be a null (size 0) string if the agent
            cannot provide the module version."
        ::= { cpqScsiOsCommonModuleEntry 3 }

    cpqScsiOsCommonModuleDate OBJECT-TYPE
        SYNTAX  OCTET STRING (SIZE (7))
        ACCESS  read-only
        STATUS  deprecated
        DESCRIPTION
            "The module date.

             field  octets  contents                  range
             =====  ======  =======                  =====
               1      1-2   year                      0..65536
               2       3    month                     1..12
               3       4    day                       1..31
               4       5    hour                      0..23
               5       6    minute                    0..59
               6       7    second                    0..60
                            (use 60 for leap-second)


            This field will be set to year = 0 if the agent cannot provide
            the module date.  The hour, minute, and second field will be set
            to zero (0) if they are not relevant.  The year field is set
            with the most significant octect first."
        ::= { cpqScsiOsCommonModuleEntry 4 }

    cpqScsiOsCommonModulePurpose OBJECT-TYPE
        SYNTAX  DisplayString (SIZE (0..255))
        ACCESS  read-only
        STATUS  deprecated
        DESCRIPTION
            "The purpose of the module described in this entry."
        ::= { cpqScsiOsCommonModuleEntry 5 }

-- ****************************************************************************
--    SCSI Controller Group
--    ====================
--
-- The compaq enterprise               (1.3.6.1.4.1.232)
--      cpqScsi Group                  (1.3.6.1.4.1.232.5)
--       cpqScsiComponent Group        (1.3.6.1.4.1.232.5.2)
--        cpqScsiCntlr Group           (1.3.6.1.4.1.232.5.2.2)
--         cpqScsiCntlrTable           (1.3.6.1.4.1.232.5.2.2.1)
--
--
--  The Cntlr group contains the configuration and statistical information
--  of the SCSI controller.
--
--  Implementation of the Cntlr group is mandatory for all agents that
--  support the SCSI MIB.
--
-- ****************************************************************************


    cpqScsiCntlrTable OBJECT-TYPE
        SYNTAX  SEQUENCE OF CpqScsiCntlrEntry
        ACCESS  not-accessible
        STATUS  mandatory
        DESCRIPTION
           "SCSI Controller Table."
        ::= { cpqScsiCntlr 1 }

    cpqScsiCntlrEntry OBJECT-TYPE
        SYNTAX  CpqScsiCntlrEntry
        ACCESS  not-accessible
        STATUS  mandatory
        DESCRIPTION
           "SCSI Controller Table Entry."
        INDEX   { cpqScsiCntlrIndex, cpqScsiCntlrBusIndex }
        ::= { cpqScsiCntlrTable 1 }

        CpqScsiCntlrEntry ::= SEQUENCE
        {
              cpqScsiCntlrIndex          INTEGER,
              cpqScsiCntlrBusIndex       INTEGER,
              cpqScsiCntlrModel          INTEGER,
              cpqScsiCntlrFWVers         DisplayString,
              cpqScsiCntlrSWVers         DisplayString,
              cpqScsiCntlrSlot           INTEGER,
              cpqScsiCntlrStatus         INTEGER,
              cpqScsiCntlrHardResets     Counter,
              cpqScsiCntlrSoftResets     Counter,
              cpqScsiCntlrTimeouts       Counter,
              cpqScsiCntlrBaseIOAddr     INTEGER,
              cpqScsiCntlrCondition      INTEGER,
              cpqScsiCntlrSerialNum      DisplayString,
              cpqScsiCntlrBusWidth       INTEGER,
              cpqScsiCntlrModelExtended  DisplayString,
              cpqScsiCntlrHwLocation     DisplayString
        }

    cpqScsiCntlrIndex OBJECT-TYPE
        SYNTAX  INTEGER
        ACCESS  read-only
        STATUS  mandatory
        DESCRIPTION
           "SCSI Controller Index.

            The controller index indicates to which SCSI adapter instance
            this table entry belongs.  The controller index is the physical
            slot in the computer system where the adapter is located."
        ::= { cpqScsiCntlrEntry 1 }

    cpqScsiCntlrBusIndex OBJECT-TYPE
        SYNTAX  INTEGER (0..255)
        ACCESS  read-only
        STATUS  mandatory
        DESCRIPTION
           "SCSI Bus Index.

            The bus index indicates to which SCSI bus instance on an
            adapter this table entry belongs.  The instances start
            at one and increment for each SCSI bus on a card."
        ::= { cpqScsiCntlrEntry 2 }

    cpqScsiCntlrModel OBJECT-TYPE
        SYNTAX  INTEGER
        {
           other(1),
           cpqs710(2),
           cpqs94(3),
           cpqs810p(4),
           cpqs825e(5),
           cpqs825p(6),
           cpqs974p(7),
           cpqs875p(8),
           extended(9),
           cpqs895p(10),
           cpqs896p(11),
           cpqa789x(12),
           cpqs876t(13),
           hpu320(14),
           hpu320r(15),
           generic(16),
           hp1u320g2(17),
           hp1u320g1(18),
           hpSc11Xe(19)
        }
        ACCESS  read-only
        STATUS  mandatory
        DESCRIPTION
           "SCSI Controller Model.

            The is the controller's model and can be used for identification
            purposes.  The following values are defined:

            other(1)    The management agent does not recognize this model.
                        You may need to upgrade your software.

            cpqs710(2)  Compaq 32-Bit Fast SCSI-2 Controller.

            cpqs94(3)   Compaq Systempro/XL Integrated SCSI-2 Options Port.

            cpqs810p(4) Integrated Fast-SCSI-2 Controller/P.

            cpqs825e(5) Compaq 32-Bit Fast-Wide SCSI-2 /E Controller.

            cpqs825p(6) Compaq 32-Bit Fast-Wide SCSI-2 /P Controller.

            cpqs974p(7) Deskpro XL Integrated PCI SCSI-2 Controller.

            cpqs875p(8) Compaq Wide-Ultra SCSI Controller.

            extended(9) SCSI Controllers described by
                        cpqScsiCntlrModelExtended.

            cpqs895p(10) Compaq Wide Ultra2 SCSI Controller.

            cpqs896p(11) Compaq 64-Bit Dual Channel Wide Ultra2 SCSI
                         Controller.

            cpqa789x(12) Compaq Wide Ultra3 SCSI Adapter.

            cpqs876t(13) Compaq StorageWorks Library Adapter.

            hpu320(14)   HP 64-Bit/133MHz PCI-X 2CH Ultra320 HBA.

            hpu320r(15)  HP PCI-X Dual Channel Ultra320 SCSI Adapter.

            generic(16)  SCSI HBA.

            hp1u320g2(17) HP Single Channel Ultra320 SCSI HBA G2.

            hp1u320g1(18) HP Single Channel Ultra320 SCSI HBA.

            hpSc11Xe(19)  HP SC11Xe Host Bus Adapter."

        ::= { cpqScsiCntlrEntry 3 }

    cpqScsiCntlrFWVers OBJECT-TYPE
        SYNTAX  DisplayString
        ACCESS  read-only
        STATUS  mandatory
        DESCRIPTION
           "SCSI Controller Firmware Version.

            This is the version of the firmware on the SCSI controller.
            If the SCSI controller does not use firmware then this string
            will be of length zero (0).  Some SCSI bus controllers are
            script driven and use the computer system's microprocessor
            thus not needing firmware."
        ::= { cpqScsiCntlrEntry 4 }

    cpqScsiCntlrSWVers OBJECT-TYPE
        SYNTAX  DisplayString (SIZE (0..5))
        ACCESS  read-only
        STATUS  deprecated
        DESCRIPTION
           "SCSI Controller Software Version.

            This is the version of any software upgrade which is being used
            in place of the firmware with the controller.  If the SCSI
            controller has not been upgraded via software or does not have
            firmware then this string will be of length zero (0).
            Some SCSI bus controllers are script driven and use the
            computer system's microprocessor thus not needing firmware."
        ::= { cpqScsiCntlrEntry 5 }

    cpqScsiCntlrSlot OBJECT-TYPE
        SYNTAX  INTEGER (0..255)
        ACCESS  read-only
        STATUS  mandatory
        DESCRIPTION
           "SCSI Controller Slot.

            This is the physical slot in which this controller is
            installed.  This information can be used for identification
            purposes."
        ::= { cpqScsiCntlrEntry 6 }

    cpqScsiCntlrStatus OBJECT-TYPE
        SYNTAX  INTEGER
        {
           other(1),
           ok(2),
           failed(3)
        }
        ACCESS  read-only
        STATUS  mandatory
        DESCRIPTION
           "SCSI Controller Status.

            This is the current status of the controller. The following
            values are currently defined:

            other(1)
              The controller is not operational due to reasons other than
              hardware failure.  The controller may be intentionally disabled.
              The controller configuration may be in conflict with the
              configuration of other hardware or software in the system.
              The controller may have failed initialization.  Corrective
              action is Operating System dependent.  Check for diagnostic
              messages which may have occurred at system boot time.

            ok(2)
              The controller is operating normally.

            failed(3)
              The controller has failed and is no longer operating.
              Please run diagnostics on the computer system to help
              identify the problem."
        ::= { cpqScsiCntlrEntry 7 }

    cpqScsiCntlrHardResets OBJECT-TYPE
        SYNTAX  Counter
        ACCESS  read-only
        STATUS  mandatory
        DESCRIPTION
           "SCSI Controller Hard Resets.

            This is the number of times the SCSI Hardware Interface driver
            detected that the SCSI bus has been reset since the driver
            was loaded.

            Hard resets may occasionally occur due to device errors.
            If this value should rise dramatically, you may have a problem.
            Check the SCSI bus statistics for unusually high error counts.
            If there is a device with a large number of bus errors, it may be
            failing and should be replaced."
        ::= { cpqScsiCntlrEntry 8 }

    cpqScsiCntlrSoftResets OBJECT-TYPE
        SYNTAX  Counter
        ACCESS  read-only
        STATUS  mandatory
        DESCRIPTION
           "SCSI Controller Soft Resets.

            This is the number of times the SCSI Hardware Interface driver
            has issued a reset command to all devices on a SCSI bus since
            the driver was loaded.

            Soft resets occur when the device driver is initializing the SCSI
            bus for operation and when device errors have left the bus in an
           ambiguous state.  If this value should rise dramatically, you may
           have a problem.  Check the SCSI bus statistics for unusually high
           error counts.  If there is a device with a large number of bus
           errors, it may be failing and should be and should be replaced."
       ::= { cpqScsiCntlrEntry 9 }

    cpqScsiCntlrTimeouts OBJECT-TYPE
        SYNTAX  Counter
        ACCESS  read-only
        STATUS  mandatory
        DESCRIPTION
           "SCSI Controller Time-outs.

            This is the number of times, since the driver was loaded, that
            the SCSI Hardware Interface driver issued a SCSI command but
            did not receive a reply within a specified amount of time.

            Timeouts may occasionally occur when a device fails to process a
            request because the SCSI bus was busy.  If this value should rise
            dramatically, you may have a problem.  Check if you have any
            non-disk SCSI devices, like tape drives, on the SCSI bus with
            the drives.  Sometimes a non-disk device can hold the SCSI bus
            for long periods of time causing time-outs."
        ::= { cpqScsiCntlrEntry 10 }

    cpqScsiCntlrBaseIOAddr OBJECT-TYPE
        SYNTAX  INTEGER
        ACCESS  read-only
        STATUS  mandatory
        DESCRIPTION
           "SCSI Controller Base I/O Address.

            This is the I/O address that the SCSI Hardware Interface driver
            uses to communicate with the SCSI bus controller.  This value
            can be used for identification purposes."
       ::= { cpqScsiCntlrEntry 11 }

    cpqScsiCntlrCondition OBJECT-TYPE
        SYNTAX  INTEGER
        {
           other(1),
           ok(2),
           degraded(3),
           failed(4)
        }
        ACCESS  read-only
        STATUS  mandatory
        DESCRIPTION
           "SCSI Controller Condition.

            This is the overall condition of the controller and all of the
            logical drives and physical drives controlled by it.
            The following values are defined:

            other(1)
              The management agent does not recognize the status as one of
              those listed below.

            ok(2)
              The controller and all of its logical drives and physical
              drives are operating normally.  No user action is required.

            degraded(3)
              One or more of the controller's logical drives or physical
              drives is degraded.  You need to check the status of all
              logical drives and physical drives.

            failed(4)
               The controller status is failed.  The drives on this
               controller are inaccessible.  Please refer to the controller
               status field for further information."
       ::= { cpqScsiCntlrEntry 12 }

    cpqScsiCntlrSerialNum OBJECT-TYPE
        SYNTAX  DisplayString (SIZE (0..16))
        ACCESS  read-only
        STATUS  mandatory
        DESCRIPTION
           "SCSI Controller Serial Number.

            This is the serial number assigned to the controller.  This can
            be used for identification purposes.  This field will be a null
            (size 0) string if the management agent cannot provide the
            serial number."
        ::= { cpqScsiCntlrEntry 13 }

    cpqScsiCntlrBusWidth OBJECT-TYPE
        SYNTAX  INTEGER
        {
           other(1),
           narrow(2),
           wide16(3)
        }
        ACCESS  read-only
        STATUS  mandatory
        DESCRIPTION
           "SCSI Controller Data Bus Width.

            This is the physical width of the controller's SCSI data bus.

            other(1)
              The management agent does not recognize this width.  You may
              need to upgrade your software.

            narrow(2)
              The SCSI controller supports an 8-bit narrow SCSI data bus.

            wide16(3)
              The SCSI controller supports a 16-bit wide SCSI data bus."
        ::= { cpqScsiCntlrEntry 14 }

    cpqScsiCntlrModelExtended OBJECT-TYPE
        SYNTAX  DisplayString (SIZE (0..80))
        ACCESS  read-only
        STATUS  mandatory
        DESCRIPTION
           "SCSI Controller Model Name.

            This is the model name for SCSI controllers not defined by
            cpqScsiCntlrModel enumerations. This field will be a null (size 0)
            string if the management agent cannot provide the SCSI Controller
            description."
        ::= { cpqScsiCntlrEntry 15  }

    cpqScsiCntlrHwLocation OBJECT-TYPE
        SYNTAX  DisplayString (SIZE (0..255))
        ACCESS  read-only
        STATUS  optional
        DESCRIPTION
            "A text description of the hardware location, on complex
             multi SBB hardware only, for the SCSI controller.
             A NULL string indicates that the hardware location could not
             be determined or is irrelevant."
        ::= { cpqScsiCntlrEntry 16  }


-- ****************************************************************************
--    SCSI Logical Drive Group
--    ========================
--
-- The compaq enterprise               (1.3.6.1.4.1.232)
--      cpqScsi Group                  (1.3.6.1.4.1.232.5)
--       cpqScsiComponent Group        (1.3.6.1.4.1.232.5.2)
--        cpqScsiLogDrv Group          (1.3.6.1.4.1.232.5.2.3)
--         cpqScsiLogDrvTable          (1.3.6.1.4.1.232.5.2.3.1)
--
--
--  The LogDrv group contains configuration and statistical information
--  about the logical drives associated with SCSI controllers.
--
--  Implementation of the LogDrv group is optional for agents that
--  support the SCSI MIB.
--
-- ****************************************************************************

    cpqScsiLogDrvTable OBJECT-TYPE
        SYNTAX  SEQUENCE OF CpqScsiLogDrvEntry
        ACCESS  not-accessible
        STATUS  mandatory
        DESCRIPTION
           "SCSI Logical Drive Table."
        ::= { cpqScsiLogDrv 1 }

    cpqScsiLogDrvEntry OBJECT-TYPE
        SYNTAX  CpqScsiLogDrvEntry
        ACCESS  not-accessible
        STATUS  mandatory
        DESCRIPTION
           "SCSI Logical Drive Entry."
        INDEX   { cpqScsiLogDrvCntlrIndex, cpqScsiLogDrvBusIndex,
                  cpqScsiLogDrvIndex }
        ::= { cpqScsiLogDrvTable 1 }

        CpqScsiLogDrvEntry ::= SEQUENCE
        {
              cpqScsiLogDrvCntlrIndex        INTEGER,
              cpqScsiLogDrvBusIndex          INTEGER,
              cpqScsiLogDrvIndex             INTEGER,
              cpqScsiLogDrvFaultTol          INTEGER,
              cpqScsiLogDrvStatus            INTEGER,
              cpqScsiLogDrvSize              INTEGER,
              cpqScsiLogDrvPhyDrvIDs         OCTET STRING,
              cpqScsiLogDrvCondition         INTEGER,
              cpqScsiLogDrvStripeSize        INTEGER,
              cpqScsiLogDrvAvailSpares       OCTET STRING,
              cpqScsiLogDrvPercentRebuild    Gauge,
              cpqScsiLogDrvOsName            DisplayString
        }

    cpqScsiLogDrvCntlrIndex OBJECT-TYPE
        SYNTAX  INTEGER
        ACCESS  read-only
        STATUS  mandatory
        DESCRIPTION
           "SCSI Logical Drive Controller Index.

            The controller index indicates to which SCSI adapter instance
            this table entry belongs."
        ::= { cpqScsiLogDrvEntry 1 }

    cpqScsiLogDrvBusIndex OBJECT-TYPE
        SYNTAX  INTEGER (0..255)
        ACCESS  read-only
        STATUS  mandatory
        DESCRIPTION
           "SCSI Logical Drive Bus Index.

            The bus index indicates to which SCSI bus instance on an
            adapter this table entry belongs."
        ::= { cpqScsiLogDrvEntry 2 }

    cpqScsiLogDrvIndex OBJECT-TYPE
        SYNTAX  INTEGER (0..255)
        ACCESS  read-only
        STATUS  mandatory
        DESCRIPTION
           "SCSI Logical Drive Index.

            The logical drive index indicates to which logical drive instance
            on a SCSI bus this table entry belongs."
        ::= { cpqScsiLogDrvEntry 3 }

    cpqScsiLogDrvFaultTol OBJECT-TYPE
        SYNTAX  INTEGER
        {
           other(1),
           none(2),
           mirroring(3),
           dataGuard(4),
           distribDataGuard(5),
           enhancedMirroring(6)
        }
        ACCESS  read-only
        STATUS  mandatory
        DESCRIPTION
           "SCSI Logical Drive Fault Tolerance.

            This shows the fault tolerance mode of the logical drive.

            The following values are valid for the Logical Drive
            Fault Tolerance:

            other(1)
              The management agent does not recognize the status.
              You may need to upgrade your software.

            none(2)
              Fault tolerance is not enabled. If a physical drive reports an
              error, the data cannot be recovered. This is known as RAID 0.

            mirroring(3)
              For each physical drive, there is a second physical drive
              containing identical data.  If a drive fails, the data can be
              retrieved from the mirror drive.

            dataGuard(4)
              One of the physical drives is used as a data guard drive and
              contains the exclusive OR of the data on the remaining drives.
              If a failure is detected, the data is rebuilt using the data
              guard information plus information from the other drives.

            distribDataGuard(5)
              Distributed Data Guarding, sometimes referred to as RAID 5, is
              similar to Data Guarding, but instead of storing the parity
              information on one drive, the information is distributed across
              all of the drives.  If a failure is detected, the data is
              rebuilt using the data guard information from all the drives.

            enhancedMirroring(6)
              This is used when there are more than 2 physical disks. Each
              'mirrored stripe' is written to a disk and is mirrored to an
              'adjacent' disk. This is commonly referred to as RAID 1E.
              If a failure is detected, the data is rebuilt using the data
              from the mirrored stripes on the other drives."
        ::= { cpqScsiLogDrvEntry 4 }

    cpqScsiLogDrvStatus OBJECT-TYPE
        SYNTAX  INTEGER
        {
           other(1),
           ok(2),
           failed(3),
           unconfigured(4),
           recovering(5),
           readyForRebuild(6),
           rebuilding(7),
           wrongDrive(8),
           badConnect(9),
           degraded(10),
           disabled(11)
        }
        ACCESS  read-only
        STATUS  mandatory
        DESCRIPTION
           "SCSI Logical Drive Status.

            The logical drive can be in one of the following states:

            other(1)
              The management agent does not recognize the status.
              You may need to upgrade your software.

            ok(2)
              Indicates that the logical drive is in normal operation mode.
              No user action is required.

            failed(3)
              Indicates that more physical drives have failed than the fault
              tolerance mode of the logical drive can handle without data loss.

            unconfigured(4)
              Indicates that the logical drive is not configured.  Insure all
              of the drive switches are properly set and run the configuration
              utility.

            recovering(5)
              Indicates that the logical drive is using Interim Recovery Mode.
              In Interim Recovery Mode, at least one physical drive has
              failed, but the logical drive's fault tolerance mode lets the
              logical drive continue to operate with no data loss.
              You should replace the failed drive as soon as possible.

            readyRebuild(6)
              Indicates that the logical drive is ready for Automatic Data
              Recovery.  The physical drive that failed has been replaced,
              but the logical drive is still operating in Interim Recovery
              Mode.

            rebuilding(7)
              Indicates that the logical drive is currently resynchronizing
              the data accross the physical drives in the logical drive.

            wrongDrive(8)
              Indicates that the wrong physical drive was replaced after a
              physical drive failure.  You need to return the drive
              incorrectly replaced and replace the failed drive.

            badConnect(9)
              Indicates that a physical drive is not responding.  Check the
              cables connected to it.

            degraded(10)
              Indicates that the logical drive is in a degraded state.

            disabled(11)
              Indicates that the logical drive is disabled. The logical drive
              configuration utility can enable or disable the logical drive.
              You should enable the logical drive using the configuration
              utility."
        ::= { cpqScsiLogDrvEntry 5 }

    cpqScsiLogDrvSize OBJECT-TYPE
        SYNTAX  INTEGER (0..2147483647)
        ACCESS  read-only
        STATUS  mandatory
        DESCRIPTION
           "SCSI Logical Drive Size.

            This is the size of the logical drive in megabytes.
            This value is calculated using the value 1,048,576 (2^20) as
            a megabyte.  Drive manufacturers sometimes use the
            number 1,000,000 as a megabyte when giving drive capacities
            so this value may differ from the advertised size of a drive."
        ::= { cpqScsiLogDrvEntry 6 }

    cpqScsiLogDrvPhyDrvIDs OBJECT-TYPE
        SYNTAX  OCTET STRING (SIZE (0..255))
        ACCESS  read-only
        STATUS  mandatory
        DESCRIPTION
           "SCSI Logical Drive Physical Drive IDs.

            This lists the physical drive SCSI ID's which are associated
            with this logical drive.  These are the same IDs which can be
            used as indices into the physical drive table.  Each byte of
            the string is an index."
        ::= { cpqScsiLogDrvEntry 7 }

    cpqScsiLogDrvCondition OBJECT-TYPE
        SYNTAX  INTEGER
        {
           other(1),
           ok(2),
           degraded(3),
           failed(4)
        }
        ACCESS  read-only
        STATUS  mandatory
        DESCRIPTION
           "SCSI Logical Drive Condition.

            This is the overall condition of the logical drive and all of the
            physical drives which comprise it.
            The following values are defined:

            other(1)
              The management agent does not recognize the status.  You may
              need to upgrade your software.

            ok(2)
              The logical drive and all of its physical drives are operating
              normally.  No user action is required.

            degraded(3)
              Either the logical drive is degraded or one or more of its
              physical drives is degraded.  You need to check the status
              of the logical drive and of all its physical drives.

            failed(4)
              Either the logical drive has failed or one or more of its
              physical drives has failed.  You need to check the status
              of the logical drive and of all its physical drives."
       ::= { cpqScsiLogDrvEntry 8 }

    cpqScsiLogDrvStripeSize OBJECT-TYPE
        SYNTAX  INTEGER
        ACCESS  read-only
        STATUS  mandatory
        DESCRIPTION
            "Logical Drive Stripe Size.

            This is the size of a logical drive stripe in kilobytes."
        ::= { cpqScsiLogDrvEntry 9 }

     cpqScsiLogDrvAvailSpares OBJECT-TYPE
        SYNTAX  OCTET STRING (SIZE (0..255))
        ACCESS  read-only
        STATUS  mandatory
        DESCRIPTION
            "SCSI Logical Drive Available Spares.

            This indicates if this logical drive has one or more spares
            designated for it that are not currently in use by another drive.
            Each octet present will be a physical drive ID that is an
            available spare for this logical drive.  These are the same ID's
            which can be used as indexes into the physical drive table.
            An octet string of length zero indicates that there are no
            available spares for this logical drive."
        ::= { cpqScsiLogDrvEntry 10 }

     cpqScsiLogDrvPercentRebuild OBJECT-TYPE
        SYNTAX  Gauge
        ACCESS  read-only
        STATUS  mandatory
        DESCRIPTION
            "Logical Drive Percent Rebuild.

            After a failed physical drive has been replaced, the physical
            drive must have its data rebuilt.  This value is the percent
            complete of the rebuild.  When the value reaches 100, the
            rebuilding process is complete.  The drive array continues to
            operate in interim recovery mode while a drive is rebuilding.

            This value is only valid if the Logical Drive Status is
            rebuilding(7).

            If the value cannot be determined or a rebuild is not active,
            the value is set to 0."
        ::= { cpqScsiLogDrvEntry 11 }

     cpqScsiLogDrvOsName OBJECT-TYPE
        SYNTAX  DisplayString (SIZE (0..255))
        ACCESS  read-only
        STATUS  mandatory
        DESCRIPTION
            "Logical Drive OS Name.

            The OS name for this array logical drive.  This field will be
            a null (size 0) string if the agent does not support OS name."
        ::= { cpqScsiLogDrvEntry 12 }

-- ****************************************************************************
--    SCSI Physical Drive Group
--    =========================
--
-- The compaq enterprise               (1.3.6.1.4.1.232)
--      cpqScsi Group                  (1.3.6.1.4.1.232.5)
--       cpqScsiComponent Group        (1.3.6.1.4.1.232.5.2)
--        cpqScsiPhyDrv Group          (1.3.6.1.4.1.232.5.2.4)
--         cpqScsiPhyDrvTable          (1.3.6.1.4.1.232.5.2.4.1)
--
--  The PhyDrv group contains configuration and statistical information
--  about the physical drives associated with SCSI controllers.
--
--  Implementation of the PhyDrv group is mandatory for all agents that
--  support the SCSI MIB.
--
-- ****************************************************************************

    cpqScsiPhyDrvTable OBJECT-TYPE
        SYNTAX  SEQUENCE OF CpqScsiPhyDrvEntry
        ACCESS  not-accessible
        STATUS  mandatory
        DESCRIPTION
           "SCSI Physical Drive Table."
        ::= { cpqScsiPhyDrv 1 }

    cpqScsiPhyDrvEntry OBJECT-TYPE
        SYNTAX  CpqScsiPhyDrvEntry
        ACCESS  not-accessible
        STATUS  mandatory
        DESCRIPTION
           "SCSI Physical Drive Entry."
        INDEX   { cpqScsiPhyDrvCntlrIndex, cpqScsiPhyDrvBusIndex,
                  cpqScsiPhyDrvIndex }
        ::= { cpqScsiPhyDrvTable 1 }

        CpqScsiPhyDrvEntry ::= SEQUENCE
        {
              cpqScsiPhyDrvCntlrIndex            INTEGER,
              cpqScsiPhyDrvBusIndex              INTEGER,
              cpqScsiPhyDrvIndex                 INTEGER,
              cpqScsiPhyDrvModel                 DisplayString,
              cpqScsiPhyDrvFWRev                 DisplayString,
              cpqScsiPhyDrvVendor                DisplayString,
              cpqScsiPhyDrvSize                  INTEGER,
              cpqScsiPhyDrvScsiID                INTEGER,
              cpqScsiPhyDrvStatus                INTEGER,
              cpqScsiPhyDrvServiceHours          Counter,
              cpqScsiPhyDrvHighReadSectors       Counter,
              cpqScsiPhyDrvLowReadSectors        Counter,
              cpqScsiPhyDrvHighWriteSectors      Counter,
              cpqScsiPhyDrvLowWriteSectors       Counter,
              cpqScsiPhyDrvHardReadErrs          Counter,
              cpqScsiPhyDrvHardWriteErrs         Counter,
              cpqScsiPhyDrvEccCorrReads          Counter,
              cpqScsiPhyDrvRecvReadErrs          Counter,
              cpqScsiPhyDrvRecvWriteErrs         Counter,
              cpqScsiPhyDrvSeekErrs              Counter,
              cpqScsiPhyDrvSpinupTime            INTEGER,
              cpqScsiPhyDrvUsedReallocs          Counter,
              cpqScsiPhyDrvTimeouts              Counter,
              cpqScsiPhyDrvPostErrs              Counter,
              cpqScsiPhyDrvPostErrCode           INTEGER,
              cpqScsiPhyDrvCondition             INTEGER,
              cpqScsiPhyDrvFuncTest1             Gauge,
              cpqScsiPhyDrvFuncTest2             Gauge,
              cpqScsiPhyDrvStatsPreserved        INTEGER,
              cpqScsiPhyDrvSerialNum             DisplayString,
              cpqScsiPhyDrvLocation              INTEGER,
              cpqScsiPhyDrvParent                INTEGER,
              cpqScsiPhyDrvSectorSize            INTEGER,
              cpqScsiPhyDrvHotPlug               INTEGER,
              cpqScsiPhyDrvPlacement             INTEGER,
              cpqScsiPhyDrvPreFailMonitoring     INTEGER,
              cpqScsiPhyDrvOsName                DisplayString,
              cpqScsiPhyDrvRotationalSpeed       INTEGER,
              cpqScsiPhyDrvMemberLogDrv          INTEGER
        }

    cpqScsiPhyDrvCntlrIndex OBJECT-TYPE
        SYNTAX  INTEGER
        ACCESS  read-only
        STATUS  mandatory
        DESCRIPTION
           "SCSI Physical Drive Controller Index.

            The controller index indicates to which SCSI adapter instance
            this table entry belongs.  The controller index is the physical
            slot in the computer where the adapter is located."
        ::= { cpqScsiPhyDrvEntry 1 }

    cpqScsiPhyDrvBusIndex OBJECT-TYPE
        SYNTAX  INTEGER (0..255)
        ACCESS  read-only
        STATUS  mandatory
        DESCRIPTION
           "SCSI Physical Drive Bus Index.

            The bus index indicates to which SCSI bus instance on an
            adapter this table entry belongs.  The instances start
            at one and increment for each SCSI bus on a card."
        ::= { cpqScsiPhyDrvEntry 2 }

    cpqScsiPhyDrvIndex OBJECT-TYPE
        SYNTAX  INTEGER (0..255)
        ACCESS  read-only
        STATUS  mandatory
        DESCRIPTION
           "SCSI Physical Drive Index.

            The physical drive index indicates to which physical drive
            instance on a SCSI bus this table entry belongs.  The physical
            drive index is the SCSI ID being used by that drive."
        ::= { cpqScsiPhyDrvEntry 3 }

    cpqScsiPhyDrvModel OBJECT-TYPE
        SYNTAX  DisplayString (SIZE (0..17))
        ACCESS  read-only
        STATUS  mandatory
        DESCRIPTION
           "SCSI Physical Drive Model.

            This is a description of the physical drive's model as returned
            by the SCSI inquiry command.  This can be used for identification
           purposes."
        ::= { cpqScsiPhyDrvEntry 4 }

    cpqScsiPhyDrvFWRev OBJECT-TYPE
        SYNTAX  DisplayString (SIZE (0..8))
        ACCESS  read-only
        STATUS  mandatory
        DESCRIPTION
           "SCSI Physical Drive Firmware Revision.

            This is the revision level of the physical drive as returned by
            the SCSI inquiry command.  This can be used for identification
            purposes."
        ::= { cpqScsiPhyDrvEntry 5 }

    cpqScsiPhyDrvVendor OBJECT-TYPE
        SYNTAX  DisplayString (SIZE (0..9))
        ACCESS  read-only
        STATUS  mandatory
        DESCRIPTION
           "SCSI Physical Drive Vendor.

            This is the physical drive vendor's name as returned by
            the SCSI inquiry command.  This can be used for identification
            purposes."
        ::= { cpqScsiPhyDrvEntry 6 }

    cpqScsiPhyDrvSize OBJECT-TYPE
        SYNTAX  INTEGER (0..2147483647)
        ACCESS  read-only
        STATUS  mandatory
        DESCRIPTION
           "SCSI Physical Drive Size in MB.

            This is the size of the physical drive in megabytes.
            This value is calculated using the value 1,048,576 (2^20) as
            a megabyte.  Drive manufacturers sometimes use the number
            1,000,000 as a megabyte when giving drive capacities so this
            value may differ from the advertised size of a drive."
        ::= { cpqScsiPhyDrvEntry 7 }

    cpqScsiPhyDrvScsiID OBJECT-TYPE
        SYNTAX  INTEGER (0..255)
        ACCESS  read-only
        STATUS  mandatory
        DESCRIPTION
           "SCSI Physical Drive SCSI ID.

            This is the SCSI ID used by the physical drive.  SCSI ID's
            identify a physical drive on a bus so the controller can
            communicate with it."
        ::= { cpqScsiPhyDrvEntry 8 }

    cpqScsiPhyDrvStatus OBJECT-TYPE
        SYNTAX  INTEGER
        {
           other(1),
           ok(2),
           failed(3),
           notConfigured(4),
           badCable(5),
           missingWasOk(6),
           missingWasFailed(7),
           predictiveFailure(8),
           missingWasPredictiveFailure(9),
           offline(10),
           missingWasOffline(11),
           hardError(12)
        }
        ACCESS  read-only
        STATUS  mandatory
        DESCRIPTION
           "SCSI Physical Drive Status.

            The physical drive can be in one of the following states:

            other(1)
              The drive is in a state other than one of those listed
              below.

            ok(2)
              Indicates that the physical drive is in normal operation mode.
              No user action is necessary.

            failed(3)
              Indicates that the physical drive has failed and can no longer
              return data.  When convenient, you should bring down the server
              and run diagnostics to help identify the problem.
              The drive may need to be replaced.

            notConfigured(4)
              Indicates that the physical drive is not configured.  You
              need to insure all of the drive's switches are properly set
              and that the configuration utility has been run.

            badCable(5)
              Indicates that a physical drive is not responding.
              You should check the cables connected to it.  You can bring
              down the server and run diagnostics to help identify
              the problem.

            missingWasOk(6)
              Indicates that a physical drive had a status of OK and is no
              longer present.  The drive has been removed.

            missingWasFailed(7)
              Indicates that a physical drive had a status of FAILED and is
              no longer present.  The drive has been removed.

            predictiveFailure(8)
              Indicates that the physical drive has exceeded a threshold
              value for one of it's predictive indicators. When convenient,
              you should bring down the server and run diagnostics to
              help identify the problem. The drive may need to be replaced.

            missingWasPredictiveFailure(9)
              Indicates that a physical drive had a status of PREDICTIVE
              FAILURE and is no longer present.  The drive has been removed.

            offline(10)
              Indicates that the physical drive is offline and can no longer
              return data.  No further status is available.

            missingWasOffline(11)
              Indicates that a physical drive had a status of OFFLINE
              and is no longer present.  The drive has been removed.

            hardError(12)
              Indicates that a hard error occurred for this physical drive."
       ::= { cpqScsiPhyDrvEntry 9 }

    cpqScsiPhyDrvServiceHours OBJECT-TYPE
        SYNTAX  Counter
        ACCESS  read-only
        STATUS  mandatory
        DESCRIPTION
           "SCSI Physical Drive Service Time in hours.

            This shows the total number of hours that a physical drive has
            been operating under the device driver.  You can use the service
            time to calculate rates for other physical drive objects."
        ::= { cpqScsiPhyDrvEntry 10 }

    cpqScsiPhyDrvHighReadSectors OBJECT-TYPE
        SYNTAX  Counter
        ACCESS  read-only
        STATUS  mandatory
        DESCRIPTION
           "SCSI Physical Drive Sectors Read (high).

            The phyDrvHighReadSectors and the phyDrvlowReadSectors together
            show the total number of sectors read from the physical disk
            drive during the service time (phyDrvServiceHours).

            The actual number of sectors read equals the phyDrvHighReadSectors
            times 2^32 plus the phyDrvLowReadSectors.

            This information may be useful for determining rates.
            For example, if you want to calculate the average number of
            reads per hour of operation, divide this number by the service
            time."
        ::= { cpqScsiPhyDrvEntry 11 }

    cpqScsiPhyDrvLowReadSectors OBJECT-TYPE
        SYNTAX  Counter
        ACCESS  read-only
        STATUS  mandatory
        DESCRIPTION
           "SCSI Physical Drive Sectors Read (low).

            The phyDrvHighReadSectors and the phyDrvlowReadSectors together
            show the total number of sectors read from the physical disk
            drive during the service time (phyDrvServiceHours).

            The actual number of sectors read equals the phyDrvHighReadSectors
            times 2^32 plus the phyDrvLowReadSectors.

            This information may be useful for determining rates.
            For example, if you want to calculate the average number of reads
            per hour of operation, divide this number by the service time."
        ::= { cpqScsiPhyDrvEntry 12 }

    cpqScsiPhyDrvHighWriteSectors OBJECT-TYPE
        SYNTAX  Counter
        ACCESS  read-only
        STATUS  mandatory
        DESCRIPTION
           "SCSI Physical Drive Sectors Written (high).

            The phyDrvHighWriteSectors and the phyDrvlowWriteSectors together
            show the total number of sectors written to the physical disk
            drive during the service time (phyDrvServiceHours).

            The actual number of sectors read equals the phyDrvHighWriteSectors
            times 2^32 plus the phyDrvLowWriteSectors.

           This information may be useful for determining rates.
           For example, if you want to calculate the average number of
           writes per hour of operation, divide this number by the service
           time."
        ::= { cpqScsiPhyDrvEntry 13 }

    cpqScsiPhyDrvLowWriteSectors OBJECT-TYPE
        SYNTAX  Counter
        ACCESS  read-only
        STATUS  mandatory
        DESCRIPTION
           "SCSI Physical Drive Sectors Written (low).

            The phyDrvHighWriteSectors and the phyDrvlowWriteSectors together
            show the total number of sectors written to the physical disk
            drive during the service time (phyDrvServiceHours).

            The actual number of sectors read equals the phyDrvHighWriteSectors
            times 2^32 plus the phyDrvLowWriteSectors.

            This information may be useful for determining rates.
            For example, if you want to calculate the average number of
            writes per hour of operation, divide this number by the service
            time."
        ::= { cpqScsiPhyDrvEntry 14 }

    cpqScsiPhyDrvHardReadErrs OBJECT-TYPE
        SYNTAX  Counter
        ACCESS  read-only
        STATUS  mandatory
        DESCRIPTION
           "SCSI Physical Drive Hard Read Errors.

            This is the number of read errors that have occurred on a drive
            that could not be recovered by a physical drive's Error Correction
            Code (ECC) algorithm, retries or any other recovery mechanisms
            during the service time (phyDrvServiceHours).

            If you see any hard read errors there may be a problem.
            This is often caused by bad media sections on the drive.  If the
            error count continues to rise you may need to replace the drive."
        ::= { cpqScsiPhyDrvEntry 15 }

    cpqScsiPhyDrvHardWriteErrs OBJECT-TYPE
        SYNTAX  Counter
        ACCESS  read-only
        STATUS  mandatory
        DESCRIPTION
           "SCSI Physical Drive Hard Write Errors.

            This is the number of write errors that have occurred on a drive
            that could not be recovered by retries or any other recovery
            mechanisms during the service time (phyDrvServiceHours).

            If you see any hard write errors there may be a problem.
            This is often caused by bad media sections on the drive.  If the
            error count continues to rise you may need to replace the drive."
        ::= { cpqScsiPhyDrvEntry 16 }

    cpqScsiPhyDrvEccCorrReads OBJECT-TYPE
        SYNTAX  Counter
        ACCESS  read-only
        STATUS  mandatory
        DESCRIPTION
           "SCSI Physical Drive ECC Corrected Read Errors (high).

            This is the number of read requests that the drive had to use
            an Error Correction Code (ECC) algorithm on to recover data
            during the service time (phyDrvServiceHours).

            ECC corrected reads will occasionally occur over time.  Having a
            large number of ECC corrected errors does not necessarily indicate
            that the drive is failing.  However, you may wish to replace a
            drive with an abnormally high amount in comparison to other
            similar drives as a precaution."
        ::= { cpqScsiPhyDrvEntry 17 }

    cpqScsiPhyDrvRecvReadErrs OBJECT-TYPE
        SYNTAX  Counter
        ACCESS  read-only
        STATUS  mandatory
        DESCRIPTION
           "SCSI Physical Drive Recovered Read Errors.

            This is the number of read requests that the drive had to use
            retries or other recovery mechanisms on to recover data during
            the service time (phyDrvServiceHours).

            Retry corrected reads will occasionally occur over time.
            Having a large number of retry corrected errors does not
            necessarily indicate that the drive is failing.  However, you
            may wish to replace a drive with an abnormally high amount in
            comparison to other similiar drives as a precaution."
        ::= { cpqScsiPhyDrvEntry 18 }

    cpqScsiPhyDrvRecvWriteErrs OBJECT-TYPE
        SYNTAX  Counter
        ACCESS  read-only
        STATUS  mandatory
        DESCRIPTION
           "SCSI Physical Drive Recovered Write Errors.

            This is the number of write requests that the drive had to use
            retries or other recovery mechanisms on to recover data during
            the service time (phyDrvServiceHours).

            Retry corrected writes will occasionally occur over time.
            Having a large number of retry corrected errors does not
            necessarily indicate that the drive is failing.  However, you
            may wish to replace a drive with an abnormally high amount in
            comparison to other similiar drives as a precaution."
        ::= { cpqScsiPhyDrvEntry 19 }

    cpqScsiPhyDrvSeekErrs OBJECT-TYPE
        SYNTAX  Counter
        ACCESS  read-only
        STATUS  mandatory
        DESCRIPTION
           "SCSI Physical Drive Seek Errors.

            This is the number of times a drive head seek failed during the
            service time (phyDrvServiceHours).

            Seek errors will occasionally occur over time.  Having a
            large number of seek errors does not necessarily indicate
            that the drive is failing.  However, you may wish to replace
            a drive with an abnormally high amount in comparison to other
            similiar drives as a precaution."
        ::= { cpqScsiPhyDrvEntry 20 }

    cpqScsiPhyDrvSpinupTime OBJECT-TYPE
        SYNTAX  INTEGER
        ACCESS  read-only
        STATUS  mandatory
        DESCRIPTION
           "SCSI Physical Drive Spin up Time (tenths of seconds).

            This is the time it takes for a physical drive to spin up to full
            speed.

            Disks require time to gain momentum and reach operating speed.
            As cars are tested to go from 0 mph to 60 mph in x number of
            seconds, drive manufacturers have preset expectations for the
            time it takes the drive to spin to full speed.  Drives that do
            not meet these expectations may have problems.

            If the drive is having problems spinning up, this value will
            increase over time.  Eventually, the drive may fail to spin up
            altogether.  If you see a large increase in this value over
            time, you may want to replace the drive as a precaution."
        ::= { cpqScsiPhyDrvEntry 21 }

    cpqScsiPhyDrvUsedReallocs OBJECT-TYPE
        SYNTAX  Counter
        ACCESS  read-only
        STATUS  mandatory
        DESCRIPTION
           "SCSI Physical Drive Used Reallocation Sectors.

            This shows the number of sectors of the reallocation area that
            have been used by the physical drive over the life of the drive.

            Because of the nature of magnetic disks, certain sectors on a
            drive may have media defects. The reallocation area is part of
            the disk drive that the drive manufacturer sets aside to
            compensate for these defects. The drive writes information
            addressed from these unusable sectors to available sectors in
            the reallocation area.

            If all of the reserved sectors have been used, then there is
            no way for the drive to remap bad sectors and the drive will
            start failing.  Unfortunately, the number of reallocation
            sectors originally reserved for this purpose is drive specific
            and you must contact the drive vendor for these values.

            If the current value starts to approach the maximum reserved you
            may wish to replace the drive before it fails."
        ::= { cpqScsiPhyDrvEntry 22 }

    cpqScsiPhyDrvTimeouts OBJECT-TYPE
        SYNTAX  Counter
        ACCESS  read-only
        STATUS  mandatory
        DESCRIPTION
           "SCSI Physical Drive Time-out Errors.

            This is the number of times the drive failed to complete a request
            within a specified amount of time during the service time
            (phyDrvServiceHours).

            Time-outs may occasionally occur when a device fails to process a
            request because the SCSI bus was busy.  If this value should rise
            dramatically, you may have a problem.  Check if you have any
            non-disk SCSI devices, like tape drives, on the SCSI bus with
            the drives.  Sometimes a non-disk device can hold onto the SCSI
            bus for long periods of time causing time-outs."
        ::= { cpqScsiPhyDrvEntry 23 }

    cpqScsiPhyDrvPostErrs OBJECT-TYPE
        SYNTAX  Counter
        ACCESS  read-only
        STATUS  mandatory
        DESCRIPTION
           "SCSI Physical Drive Power On Self Test (POST) Errors.

            This is the number of times that a drive failed its self test
            during the service time (phyDrvServiceHours).  The drive does
            a self test each time power is applied to the system.

            If you see any self test errors there may be a problem.
            You can run diagnostics to help identify the problem."
        ::= { cpqScsiPhyDrvEntry 24 }

    cpqScsiPhyDrvPostErrCode OBJECT-TYPE
        SYNTAX  INTEGER
        ACCESS  read-only
        STATUS  mandatory
        DESCRIPTION
           "SCSI Physical Drive Last POST Error Code.

            This is the result of the last SCSI command which caused a self
            test to fail.  The value is split into three fields.  The first
            byte is the SCSI Sense Qualifier.  The second byte is the
            SCSI Sense Code.  The third byte is the SCSI Sense Key.  You
            will need to refer to a SCSI-2 specification for the valid values
            of these fields."
        ::= { cpqScsiPhyDrvEntry 25 }

    cpqScsiPhyDrvCondition OBJECT-TYPE
        SYNTAX  INTEGER
        {
           other(1),
           ok(2),
           degraded(3),
           failed(4)
        }
        ACCESS  read-only
        STATUS  mandatory
        DESCRIPTION
           "SCSI Physical Drive Condition.

            This is the overall condition of the physical drive.
            The following values are defined:

            other(1)
              The agent does not recognize the status.  You may need
              to upgrade your software.

            ok(2)
              The physical drive is operating normally.  No user action
              is required.

            degraded(3)
              The physical drive is degraded.  You need to check the status
              of all logical drives and physical drives.

            failed(4)
              The physical drives has failed.  When convenient, you
              should bring down the server and run diagnostics
              to help identify the problem."
       ::= { cpqScsiPhyDrvEntry 26 }

    cpqScsiPhyDrvFuncTest1 OBJECT-TYPE
        SYNTAX  Gauge
        ACCESS  read-only
        STATUS  mandatory
        DESCRIPTION
           "SCSI Physical Drive Functional Test 1.

            This is a percentage value that represents the operating
            efficiency of a drive.  The functional test issues a series of
            SCSI commands and times the results.  When the drive has the
            test run for the very first time (service time is zero), the
            results are saved as the baseline value.  Then, whenever the
            test is executed the current result is compared to the baseline
            result and expressed as a percent.

            If the percentage result should drop rapidly there may be a
            problem with the drive.  You may wish to replace the drive as a
            precaution."
        ::= { cpqScsiPhyDrvEntry 27 }

    cpqScsiPhyDrvFuncTest2 OBJECT-TYPE
        SYNTAX  Gauge
        ACCESS  read-only
        STATUS  mandatory
        DESCRIPTION
           "SCSI Physical Drive Functional Test 2.

            This is a percentage value that represents the operating
            efficiency of a drive.  The functional test issues a series of
            SCSI commands and times the results.  When the drive has the
            test run for the very first time (service time is zero), the
            results are saved as the baseline value.  Then, whenever the
            test is executed the current result is compared to the baseline
            result and expressed as a percent.

            If the percentage result should drop rapidly there may be a
            problem with the drive.  You may wish to replace the drive as a
            precaution."
        ::= { cpqScsiPhyDrvEntry 28 }

    cpqScsiPhyDrvStatsPreserved OBJECT-TYPE
        SYNTAX  INTEGER
        {
           other(1),
           inNVRAM(2),
           onDisk(3),
           noCPUSupport(4),
           noFreeNVRAM(5),
           noDrvSupport(6),
           noSoftwareSupport(7),
           statsNotSupported(8)
        }
        ACCESS  read-only
        STATUS  mandatory
        DESCRIPTION
           "SCSI Physical Drive Statistics Preservation Method.

            This value indicates how all of the objects in this table
            are saved over a power cycle.  If the objects are not saved
            then all of their values will be reset whenever the device
            driver is unloaded.  The following values are defined:

            other(1)
              The agent does not recognize the status.  You may
              need to upgrade your software.

            inNVRAM(2)
              The objects are saved in non-volatile memory in the
              computer system.

            onDisk(3)
              The objects are saved on the physical drives in reserved
              sectors.

            noCPUSupport(4)
              The objects are not saved across power cycles because
              the hardware does not support this operation.

            noFreeNVRAM(5)
              The objects are not saved across power cycles because
              all of the available non-volatile memory is in use.

            noDrvSupport(6)
              The objects are not saved across power cycles because
              the physical drive does not contain a unique identifier to
              save it under.

            noSoftwareSupport(7)
              The objects are not saved across power cycles because
              either the device driver or computer system firmware do not
              provide support.

            statsNotSupported(8)
              Drive statistics are not supported."
        ::= { cpqScsiPhyDrvEntry 29 }

    cpqScsiPhyDrvSerialNum OBJECT-TYPE
        SYNTAX  DisplayString (SIZE (0..40))
        ACCESS  read-only
        STATUS  mandatory
        DESCRIPTION
           "SCSI Physical Drive Serial Number.

            This is the serial number assigned to the physical drive.
            This value is based upon the serial number as returned by the
            SCSI inquiry command but may have been modified due to space
            limitations.  This can be used for identification purposes."
        ::= { cpqScsiPhyDrvEntry 30 }

    cpqScsiPhyDrvLocation OBJECT-TYPE
        SYNTAX  INTEGER
        {
           other(1),
           proliant(2)
        }
        ACCESS  read-only
        STATUS  deprecated
        DESCRIPTION
           "SCSI Physical Drive Location.

            This is the physical location of where the drive is located.  The
            following values are defined:

            other(1)
              The drives are not located in any special product that
              identifies the location.

            proliant(2)
              The drives are located in the ProLiant Storage System."

        ::= { cpqScsiPhyDrvEntry 31 }

    cpqScsiPhyDrvParent OBJECT-TYPE
        SYNTAX  INTEGER (0..255)
        ACCESS  read-only
        STATUS  mandatory
        DESCRIPTION
           "SCSI Physical Drive Parent.

            This is the logical drive index to which this physical
            drive belongs."
       ::= { cpqScsiPhyDrvEntry 32 }

    cpqScsiPhyDrvSectorSize OBJECT-TYPE
        SYNTAX  INTEGER (0..2147483647)
        ACCESS  read-only
        STATUS  mandatory
        DESCRIPTION
           "SCSI Physical Drive Sector Size in Bytes.

            This allows one to convert counters that are reported in sectors
            to bytes."
        ::= { cpqScsiPhyDrvEntry 33 }

    cpqScsiPhyDrvHotPlug OBJECT-TYPE
        SYNTAX  INTEGER
        {
           other(1),
           hotPlug(2),
           nonHotPlug(3)
        }
        ACCESS  read-only
        STATUS  mandatory
        DESCRIPTION
           "SCSI Physical Drive Hot Plug Support Status.

            The following values are defined:

            other(1)
              The agent is unable to determine if this drive
              supports hot plug replacement.

            hotPlug(2)
              The drive supports hot plug replacement.

            nonhotPlug(3)
              The drive does not support hot plug replacement."
        ::= { cpqScsiPhyDrvEntry 34 }

    cpqScsiPhyDrvPlacement OBJECT-TYPE
        SYNTAX  INTEGER
        {
           other(1),
           internal(2),
           external(3)
        }
        ACCESS  read-only
        STATUS  mandatory
        DESCRIPTION
           "SCSI Physical Drive Placement.

            The following values are defined:

            other(1)
              The agent is unable to determine if the drive is internal or
              external to the system chassis.

            internal(2)
              The drive is located in an internal Proliant system chassis.

            external(3)
              The drive is located in an external Proliant storage system."
        ::= { cpqScsiPhyDrvEntry 35 }

    cpqScsiPhyDrvPreFailMonitoring OBJECT-TYPE
        SYNTAX  INTEGER
        {
           other(1),
           notAvailable(2),
           available(3)
        }
        ACCESS  read-only
        STATUS  mandatory
        DESCRIPTION
           "SCSI Physical Drive Predictive Failure Monitoring.

            The following values are defined:

            other(1)
              The agent is unable to determine if the drive supports
              predictive failure monitoring.

            notAvailable(2)
              This drive does not support predictive failure monitoring.

            available(3)
              This drive supports predictive failure monitoring."
        ::= { cpqScsiPhyDrvEntry 36 }

     cpqScsiPhyDrvOsName OBJECT-TYPE
        SYNTAX  DisplayString (SIZE (0..255))
        ACCESS  read-only
        STATUS  mandatory
        DESCRIPTION
            "Physical Drive OS Name.

            The OS name for this SCSI physical drive.  This field will be
            a null (size 0) string if the agent does not support OS name."
        ::= { cpqScsiPhyDrvEntry 37 }

    cpqScsiPhyDrvRotationalSpeed OBJECT-TYPE
       SYNTAX  INTEGER
       {
           other(1),
           rpm7200(2),
           rpm10K(3),
           rpm15K(4)
       }
       ACCESS  read-only
       STATUS  mandatory
       DESCRIPTION
           "SCSI Physical Drive Rotational Speed.

           The following values are defined:

           other(1)
             The agent is unable to determine the rotational speed for
             this drive.

           rpm7200(2)
             The rotational speed for this drive is 7200 rpm.

           rpm10K(3)
             The rotational speed for this drive is 10000 rpm.

           rpm15K(4)
             The rotational speed for this drive is 15000 rpm."
       ::= { cpqScsiPhyDrvEntry 38 }

    cpqScsiPhyDrvMemberLogDrv OBJECT-TYPE
        SYNTAX  INTEGER
        {
                other(1),
                member(2),
                spare(3),
                nonMember(4)
        }
        ACCESS  read-only
        STATUS  mandatory
        DESCRIPTION
            "The Physical Drive is a Member of a Logical Drive.

             This is an indication of whether the physical drive is
             a member of a SCSI logical drive.

             This variable can be in one of the following states:

             other(1)
              The agent is unable to determine if the physical drive is a
              member of a logical drive.

             member(2)
              The physical drive is a member of a logical drive.

             spare(2)
              The physical drive is a spare drive for a logical drive.

             nonMember(4)
              The physical drive is not a logical drive member or spare."
        ::= { cpqScsiPhyDrvEntry 39 }

-- ****************************************************************************
--    SCSI Target Group
--    =================
--
-- The compaq enterprise               (1.3.6.1.4.1.232)
--      cpqScsi Group                  (1.3.6.1.4.1.232.5)
--       cpqScsiComponent Group        (1.3.6.1.4.1.232.5.2)
--        cpqScsiTarget Group          (1.3.6.1.4.1.232.5.2.5)
--         cpqScsiTargetTable          (1.3.6.1.4.1.232.5.2.5.1)
--
--  The SCSI target group describes the generic SCSI bus information about
--  the SCSI bus targets (devices) in the system.
--
--  Implementation of the SCSI target group is mandatory for all agents
--  supporting the SCSI MIB.
--
-- ****************************************************************************

    cpqScsiTargetTable OBJECT-TYPE
        SYNTAX  SEQUENCE OF CpqScsiTargetEntry
        ACCESS  not-accessible
        STATUS  mandatory
        DESCRIPTION
           "SCSI Target Table."
        ::= { cpqScsiTarget 1 }

    cpqScsiTargetEntry OBJECT-TYPE
        SYNTAX  CpqScsiTargetEntry
        ACCESS  not-accessible
        STATUS  mandatory
        DESCRIPTION
           "SCSI Target Entry."
        INDEX   { cpqScsiTargetCntlrIndex, cpqScsiTargetBusIndex,
                 cpqScsiTargetScsiIdIndex }
        ::= { cpqScsiTargetTable 1 }

        CpqScsiTargetEntry ::= SEQUENCE
        {
             cpqScsiTargetCntlrIndex         INTEGER,
             cpqScsiTargetBusIndex           INTEGER,
             cpqScsiTargetScsiIdIndex        INTEGER,
             cpqScsiTargetType               INTEGER,
             cpqScsiTargetModel              DisplayString,
             cpqScsiTargetFWRev              DisplayString,
             cpqScsiTargetVendor             DisplayString,
             cpqScsiTargetParityErrs         Counter,
             cpqScsiTargetPhaseErrs          Counter,
             cpqScsiTargetSelectTimeouts     Counter,
             cpqScsiTargetMsgRejects         Counter,
             cpqScsiTargetNegPeriod          INTEGER,
             cpqScsiTargetLocation           INTEGER,
             cpqScsiTargetNegSpeed           INTEGER,
             cpqScsiTargetPhysWidth          INTEGER,
             cpqScsiTargetNegWidth           INTEGER,
             cpqScsiTargetTypeExtended       INTEGER,
             cpqScsiTargetCurrentSpeed       INTEGER
        }

    cpqScsiTargetCntlrIndex OBJECT-TYPE
        SYNTAX  INTEGER
        ACCESS  read-only
        STATUS  mandatory
        DESCRIPTION
           "SCSI Target Controller Index.

            The controller index indicates to which SCSI adapter instance
            this table entry belongs.  The controller index is the physical
            slot in the computer system where the adapter is located."
        ::= { cpqScsiTargetEntry 1 }

    cpqScsiTargetBusIndex OBJECT-TYPE
        SYNTAX  INTEGER (0..255)
        ACCESS  read-only
        STATUS  mandatory
        DESCRIPTION
           "SCSI Target Bus Index.

            The bus index indicates to which SCSI bus instance on an
            adapter card this table entry belongs.  The instances start
            at one and increment for each SCSI bus on a card."
        ::= { cpqScsiTargetEntry 2 }

    cpqScsiTargetScsiIdIndex OBJECT-TYPE
        SYNTAX  INTEGER (0..255)
        ACCESS  read-only
        STATUS  mandatory
        DESCRIPTION
           "SCSI Target Device Index.

            The device index indicates to which device instance on a
            SCSI bus this table entry belongs.  The device index
            is the SCSI ID being used by that device."
        ::= { cpqScsiTargetEntry 3 }

    cpqScsiTargetType OBJECT-TYPE
        SYNTAX  INTEGER
        {
           other(1),
           disk(2),
           tape(3),
           printer(4),
           processor(5),
           wormDrive(6),
           cd-rom(7),
           scanner(8),
           optical(9),
           jukeBox(10),
           commDev(11)
        }
        ACCESS  read-only
        STATUS  mandatory
        DESCRIPTION
           "SCSI Device Type.

            This is the type of SCSI device.  The following types are defined:

            other(1)
              The agent does not recognize this type.
              You may need to upgrade your software.

            disk(2)
              This is a direct-access device like a disk drive.

            tape(3)
              This is a sequential-access device like a tape drive.

            printer(4)
              This is a printer device.

            processor(5)
              This is a processor device like the ProLiant Storage System.

            worm(6)
              This is a write-once, read-many times device.

            cd-rom(7)
              This is a CD or DVD device.

            scanner(8)
              This is a scanner device.

            optical(9)
              This is an optical memory device.

            jukeBox(10)
              This is a media changer device like a jukebox.

            commDev(11)
              This is a communications device like a LAN bridge."
        ::= { cpqScsiTargetEntry 4 }

    cpqScsiTargetModel OBJECT-TYPE
        SYNTAX  DisplayString (SIZE (0..17))
        ACCESS  read-only
        STATUS  mandatory
        DESCRIPTION
           "SCSI Device Model.

            This is a description of the device's model as returned by
            the SCSI inquiry command.  This can be used for identification
            purposes."
        ::= { cpqScsiTargetEntry 5 }

    cpqScsiTargetFWRev OBJECT-TYPE
        SYNTAX  DisplayString (SIZE (0..8))
        ACCESS  read-only
        STATUS  mandatory
        DESCRIPTION
           "SCSI Device Firmware Revision.

            This is the revision level of the device as returned by
            the SCSI inquiry command.  This can be used for identification
            purposes."
        ::= { cpqScsiTargetEntry 6 }

    cpqScsiTargetVendor OBJECT-TYPE
        SYNTAX  DisplayString (SIZE (0..9))
        ACCESS  read-only
        STATUS  mandatory
        DESCRIPTION
           "SCSI Device Vendor.

            This is the device vendor's name as returned by the SCSI
            inquiry command.  This can be used for identification purposes."
        ::= { cpqScsiTargetEntry 7 }

    cpqScsiTargetParityErrs OBJECT-TYPE
        SYNTAX  Counter
        ACCESS  read-only
        STATUS  mandatory
        DESCRIPTION
           "SCSI Device Bus Parity Errors.

            This is the number of parity errors seen on the SCSI bus while
            processing commands for this SCSI ID.  This value is maintained
            since the SCSI Hardware Interface driver was loaded.

            Parity errors may occasionally occur.  If this value should rise
            dramatically, you may have a problem.  Some common causes include
            radio frequency interference (RFI) on the bus cables, bad or
            missing terminating resisters on the drives or having more than
            one device with the same SCSI ID.  Insure the bus cable is free
            of obstructions and that the devices on the bus are properly
            configured."
        ::= { cpqScsiTargetEntry 8 }

    cpqScsiTargetPhaseErrs OBJECT-TYPE
        SYNTAX  Counter
        ACCESS  read-only
        STATUS  mandatory
        DESCRIPTION
           "SCSI Device Bus Phase Errors.

            This is the number of times the SCSI bus entered an invalid
            operating state while processing commands for the SCSI ID.
            This value is maintained since the SCSI Hardware Interface driver
            was loaded.

            If you see any phase errors you may have a problem.
            Phase errors can be caused by a device which is not operating
            correctly.  If the phase errors continue to increase the device
            should be replaced."
        ::= { cpqScsiTargetEntry 9 }

    cpqScsiTargetSelectTimeouts OBJECT-TYPE
        SYNTAX  Counter
        ACCESS  read-only
        STATUS  mandatory
        DESCRIPTION
           "SCSI Device Bus Select Time-outs.

            This is the number of times the controller attempted to start
            communications with a device by selecting it but the device did
            not respond.

            If you see any select time-outs you may have a problem.  The device
            may have hung during operations.  The SCSI controller will attempt
            to reset the device but if this value continues to increment you
            may need to power cycle the device."
        ::= { cpqScsiTargetEntry 10 }

    cpqScsiTargetMsgRejects OBJECT-TYPE
        SYNTAX  Counter
        ACCESS  read-only
        STATUS  mandatory
        DESCRIPTION
           "SCSI Device Bus Message Rejects.

            This is the number of times the device rejected a command because
            it did not support the specified operation since the SCSI Hardware
            Interface driver was loaded.

            A large number for this object does not indicate a problem.
            It only shows that the device does not support certain advanced
            SCSI commands that the device driver issued."
        ::= { cpqScsiTargetEntry 11 }

    cpqScsiTargetNegPeriod OBJECT-TYPE
        SYNTAX  INTEGER (0..2147483647)
        ACCESS  read-only
        STATUS  deprecated
        DESCRIPTION
           "SCSI Device Negotiated Period.

            This is the amount of time that was negotiated between the
            controller and the device as a synchronous transfer window.
            A synchronous transfer window is how long the device can
            transfer data without requiring an acknowledgment from the
            controller.  In general the larger the negotiated period is,
            the lower the device throughput.  This value is reported in
            quarters of nanoseconds."
        ::= { cpqScsiTargetEntry 12 }

    cpqScsiTargetLocation OBJECT-TYPE
        SYNTAX  INTEGER
        {
           other(1),
           proliant(2)
        }
        ACCESS  read-only
        STATUS  mandatory
        DESCRIPTION
           "SCSI Device Location.

            This is the physical location of where the device is located.
            The following values are defined:

            other(1)
              The device is not located in any special product that
              identifies the location.

            proliant(2)
              The device is located in the ProLiant Storage System."
        ::= { cpqScsiTargetEntry 13 }

    cpqScsiTargetNegSpeed OBJECT-TYPE
        SYNTAX  INTEGER
        ACCESS  read-only
        STATUS  mandatory
        DESCRIPTION
           "SCSI Device Negotiated Speed.

            This is the data transfer speed that was negotiated between
            the controller and the device.  This value is reported in bits
            per second."

        ::= { cpqScsiTargetEntry 14 }

    cpqScsiTargetPhysWidth OBJECT-TYPE
        SYNTAX  INTEGER
        {
           other(1),
           narrow(2),
           wide16(3)
        }
        ACCESS  read-only
        STATUS  mandatory
        DESCRIPTION
           "SCSI Device Data Bus Physical Width.

            This is the physical width of the device's SCSI data bus.

            other(1)
              The management agent does not recognize this width.  You may
              need to upgrade your software.

            narrow(2)
              The SCSI device supports an 8-bit narrow SCSI data bus.

            wide16(3)
              The SCSI device supports a 16-bit wide SCSI data bus."
        ::= { cpqScsiTargetEntry 15 }

    cpqScsiTargetNegWidth OBJECT-TYPE
        SYNTAX  INTEGER
        ACCESS  read-only
        STATUS  mandatory
        DESCRIPTION
           "SCSI Device Data Bus Negotiated Width.

            This is the width of the device's SCSI data bus that was
            negotiated between the controller and the device.  This value
            is reported in bits."
        ::= { cpqScsiTargetEntry 16 }

    cpqScsiTargetTypeExtended OBJECT-TYPE
        SYNTAX  INTEGER
        {
           other(1),
           pdcd(2),
           removableDisk(3),
           dltAutoloader(4),
           cdJukebox(5),
           cr3500(6),
           autoloader(7)
        }
        ACCESS  read-only
        STATUS  mandatory
        DESCRIPTION
           "SCSI Extended Device Type.

            This is additional information about the type of SCSI device.
            The following types are defined:

            other(1)
              This target does not have any extended type information.

            pdcd(2)
              This is a power-drive CD-ROM.

            removableDisk(3)
              This is a removable media disk device like a floppy drive.

            dltAutoloader(4)
              This is a tape library device.

            cdJukebox(5)
              This is a CD storage system device.

            cr3500(6)
              This is a CR3500 RAID SCSI controller.

            autoloader(7)
              This is an autoloader medium changer device."

        ::= { cpqScsiTargetEntry 17 }

    cpqScsiTargetCurrentSpeed OBJECT-TYPE
        SYNTAX  INTEGER
        {
           other(1),
           asynchronous(2),
           fast(3),
           ultra(4),
           ultra2(5),
           ultra3(6),
           scsi1(7),
           ultra4(8)
        }
        ACCESS  read-only
        STATUS  mandatory
        DESCRIPTION
          "SCSI Device Current Data Transfer Speed.

           The following values are defined:

           other(1)
             The agent is unable to determine the current negotiated data
             transfer speed for this drive.

           asynchronous(2)
             The negotiated data transfer speed for this drive is
             asynchronous.

           fast(3)
             The negotiated data transfer speed for this drive is 10 million
             transfers per second.

           ultra(4)
             The negotiated data transfer speed for this drive is 20 million
             transfers per second.

           ultra2(5)
             The negotiated data transfer speed for this drive is 40 million
             transfers per second.

           ultra3(6)
             The negotiated data transfer speed for this drive is 80 million
             transfers per second.

           scsi1(7)
             The negotiated data transfer speed for this drive is 5 million
             transfers per second.

           ultra4(8)
             The negotiated data transfer speed for this drive is 160 million
             transfers per second. Ultra4 is now referred to as Ultra320."
       ::= { cpqScsiTargetEntry 18 }

-- ****************************************************************************
--    SCSI CD Group
--    =================
--
-- The compaq enterprise               (1.3.6.1.4.1.232)
--      cpqScsi Group                  (1.3.6.1.4.1.232.5)
--       cpqScsiComponent Group        (1.3.6.1.4.1.232.5.2)
--        cpqScsiCd Group              (1.3.6.1.4.1.232.5.2.6)
--         cpqScsiCdDrvTable           (1.3.6.1.4.1.232.5.2.6.1)
--
--  The SCSI CD group describes the CD storage jukebox associated with
--  SCSI controllers and the CD_ROM devices in the jukebox.
--
--  Implementation of the CD group is mandatory for all agents supporting
--  the SCSI MIB.
--
-- ****************************************************************************

   cpqScsiCdDrvTable OBJECT-TYPE
        SYNTAX  SEQUENCE OF CpqScsiCdDrvEntry
        ACCESS  not-accessible
        STATUS  mandatory
        DESCRIPTION
           "Scsi CD-ROM Drive Table."
        ::= { cpqScsiCd 1 }

    cpqScsiCdDrvEntry OBJECT-TYPE
        SYNTAX  CpqScsiCdDrvEntry
        ACCESS  not-accessible
        STATUS  mandatory
        DESCRIPTION
           "Scsi CD-ROM Drive Entry."
        INDEX   { cpqScsiCdDrvCntlrIndex, cpqScsiCdDrvBusIndex,
                  cpqScsiCdDrvScsiIdIndex, cpqScsiCdDrvLunIndex }
        ::= { cpqScsiCdDrvTable 1 }

        CpqScsiCdDrvEntry ::= SEQUENCE
        {
              cpqScsiCdDrvCntlrIndex            INTEGER,
              cpqScsiCdDrvBusIndex              INTEGER,
              cpqScsiCdDrvScsiIdIndex           INTEGER,
              cpqScsiCdDrvLunIndex              INTEGER,
              cpqScsiCdDrvModel                 DisplayString,
              cpqScsiCdDrvVendor                DisplayString,
              cpqScsiCdDrvFwRev                 DisplayString
        }

    cpqScsiCdDrvCntlrIndex OBJECT-TYPE
        SYNTAX  INTEGER
        ACCESS  read-only
        STATUS  mandatory
        DESCRIPTION
           "SCSI CD-ROM Drive Controller Index.

            The controller index indicates to which SCSI adapter instance
            this CD table entry belongs.  The controller index is the
            physical slot in the computer where the adapter is located."
        ::= { cpqScsiCdDrvEntry 1 }

    cpqScsiCdDrvBusIndex OBJECT-TYPE
        SYNTAX  INTEGER (0..255)
        ACCESS  read-only
        STATUS  mandatory
        DESCRIPTION
           "SCSI CD-ROM Drive Bus Index.

            The bus index indicates to which SCSI bus instance on an
            adapter this table entry belongs.  The instances start
            at one and increment for each SCSI bus on a card."
        ::= { cpqScsiCdDrvEntry 2 }

    cpqScsiCdDrvScsiIdIndex OBJECT-TYPE
        SYNTAX  INTEGER (0..255)
        ACCESS  read-only
        STATUS  mandatory
        DESCRIPTION
           "SCSI CD-ROM Drive Index.

            The CD-ROM drive index indicates to which CD-ROM drive
            instance on a SCSI bus this table entry belongs.  The physical
            drive index is the SCSI ID being used by that CD drive."
        ::= { cpqScsiCdDrvEntry 3 }

    cpqScsiCdDrvLunIndex OBJECT-TYPE
        SYNTAX  INTEGER (0..255)
        ACCESS  read-only
        STATUS  mandatory
        DESCRIPTION
           "SCSI CD-ROM Drive Logical Unit Index.

            The CD-ROM drive logical unit index indicates to which
            physical drive logical unit on a SCSI ID instance on a SCSI
            bus this table entry belongs.  The CD-ROM drive Lun index
            is the logical unit number being used by that CD drive."
        ::= { cpqScsiCdDrvEntry 4 }

    cpqScsiCdDrvModel OBJECT-TYPE
        SYNTAX  DisplayString (SIZE (0..17))
        ACCESS  read-only
        STATUS  mandatory
        DESCRIPTION
           "SCSI CD Device Model.

            This is a description of the device's model as returned by
            the SCSI inquiry command.  This can be used for identification
            purposes."
        ::= { cpqScsiCdDrvEntry 5 }

    cpqScsiCdDrvVendor OBJECT-TYPE
        SYNTAX  DisplayString (SIZE (0..9))
        ACCESS  read-only
        STATUS  mandatory
        DESCRIPTION
           "SCSI CD Drive Vendor.

            This is the CD drive vendor's name as returned by
            the SCSI inquiry command.  This can be used for identification
            purposes."
        ::= { cpqScsiCdDrvEntry 6 }

    cpqScsiCdDrvFwRev OBJECT-TYPE
        SYNTAX  DisplayString (SIZE (0..8))
        ACCESS  read-only
        STATUS  mandatory
        DESCRIPTION
            "SCSI CD-ROM Firmware Revision.

             This is used to differentiate the firmware versions
             which have the same CD-ROM drive vendor and model (as specified by
             cpqScsiCdVendor and cpqScsiCdModel). This can be retrieved by the
             SCSI inquiry command. "
        ::= { cpqScsiCdDrvEntry 7 }


-- ****************************************************************************
--    CD Library Table
--    ===================
--
-- The compaq enterprise               (1.3.6.1.4.1.232)
--      cpqScsi Group                  (1.3.6.1.4.1.232.5)
--       cpqScsiComponent Group        (1.3.6.1.4.1.232.5.2)
--        cpqScsiCd Group              (1.3.6.1.4.1.232.5.2.6)
--         cpqCdLibraryTable           (1.3.6.1.4.1.232.5.2.6.2)
--
--  The CD Library Table describes the information about CD storage jukebox
--  associated with Conpaq SCSI controllers.
--
--  Implementation of the CD Library is mandatory for all agents supporting
--  the SCSI MIB.
--
-- ****************************************************************************

    cpqCdLibraryTable OBJECT-TYPE
        SYNTAX  SEQUENCE OF CpqCdLibraryEntry
        ACCESS  not-accessible
        STATUS  mandatory
        DESCRIPTION
           "CD Library Table."
        ::= { cpqScsiCd 2 }

    cpqCdLibraryEntry OBJECT-TYPE
        SYNTAX  CpqCdLibraryEntry
        ACCESS  not-accessible
        STATUS  mandatory
        DESCRIPTION
           "CD Library Entry."
        INDEX   { cpqCdLibraryCntlrIndex, cpqCdLibraryBusIndex,
                 cpqCdLibraryScsiIdIndex, cpqCdLibraryLunIndex }
        ::= { cpqCdLibraryTable 1 }

        CpqCdLibraryEntry ::= SEQUENCE
        {
             cpqCdLibraryCntlrIndex         INTEGER,
             cpqCdLibraryBusIndex           INTEGER,
             cpqCdLibraryScsiIdIndex        INTEGER,
             cpqCdLibraryLunIndex           INTEGER,
             cpqCdLibraryCondition          INTEGER,
             cpqCdLibraryStatus             INTEGER,
             cpqCdLibraryModel              DisplayString,
             cpqCdLibraryVendor             DisplayString,
             cpqCdLibrarySerialNumber       DisplayString,
             cpqCdLibraryDriveList          OCTET STRING,
             cpqCdLibraryFwRev             DisplayString,
             cpqCdLibraryFwSubtype         INTEGER
        }

    cpqCdLibraryCntlrIndex OBJECT-TYPE
        SYNTAX  INTEGER
        ACCESS  read-only
        STATUS  mandatory
        DESCRIPTION
           "SCSI CD Library Controller Index.

            The controller index indicates to which SCSI adapter instance
            this table entry belongs.  The controller index is the physical
            slot in the computer system where the adapter is located."
        ::= { cpqCdLibraryEntry 1 }

    cpqCdLibraryBusIndex OBJECT-TYPE
        SYNTAX  INTEGER (0..255)
        ACCESS  read-only
        STATUS  mandatory
        DESCRIPTION
           "SCSI CD Library Bus Index.

            The bus index indicates to which SCSI bus instance on an
            adapter card this table entry belongs.  The instances start
            at one and increment for each SCSI bus on a card."
        ::= { cpqCdLibraryEntry 2 }

    cpqCdLibraryScsiIdIndex OBJECT-TYPE
        SYNTAX  INTEGER (0..255)
        ACCESS  read-only
        STATUS  mandatory
        DESCRIPTION
           "SCSI CD Library Device Index.

            The device index indicates to which device instance on a
            SCSI bus this table entry belongs.  The device index
            is the SCSI ID being used by that device."
        ::= { cpqCdLibraryEntry 3 }

    cpqCdLibraryLunIndex OBJECT-TYPE
        SYNTAX  INTEGER (0..255)
        ACCESS  read-only
        STATUS  mandatory
        DESCRIPTION
           "SCSI CD Library Logical Unit Index.

            The logical unit index indicates to which Lun device instance
            on a SCSI bus this table entry belongs.  The logical unit
            index is the Lun being used by that device."
        ::= { cpqCdLibraryEntry 4 }

    cpqCdLibraryCondition OBJECT-TYPE
        SYNTAX  INTEGER
        {
           other(1),
           ok(2),
           degraded(3),
           failed(4)
        }
        ACCESS  read-only
        STATUS  mandatory
        DESCRIPTION
           "CD Library Condition.

            This value represents the overall condition of this CD Library.

            The library can be in one of the following states:

            other(1)
              The library is in a state other than one of those listed
              below.

            ok(2)
              Indicates that the library is in normal operation mode.
              No user action is necessary.

            degraded(3)
              Indicates that the library has degraded in some manner.

            failed(4)
              Indicates that the library has failed and can no longer
              return data.  When convenient, you should bring down the server
              and run diagnostics to help identify the problem."
       ::= { cpqCdLibraryEntry 5 }

    cpqCdLibraryStatus OBJECT-TYPE
         SYNTAX  INTEGER
        {
           other(1),
           ok(2),
           failed(3),
           offline(4)
        }
        ACCESS  read-only
        STATUS  mandatory
        DESCRIPTION
           "CD Library Status.

            This value represents the status of this CD Library.

            The library can be in one of the following states:

            other(1)
              The library is in a state other than one of those listed
              below.

            ok(2)
              Indicates that the CD library fault light is in an 'ok' state.

            failed(3)
              Indicates that the CD library fault light is in a 'failed' state.
              The fault light is activated for hardware errors (Sense Code 04h)
              with additional Sense codes: 40h-4fh except the parity error.
              The LED will remain on until is powered cycled.

            offline(4)
              Indicates that the agents can no longer communicate with
              the CD library.  This could be caused by a cabling problem or the
              CD library may be powered off."

       ::= { cpqCdLibraryEntry 6 }

    cpqCdLibraryModel OBJECT-TYPE
        SYNTAX  DisplayString (SIZE (0..17))
        ACCESS  read-only
        STATUS  mandatory
        DESCRIPTION
           "SCSI CD Library Device Model.

            This is a description of the device's model as returned by
            the SCSI inquiry command.  This can be used for identification
            purposes."
        ::= { cpqCdLibraryEntry 7 }

    cpqCdLibraryVendor OBJECT-TYPE
        SYNTAX  DisplayString (SIZE (0..9))
        ACCESS  read-only
        STATUS  mandatory
        DESCRIPTION
           "SCSI CD Library Vendor.

            This is the CD Library drive vendor's name as returned by
            the SCSI inquiry command.  This can be used for identification
            purposes."
        ::= { cpqCdLibraryEntry 8 }

    cpqCdLibrarySerialNumber OBJECT-TYPE
        SYNTAX  DisplayString (SIZE (0..64))
        ACCESS  read-only
        STATUS  mandatory
        DESCRIPTION
            "CD Library Serial Number.

            This is the unit serial number for the library.  It
            can be used for identification purposes."
        ::= { cpqCdLibraryEntry 9 }

    cpqCdLibraryDriveList OBJECT-TYPE
        SYNTAX  OCTET STRING (SIZE (0..64))
        ACCESS  read-only
        STATUS  mandatory
        DESCRIPTION
           "CD Library Drive List

            This is a data structure containing the list of CD drive ids
            that are present in this library.  The format is:

              BYTE    Controller Number
              BYTE    Bus Number
              BYTE    SCSI ID
              BYTE    Logical Unit Number

            There will be 1 structure for each drive present in the library."

        ::= { cpqCdLibraryEntry 10 }

    cpqCdLibraryFwRev OBJECT-TYPE
        SYNTAX  DisplayString (SIZE (0..8))
        ACCESS  read-only
        STATUS  mandatory
        DESCRIPTION
            "SCSI CD Library Firmware Revision.

             This is used to differentiate the firmware versions
             which have the same CD library vendor and model (as specified in
             cpqCdLibraryVendor and cpqCdLibraryModel). This can be retrieved
             by the SCSI inquiry command. "
        ::= { cpqCdLibraryEntry 11}

    cpqCdLibraryFwSubtype OBJECT-TYPE
        SYNTAX  INTEGER (0..255)
        ACCESS  read-only
        STATUS  mandatory
        DESCRIPTION
            "SCSI CD library Firmware Subtype.

             This is used to differentiate the firmware versions
             which have the same vendor and model. CD library will contain
             a value of 1 for this variable when they first ship, and this value
             will be incremented if future versions are shipped which
             are not firmware compatible with the predecessor.  If the
             CD library does not support this capability, a value of 0
             will be returned."
        ::= { cpqCdLibraryEntry 12 }


-- ****************************************************************************
--    SCSI Trap Log
--    =============
--
-- The compaq enterprise               (1.3.6.1.4.1.232)
--      cpqScsi Group                  (1.3.6.1.4.1.232.5)
--       cpqScsiTrap                   (1.3.6.1.4.1.232.5.3)   (deprecated)
--
--  The trap group maintains information about the number of traps issued
--  from the scsiDrv enterprise.  The trap group also maintains a table of
--  the last several traps issued.  This table is intended to give a
--  management application some recent status information immediately upon
--  accessing the agent.
--
--  Implementation of the Trap group is optional for agents that support the
--  SCSI MIB.
--
-- ****************************************************************************

    cpqScsiTrapPkts OBJECT-TYPE
        SYNTAX  Counter
        ACCESS  read-only
        STATUS  deprecated
        DESCRIPTION
           "The total number of trap packets issued by the SCSI
            enterprise since the instrument agent was loaded."
        ::= { cpqScsiTrap 1 }

    cpqScsiTrapLogMaxSize OBJECT-TYPE
        SYNTAX  INTEGER (0..2147483647)
        ACCESS  read-only
        STATUS  deprecated
        DESCRIPTION
           "The maximum number of entries that will currently be kept in
            the trap log.  If the maximum size has been reached and a new
            trap occurs the oldest trap will be removed."
        ::= { cpqScsiTrap 2 }

-- ****************************************************************************
--    SCSI Trap Log
--    =============
--
-- The compaq enterprise               (1.3.6.1.4.1.232)
--      cpqScsi Group                  (1.3.6.1.4.1.232.5)
--       cpqScsiTrap                   (1.3.6.1.4.1.232.5.3)    (deprecated)
--        cpqScsiTrapLogTable          (1.3.6.1.4.1.232.5.3.3)  (deprecated)
--
-- ****************************************************************************

    cpqScsiTrapLogTable OBJECT-TYPE
        SYNTAX  SEQUENCE OF CpqScsiTrapLogEntry
        ACCESS  not-accessible
        STATUS  deprecated
        DESCRIPTION
           "An ordered list of trap log entries (conceptually a queue).
            The trap log entries will be kept in the order in which they were
            generated with the most recent trap at index 1 and the oldest
            trap entry at index trapLogMaxSize.  If the maximum number size
            has been reached and a new trap occurs the oldest trap will be
            removed when the new trap is added so the trapMaxLogSize is not
            exceeded."
        ::= { cpqScsiTrap 3 }

    cpqScsiTrapLogEntry OBJECT-TYPE
        SYNTAX  CpqScsiTrapLogEntry
        ACCESS  not-accessible
        STATUS  deprecated
        DESCRIPTION
           "A description of a trap event."
        INDEX   { cpqScsiTrapLogIndex }
        ::= { cpqScsiTrapLogTable 1 }

        CpqScsiTrapLogEntry ::= SEQUENCE
        {
              cpqScsiTrapLogIndex        INTEGER,
              cpqScsiTrapType            INTEGER,
              cpqScsiTrapTime            OCTET STRING
        }

    cpqScsiTrapLogIndex OBJECT-TYPE
        SYNTAX  INTEGER (0..2147483647)
        ACCESS  read-only
        STATUS  deprecated
        DESCRIPTION
           "The value of this object uniquely identifies this trapLogEntry
            at this time.  The most recent trap will have an index of 1 and
            the oldest trap will have an index of trapLogMaxSize.  Because of
            the queue-like nature of the trapLog this particular trap event's
            index will change as new traps are issued."
        ::= { cpqScsiTrapLogEntry 1 }

    cpqScsiTrapType OBJECT-TYPE
        SYNTAX  INTEGER {
            cpqScsiCntlrStatusChange(1),
            cpqScsiLogDrvStatusChange(2),
            cpqScsiPhyDrvStatusChange(3),
            cpqScsi2CntlrStatusChange(5001),
            cpqScsi2LogDrvStatusChange(5002),
            cpqScsi2PhyDrvStatusChange(5003)
            }
        ACCESS  read-only
        STATUS  deprecated
        DESCRIPTION
           "The type of the trap event that this entry describes.
            This number refers to an entry in a list of traps enumerating the
            possible traps the SCSI agent may issue."
        ::= { cpqScsiTrapLogEntry 2 }

    cpqScsiTrapTime OBJECT-TYPE
        SYNTAX  OCTET STRING (SIZE (6))
        ACCESS  read-only
        STATUS  deprecated
        DESCRIPTION
           "The time of the trap event that this entry describes.
            The time is given in year (first octet), month, day of month,
            hour, minute, second (last octet) order.  Each octet gives the
            value in Binary Coded Decimal (BCD)."
        ::= { cpqScsiTrapLogEntry 3 }

-- ****************************************************************************
--    SCSI Bus Group
--    ==============
--
-- The compaq enterprise               (1.3.6.1.4.1.232)
--      cpqSbScsiBus Group             (1.3.6.1.4.1.232.7)    (deprecated)
--       cpqSbScsiMibRev Group         (1.3.6.1.4.1.232.7.1)  (deprecated)
--        cpqSbDevice Group            (1.3.6.1.4.1.232.7.2)  (deprecated)
--
--     The scsiBus Group contains a MIB Revision group that contains
--     information about the revision of this document to which an
--     agent conforms.  The scsiBus Group contains component child groups
--     that contains information describing the parts of the SCSI subsystems
--     in this machine.
--
-- The status of this group has been changed to deprecated.  All useful
-- Information in this group can also be found in the cpqScsiTarget group.
-- Support of this group is optional for agents implementing the SCSI MIB.
-- This group should only be implemented if compatibility with older versions
-- of Insight Manager version 1.x is required.
--
--
--     An Insight Agent conforming to this document will return a mibRevMajor
--     of one and a mibRevMinor of zero.
--
--
-- The status of this group has been changed to deprecated.  All useful
-- Information in this group can also be found in the cpqScsiTarget group.
-- Support of this group is optional for agents implementing the SCSI MIB.
-- This group should only be implemented if compatibility with older versions
-- of Insight Manager version 1.x is desired.
--
-- ****************************************************************************

    cpqSbMibRevMajor OBJECT-TYPE
        SYNTAX  INTEGER (1..65535)
        ACCESS  read-only
        STATUS  deprecated
        DESCRIPTION
           "The Major Revision level.  A change in the major revision level
            represents a major change in the architecture of the MIB.  A
            change in the major revision level may indicate a significant
            change in the information supported and/or the meaning of the
            supported information, correct interpretation of data may require
            a MIB document with the same major revision level."
        ::= { cpqSbScsiMibRev 1 }

    cpqSbMibRevMinor OBJECT-TYPE
        SYNTAX  INTEGER (0..65535)
        ACCESS  read-only
        STATUS  deprecated
        DESCRIPTION
           "The Minor Revision level.  A change in the minor revision level
            may represent some minor additional support; no changes to any
            pre-existing information has occurred."
        ::= { cpqSbScsiMibRev 2 }

-- ****************************************************************************
--  The SCSI Device Group (Deprecated)
-- ****************************************************************************
--
--  The SCSI Device group describes the devices on the SCSI buses in the
--  system.
--
--  Implementation of the SCSI Device group is mandatory for all agents
--  supporting the SCSI Drive MIB.
--
--
-- The status of this group has been changed to deprecated.  All useful
-- Information in this group can also be found in the cpqScsiTarget group.
-- Support of this group is optional for agents implementing the SCSI MIB.
-- This group should only be implemented if compatibility with older versions
-- of Insight Manager version 1.x is desired.

    cpqSbDeviceTable OBJECT-TYPE
        SYNTAX  SEQUENCE OF CpqSbDeviceEntry
        ACCESS  not-accessible
        STATUS  deprecated
        DESCRIPTION
           "SCSI Drive Bus Table"
        ::= { cpqSbDevice 2 }

    cpqSbDeviceEntry OBJECT-TYPE
        SYNTAX  CpqSbDeviceEntry
        ACCESS  not-accessible
        STATUS  deprecated
        DESCRIPTION
           "SCSI Drive Bus Entry"
        INDEX   { cpqSbDevCntlrIndex, cpqSbDevBusIndex, cpqSbDevScsiIdIndex }
        ::= { cpqSbDeviceTable 1 }

        CpqSbDeviceEntry ::= SEQUENCE
        {
              cpqSbDevCntlrIndex         INTEGER,
              cpqSbDevBusIndex           INTEGER,
              cpqSbDevScsiIdIndex        INTEGER,
              cpqSbDevType               INTEGER,
              cpqSbDevModel              DisplayString,
              cpqSbDevFWRev              DisplayString,
              cpqSbDevVendor             DisplayString,
              cpqSbDevParityErrs         Counter,
              cpqSbDevPhaseErrs          Counter,
              cpqSbDevSelectTimeouts     Counter,
              cpqSbDevMsgRejects         Counter,
              cpqSbDevNegPeriod          INTEGER,
              cpqSbDevLocation           INTEGER
        }

    cpqSbDevCntlrIndex OBJECT-TYPE
        SYNTAX  INTEGER (0..255)
        ACCESS  read-only
        STATUS  deprecated
        DESCRIPTION
           "SCSI Device Bus Controller Index

            The controller index indicates which SCSI adapter card instance
            this table entry belongs to.  The controller index is the physical
            slot in the computer system where the adapter card is located."
        ::= { cpqSbDeviceEntry 1 }

    cpqSbDevBusIndex OBJECT-TYPE
        SYNTAX  INTEGER (0..255)
        ACCESS  read-only
        STATUS  deprecated
        DESCRIPTION
           "SCSI Device Bus Index

            The bus index indicates which SCSI bus instance on an
            adapter card this table entry belongs to.  The instances start
            at one and increment for each SCSI bus on a card."
        ::= { cpqSbDeviceEntry 2 }

    cpqSbDevScsiIdIndex OBJECT-TYPE
        SYNTAX  INTEGER (0..255)
        ACCESS  read-only
        STATUS  deprecated
        DESCRIPTION
           "SCSI Device Bus Physical Drive Index

            The physical drive index indicates which physical drive instance
            on a SCSI bus this table entry belongs to.  The physical drive
            index is the SCSI ID being used by that device."
        ::= { cpqSbDeviceEntry 3 }

    cpqSbDevType OBJECT-TYPE
        SYNTAX  INTEGER
        {
           other(1),
           disk(2),
           tape(3),
           printer(4),
           processor(5),
           wormDrive(6),
           cd-rom(7),
           scanner(8),
           optical(9),
           jukeBox(10),
           commDev(11)
        }
        ACCESS  read-only
        STATUS  deprecated
        DESCRIPTION
           "SCSI Device Type

            This is the type of SCSI device.  The following types are defined:

            other(1)
              The management agent does not recognize this type.  You may
              need to upgrade you software.

            disk(2)
              This is a direct-access device like a disk drive.

            tape(3)
              This is a sequential-access device like a tape drive.

            printer(4)
              This is a printer device.

            processor(5)
              This is a processor device like the ProLiant Storage System.

            worm(6)
              This is a write-once, read-many times device.

            cd-rom(7)
              This is a CD-ROM, read-only device.

            scanner(8)
              This is a scanner device.

            optical(9)
              This is an optical memory device.

            jukeBox(10)
              This is a medium changer device like a jukebox.

            commDev(11)
              This is a communications device like a LAN bridge."
        ::= { cpqSbDeviceEntry 4 }

    cpqSbDevModel OBJECT-TYPE
        SYNTAX  DisplayString (SIZE (0..17))
        ACCESS  read-only
        STATUS  deprecated
        DESCRIPTION
           "SCSI Device Model

            This is a description of the physical drive's model as returned by
            the SCSI inquiry command.  This can be used for identification
            purposes."
        ::= { cpqSbDeviceEntry 5 }

    cpqSbDevFWRev OBJECT-TYPE
        SYNTAX  DisplayString (SIZE (0..8))
        ACCESS  read-only
        STATUS  deprecated
        DESCRIPTION
           "SCSI Device Firmware Revision

            This is the revision level of the physical drive as returned by
            the SCSI inquiry command.  This can be used for identification
            purposes."
        ::= { cpqSbDeviceEntry 6 }

    cpqSbDevVendor OBJECT-TYPE
        SYNTAX  DisplayString (SIZE (0..9))
        ACCESS  read-only
        STATUS  deprecated
        DESCRIPTION
           "SCSI Device Vendor.

           This is the physical drive vendor's name as returned by
           the SCSI inquiry command.  This can be used for identification
           purposes."
        ::= { cpqSbDeviceEntry 7 }

    cpqSbDevParityErrs OBJECT-TYPE
        SYNTAX  Counter
        ACCESS  read-only
        STATUS  deprecated
        DESCRIPTION
           "SCSI Device Bus Parity Errors

           This is the number of parity errors seen on the SCSI bus while
           processing commands for this SCSI ID since the SCSI Interface
           Module was loaded.

           Parity errors may occasionally occur.  If this value should rise
           dramatically, you may have a problem.  Some common causes include
           radio frequency interference (RFI) on the bus cables, bad or missing
           terminating resisters on the drives or having more than one device
           with the same SCSI ID.  Insure the bus cable is free of obstructions
           and that the devices on the bus are properly configured."
        ::= { cpqSbDeviceEntry 8 }

    cpqSbDevPhaseErrs OBJECT-TYPE
        SYNTAX  Counter
        ACCESS  read-only
        STATUS  deprecated
        DESCRIPTION
           "SCSI Device Bus Phase Errors

           This is the number of times the SCSI bus entered an invalid operating
           state while processing commands for the SCSI ID since the SCSI
           Hardware Interface driver was loaded.

           If you see any phase errors you may have a problem.  Phase errors can
           be caused by a device which is not operating correctly.  If the phase
           errors continue to increase the device should be replaced."
        ::= { cpqSbDeviceEntry 9 }

    cpqSbDevSelectTimeouts OBJECT-TYPE
        SYNTAX  Counter
        ACCESS  read-only
        STATUS  deprecated
        DESCRIPTION
           "SCSI Device Bus Select Time-outs

           This is the number of times the controller attempted to start
           communications with a device by selecting it but the device did not
           respond.

           If you see any select time-outs you may have a problem.  The device
           may have hung during operations.  The SCSI controller will attempt to
           reset the device but if this value continues to increment you may
           need to power cycle the device."
        ::= { cpqSbDeviceEntry 10 }

    cpqSbDevMsgRejects OBJECT-TYPE
        SYNTAX  Counter
        ACCESS  read-only
        STATUS  deprecated
        DESCRIPTION
           "SCSI Device Bus Message Rejects

           This is the number of times the device rejected a command because
           it did not support the specified operation since the SCSI Hardware
           Interface driver was loaded.

           A large number for this object does not indicate a problem.  It
           only shows that the device does not support certain advanced SCSI
           commands that the device driver issued."
        ::= { cpqSbDeviceEntry 11 }

    cpqSbDevNegPeriod OBJECT-TYPE
        SYNTAX  INTEGER (0..2147483647)
        ACCESS  read-only
        STATUS  deprecated
        DESCRIPTION
           "SCSI Device Negotiated Period

           This is the amount of time that was negotiated between the controller
           and the device as a synchronous transfer window.  A synchronous
           transfer window is how long the device can transfer data without
           requiring an acknowledgment from the controller.  In general the
           larger the negotiated period is, the higher the device throughput."
        ::= { cpqSbDeviceEntry 12 }

    cpqSbDevLocation OBJECT-TYPE
        SYNTAX  INTEGER
        {
           other(1),
           proliant(2)
        }
        ACCESS  read-only
        STATUS  deprecated
        DESCRIPTION
           "SCSI Device Location

           This is the physical location of where the device is located.  The
           following values are defined:

           other(1)    The drives are not located in any special product that
                       identifies the location.
           proliant(2) The drives are located in the ProLiant Storage System."
        ::= { cpqSbDeviceEntry 13 }

-- ****************************************************************************
--    Tape Physical Drive Group
--    =========================
--
-- The compaq enterprise               (1.3.6.1.4.1.232)
--      cpqTape Group                  (1.3.6.1.4.1.232.5)
--       cpqTapeComponent Group        (1.3.6.1.4.1.232.5.4)
--        cpqTapePhyDrv Group          (1.3.6.1.4.1.232.5.4.1)
--         cpqTapePhyDrvTable          (1.3.6.1.4.1.232.5.4.1.1)
--
--  The PhyDrv group contains configuration about the physical drives
--  associated with tape backup products.
--
--  Implementation of the PhyDrv group is mandatory for all agents that
--  support the Tape MIB.
--
-- ****************************************************************************

    cpqTapePhyDrvTable OBJECT-TYPE
        SYNTAX  SEQUENCE OF CpqTapePhyDrvEntry
        ACCESS  not-accessible
        STATUS  mandatory
        DESCRIPTION
           "Tape Physical Drive Table."
        ::= { cpqTapePhyDrv 1 }

    cpqTapePhyDrvEntry OBJECT-TYPE
        SYNTAX  CpqTapePhyDrvEntry
        ACCESS  not-accessible
        STATUS  mandatory
        DESCRIPTION
           "Tape Physical Drive Entry."
        INDEX   { cpqTapePhyDrvCntlrIndex, cpqTapePhyDrvBusIndex,
                  cpqTapePhyDrvScsiIdIndex, cpqTapePhyDrvLunIndex }
        ::= { cpqTapePhyDrvTable 1 }

        CpqTapePhyDrvEntry ::= SEQUENCE
        {
              cpqTapePhyDrvCntlrIndex            INTEGER,
              cpqTapePhyDrvBusIndex              INTEGER,
              cpqTapePhyDrvScsiIdIndex           INTEGER,
              cpqTapePhyDrvLunIndex              INTEGER,
              cpqTapePhyDrvType                  INTEGER,
              cpqTapePhyDrvCondition             INTEGER,
              cpqTapePhyDrvMagSize               INTEGER,
              cpqTapePhyDrvSerialNumber          DisplayString,
              cpqTapePhyDrvCleanReq              INTEGER,
              cpqTapePhyDrvCleanTapeRepl         INTEGER,
              cpqTapePhyDrvFwSubtype             INTEGER,
              cpqTapePhyDrvName                  DisplayString,
              cpqTapePhyDrvCleanTapeCount        INTEGER,
              cpqTapePhyDrvFwRev                 DisplayString,
              cpqTapePhyDrvStatus                INTEGER,
              cpqTapePhyDrvHotPlug               INTEGER,
              cpqTapePhyDrvPlacement             INTEGER,
              cpqTapePhyDrvLibraryDrive          INTEGER,
              cpqTapePhyDrvLoaderName            DisplayString,
              cpqTapePhyDrvLoaderFwRev           DisplayString,
              cpqTapePhyDrvLoaderSerialNum       DisplayString
        }

    cpqTapePhyDrvCntlrIndex OBJECT-TYPE
        SYNTAX  INTEGER
        ACCESS  read-only
        STATUS  mandatory
        DESCRIPTION
           "Tape Physical Drive Controller Index.

            The controller index indicates to which SCSI adapter instance
            this tape table entry belongs.  The controller index is the
            physical slot in the computer where the adapter is located."
        ::= { cpqTapePhyDrvEntry 1 }

    cpqTapePhyDrvBusIndex OBJECT-TYPE
        SYNTAX  INTEGER (0..255)
        ACCESS  read-only
        STATUS  mandatory
        DESCRIPTION
           "Tape Physical Drive Bus Index.

            The bus index indicates to which SCSI bus instance on an
            adapter this table entry belongs.  The instances start
            at one and increment for each SCSI bus on a card."
        ::= { cpqTapePhyDrvEntry 2 }

    cpqTapePhyDrvScsiIdIndex OBJECT-TYPE
        SYNTAX  INTEGER (0..255)
        ACCESS  read-only
        STATUS  mandatory
        DESCRIPTION
           "Tape Physical Drive Index.

            The physical drive index indicates to which physical drive
            instance on a SCSI bus this table entry belongs.  The physical
            drive index is the SCSI ID being used by that tape drive."
        ::= { cpqTapePhyDrvEntry 3 }

    cpqTapePhyDrvLunIndex OBJECT-TYPE
        SYNTAX  INTEGER (0..255)
        ACCESS  read-only
        STATUS  mandatory
        DESCRIPTION
           "Tape Physical Drive Logical Unit Index.

            The physical drive logical unit index indicates to which
            physical drive logical unit on a SCSI ID instance on a SCSI
            bus this table entry belongs.  The physical drive Lun index
            is the logical unit number being used by that tape drive."
        ::= { cpqTapePhyDrvEntry 4 }

    cpqTapePhyDrvType OBJECT-TYPE
        SYNTAX  INTEGER
        {
           other(1),
           cpqDat4-16(2),
           cpqDatAuto(3),
           cpqDat2-8(4),
           cpqDlt10-20(5),
           cpqDlt20-40(6),
           cpqDlt15-30(7),
           cpqDlt35-70(8),
           cpqDat4-8(9),
           cpqSlr4-8(10),
           cpqDat12-24(11),
           cpqDatAuto12-24(12),
           cpqMlr16-32(13),
           cpqAit35(14),
           cpqAit50(15),
           cpqDat20-40(16),
           cpqDlt40-80(17),
           cpqDatAuto20-40(18),
           cpqSuperDlt1(19),
           cpqAit35Lvd(20),
           cpqCompaq(21)
        }
        ACCESS  read-only
        STATUS  mandatory
        DESCRIPTION
           "Tape Device Type.

            This is the drives model, and can be used for identification
            purposes.  The following values are defined:

            other(1)
               The management agent does not recognize this model.
               You may need to upgrade your software.

            cpqDat4-16(2)
               Compaq 4/8-Gigabyte TurboDAT Drive.

            cpqDatAuto(3)
               Compaq TurboDAT Autoloader.

            cpqDat2-8(4)
               Compaq 2/8-Gigabyte TurboDAT Drive.

            cpqDlt10-20(5)
               Compaq 10/20-GB DLT Drive.

            cpqDlt20-40(6)
               Compaq 20/40-GB DLT Drive.

            cpqDlt15-30(7)
               Compaq 15/30-GB DLT Drive.

            cpqDlt35-70(8)
               Compaq 35/70-GB DLT Drive.

            cpqDat4-8(9)
               Compaq 4/8-GB DAT Drive.

            cpqSlr4-8(10)
               Compaq 4/8-GB SLR Drive.

            cpqDat12-24(11)
               Compaq 12/24-GB DAT Drive.

            cpqDatAuto12-24(12)
               Compaq 12/24-GB DAT Autoloader.

            cpqMlr16-32(13)
               Compaq 16/32-GB MLR Drive.

            cpqAit35(14)
               Compaq AIT 35GB Drive.

            cpqAit50(15)
               Compaq AIT 50GB Drive.

            cpqDat20-40(16)
               Compaq 20/40GB DAT Drive.

            cpqDlt40-80(17)
               Compaq 40/80GB DLT Drive.

            cpqDatAuto20-40(18)
               Compaq 20/40GB DAT Autoloader.

            cpqSuperDlt1(19)
               Compaq 100GB Super DLT Drive.

            cpqAit35Lvd(20)
               Compaq AIT 35 LVD Drive.

            cpqCompaq(21)
               Supported Tape Drive."

        ::= { cpqTapePhyDrvEntry 5 }

    cpqTapePhyDrvCondition OBJECT-TYPE
        SYNTAX  INTEGER
        {
           other(1),
           ok(2),
           degraded(3),
           failed(4)
        }
        ACCESS  read-only
        STATUS  mandatory
        DESCRIPTION
           "Tape Physical Drive Status.

            The physical drive can be in one of the following states:

            other(1)
              The drive is in a state other than one of those listed
              below.

            ok(2)
              Indicates that the physical drive is in normal operation mode.
              No user action is necessary.

            degraded(3)
              Indicates that the physical drive has degraded in some manner.

            failed(4)
              Indicates that the physical drive has failed and can no longer
              return data.  When convenient, you should bring down the server
              and run diagnostics to help identify the problem.
              The drive may need to be replaced."
       ::= { cpqTapePhyDrvEntry 6 }


    cpqTapePhyDrvMagSize OBJECT-TYPE
        SYNTAX  INTEGER (1..255)
        ACCESS  read-only
        STATUS  mandatory
        DESCRIPTION
           "Tape Physical Drive Magazine Size.

            The number of tape slots available in the magazine cartridge
            that is currently loaded into the tape drive.

            For non-autoloader devices, this value will be 1."
        ::= { cpqTapePhyDrvEntry 7 }

    cpqTapePhyDrvSerialNumber OBJECT-TYPE
        SYNTAX  DisplayString (SIZE (0..64))
        ACCESS  read-only
        STATUS  mandatory
        DESCRIPTION
            "Tape Physical Drive Serial Number.

            This is the unit serial number for the tape drive.  It
            can be used for identification purposes."
        ::= { cpqTapePhyDrvEntry 8 }

    cpqTapePhyDrvCleanReq OBJECT-TYPE
        SYNTAX  INTEGER
        {
                other(1),
                true(2),
                false(3)
        }
        ACCESS  read-only
        STATUS  mandatory
        DESCRIPTION
            "Tape Physical Drive Cleaning Required Status.

             This is an indication of whether the tape drive heads
             require a cleaning session to occur.  If this variable
             indicates a need to clean the tape heads, then a cleaning
             tape will need to be inserted and run through a cleaning
             cycle.

             This variable can be in one of the following states:

             other(1)
              The tape drive does not support monitoring of the cleaning
              required status.

             true(2)
              The tape drive requires a cleaning tape session in order
              to clean the heads.

             false(3)
              The tape drive does not require any cleaning tape session."
        ::= { cpqTapePhyDrvEntry 9 }

    cpqTapePhyDrvCleanTapeRepl OBJECT-TYPE
        SYNTAX  INTEGER
        {
                other(1),
                true(2),
                false(3)
        }
        ACCESS  read-only
        STATUS  mandatory
        DESCRIPTION
            "Tape Physical Drive Cleaning Tape Replacement Status.

             This variable is only applicable to autoloader tape drives.
             This variable indicates whether the cleaning tape which is
             inserted in an autoloader needs to be replaced because its
             cleaning capability is exhausted (it is at end of tape).

             This variable can be in one of the following states:

             other(1)
              The tape drive does not support monitoring of the cleaning
              tape replacement status.

             true(2)
              The autoloader tape drive requires a new cleaning tape to
              be inserted.

             false(3)
              The tape drive does not require a new cleaning tape."
        ::= { cpqTapePhyDrvEntry 10 }

    cpqTapePhyDrvFwSubtype OBJECT-TYPE
        SYNTAX  INTEGER (0..255)
        ACCESS  read-only
        STATUS  mandatory
        DESCRIPTION
            "Tape Physical Drive Firmware Subtype.

             This is used to differentiate the firmware versions
             which have the same tape drive type (as specified by
             cpqTapePhyDrvType).  Tape drives will contain a value
             of 1 for this variable when they first ship, and this value
             will be incremented if future versions are shipped which
             are not firmware compatible with the predecessor.  If the
             tape drive does not support this capability, a value of 0
             will be returned."
        ::= { cpqTapePhyDrvEntry 11 }

    cpqTapePhyDrvName OBJECT-TYPE
        SYNTAX  DisplayString (SIZE (0..128))
        ACCESS  read-only
        STATUS  mandatory
        DESCRIPTION
            "Tape Physical Drive Name.

             This is a combination of the vendor ID and the product ID as
             returned by the SCSI inquiry command.  This can be used for
             identification purposes."
        ::= { cpqTapePhyDrvEntry 12 }

   cpqTapePhyDrvCleanTapeCount OBJECT-TYPE
        SYNTAX  INTEGER
        ACCESS  read-only
        STATUS  mandatory
        DESCRIPTION
            "Tape Physical Drive Cleaning Tape Count.

             This variable is only applicable to autoloader tape drives.
             This variable is a count from a tape drive of the number of
             cleanings done by the tape cleaner last in the drive."
        ::= { cpqTapePhyDrvEntry 13 }

   cpqTapePhyDrvFwRev OBJECT-TYPE
        SYNTAX  DisplayString (SIZE (0..8))
        ACCESS  read-only
        STATUS  mandatory
        DESCRIPTION
            "Tape Physical Drive Firmware Revision.

             This is the revision level of the physical drive as returned by
             the SCSI inquiry command.  This can be used for identification
             purposes."
        ::= { cpqTapePhyDrvEntry 14 }

    cpqTapePhyDrvStatus OBJECT-TYPE
        SYNTAX  INTEGER
        {
           other(1),
           ok(2),
           failed(4),
           offline(5),
           missingWasOk(6),
           missingWasFailed(7),
           missingWasOffline(8)
        }
        ACCESS  read-only
        STATUS  mandatory
        DESCRIPTION
           "Tape Physical Drive Status.

            The tape physical drive can be in one of the following states:

            other(1)
              The tape drive is in a state other than one of those listed
              below.

            ok(2)
              Indicates that the tape physical drive is in normal operation
              mode.  No user action is necessary.

            failed(4)
              Indicates that the tape physical drive has failed and can no
              longer return data.  The drive may need to be replaced.

            offline(5)
              Indicates that the tape physical drive is offline and can no
              longer return data.  No further status is available.

            missingWasOk(6)
              Indicates that a tape physical drive had a status of OK and
              is no longer present.  The drive has been removed.

            missingWasFailed(7)
              Indicates that a tape physical drive had a status of FAILED
              and is no longer present.  The drive has been removed.

            missingWasOffline(8)
              Indicates that a tape physical drive had a status of OFFLINE
              and is no longer present.  The drive has been removed."
        ::= { cpqTapePhyDrvEntry 15 }

    cpqTapePhyDrvHotPlug OBJECT-TYPE
        SYNTAX  INTEGER
        {
           other(1),
           hotPlug(2),
           nonHotPlug(3)
        }
        ACCESS  read-only
        STATUS  mandatory
        DESCRIPTION
           "Tape Physical Drive Hot Plug Support Status.

            The following values are defined:

            other(1)
              The agent is unable to determine if this drive
              supports hot plug replacement.

            hotPlug(2)
              The drive supports hot plug replacement.

            nonhotPlug(3)
              The drive does not support hot plug replacement."
        ::= { cpqTapePhyDrvEntry 16 }

    cpqTapePhyDrvPlacement OBJECT-TYPE
        SYNTAX  INTEGER
        {
           other(1),
           internal(2),
           external(3)
        }
        ACCESS  read-only
        STATUS  mandatory
        DESCRIPTION
           "Tape Physical Drive Placement.

            The following values are defined:

            other(1)
              The agent is unable to determine if the tape drive is
              internal or external to the system chassis.

            internal(2)
              The tape drive is located in an internal Proliant system
              chassis.

            external(3)
              The tape drive is located in an external Proliant storage
              system."
        ::= { cpqTapePhyDrvEntry 17 }

     cpqTapePhyDrvLibraryDrive OBJECT-TYPE
        SYNTAX  INTEGER
        {
           other(1),
           true(2),
           false(3)
        }
        ACCESS  read-only
        STATUS  mandatory
        DESCRIPTION
            "Tape Physical Drive Library Drive.

             This variable indicates whether or not the tape drive is part
             of a tape library.  It can be in one of the following states:

             other(1)
              Indicates that the storage agents cannot determine if the
              tape drive is part of a tape library.

             true(2)
              The tape drive is part of a tape library.

             false(3)
              The tape drive is not part of a tape library."
        ::= { cpqTapePhyDrvEntry 18 }

    cpqTapePhyDrvLoaderName OBJECT-TYPE
        SYNTAX  DisplayString (SIZE (0..128))
        ACCESS  read-only
        STATUS  mandatory
        DESCRIPTION
            "Tape Autoloader Name.

             This is a combination of the vendor ID and the product ID as
             returned by the SCSI inquiry command.  This can be used for
             identification purposes."
        ::= { cpqTapePhyDrvEntry 19 }

   cpqTapePhyDrvLoaderFwRev OBJECT-TYPE
        SYNTAX  DisplayString (SIZE (0..8))
        ACCESS  read-only
        STATUS  mandatory
        DESCRIPTION
            "Tape Autoloader Firmware Revision.

             This is the firmware revision level of the autoloader as returned
             by the SCSI inquiry command.  This can be used for identification
             purposes."
        ::= { cpqTapePhyDrvEntry 20 }

    cpqTapePhyDrvLoaderSerialNum OBJECT-TYPE
        SYNTAX  DisplayString (SIZE (0..64))
        ACCESS  read-only
        STATUS  mandatory
        DESCRIPTION
            "Tape Autoloader Serial Number.

            This is the autoloader serial number.  It can be used for
            identification purposes."
        ::= { cpqTapePhyDrvEntry 21 }


-- ****************************************************************************
--    Tape Counters Group
--    ===================
--
-- The compaq enterprise               (1.3.6.1.4.1.232)
--      cpqTape Group                  (1.3.6.1.4.1.232.5)
--       cpqTapeComponent Group        (1.3.6.1.4.1.232.5.4)
--        cpqTapeCounters Group        (1.3.6.1.4.1.232.5.4.2)
--         cpqTapeCountersTable        (1.3.6.1.4.1.232.5.4.2.1)
--
--  The Tape counters group describes the tape device error information about
--  the Tape bus targets (devices) in the system.
--
--  Implementation of the Tape counters group is mandatory for all agents
--  supporting the Tape MIB.
--
-- ****************************************************************************

    cpqTapeCountersTable OBJECT-TYPE
        SYNTAX  SEQUENCE OF CpqTapeCountersEntry
        ACCESS  not-accessible
        STATUS  mandatory
        DESCRIPTION
           "Tape Counters Table."
        ::= { cpqTapeCounters 1 }

    cpqTapeCountersEntry OBJECT-TYPE
        SYNTAX  CpqTapeCountersEntry
        ACCESS  not-accessible
        STATUS  mandatory
        DESCRIPTION
           "Tape Counters Entry."
        INDEX   { cpqTapeCountersCntlrIndex, cpqTapeCountersBusIndex,
                 cpqTapeCountersScsiIdIndex, cpqTapeCountersLunIndex }
        ::= { cpqTapeCountersTable 1 }

        CpqTapeCountersEntry ::= SEQUENCE
        {
             cpqTapeCountersCntlrIndex         INTEGER,
             cpqTapeCountersBusIndex           INTEGER,
             cpqTapeCountersScsiIdIndex        INTEGER,
             cpqTapeCountersLunIndex           INTEGER,
             cpqTapeCountersReWrites           Counter,
             cpqTapeCountersReReads            Counter,
             cpqTapeCountersTotalErrors        Counter,
             cpqTapeCountersTotalUncorrectable Counter,
             cpqTapeCountersTotalBytes         Counter
        }

    cpqTapeCountersCntlrIndex OBJECT-TYPE
        SYNTAX  INTEGER
        ACCESS  read-only
        STATUS  mandatory
        DESCRIPTION
           "SCSI Counters Controller Index.

            The controller index indicates to which SCSI adapter instance
            this table entry belongs.  The controller index is the physical
            slot in the computer system where the adapter is located."
        ::= { cpqTapeCountersEntry 1 }

    cpqTapeCountersBusIndex OBJECT-TYPE
        SYNTAX  INTEGER (0..255)
        ACCESS  read-only
        STATUS  mandatory
        DESCRIPTION
           "SCSI Counters Bus Index.

            The bus index indicates to which SCSI bus instance on an
            adapter card this table entry belongs.  The instances start
            at one and increment for each SCSI bus on a card."
        ::= { cpqTapeCountersEntry 2 }

    cpqTapeCountersScsiIdIndex OBJECT-TYPE
        SYNTAX  INTEGER (0..255)
        ACCESS  read-only
        STATUS  mandatory
        DESCRIPTION
           "SCSI Counters Device Index.

            The device index indicates to which device instance on a
            SCSI bus this table entry belongs.  The device index
            is the SCSI ID being used by that device."
        ::= { cpqTapeCountersEntry 3 }

    cpqTapeCountersLunIndex OBJECT-TYPE
        SYNTAX  INTEGER (0..255)
        ACCESS  read-only
        STATUS  mandatory
        DESCRIPTION
           "SCSI Counters Logical Unit Index.

            The logical unit index indicates to which Lun device instance
            on a SCSI bus this table entry belongs.  The logical unit
            index is the Lun being used by that device."
        ::= { cpqTapeCountersEntry 4 }

    cpqTapeCountersReWrites OBJECT-TYPE
        SYNTAX  Counter
        ACCESS  read-only
        STATUS  mandatory
        DESCRIPTION
           "Tape Device Re-write count.

            This is the number of times blocks had to be re-written to the
            device.  This value is maintained since the Tape Hardware Interface
            driver was loaded.

            Re-write errors may occasionally occur.  If this value should rise
            dramatically, you may need to clean the device.  If you continue
            to have re-writes, you may have a problem.  Some common causes
            include radio frequency interference (RFI) on the bus cables,
            bad or missing terminating resisters on the drives or having more
            than one device with the same SCSI ID.  Insure the bus cable is
            free of obstructions and that the devices on the bus are properly
            configured."
        ::= { cpqTapeCountersEntry 5 }

    cpqTapeCountersReReads OBJECT-TYPE
        SYNTAX  Counter
        ACCESS  read-only
        STATUS  mandatory
        DESCRIPTION
           "Tape Device Re-read count.

            This is the number of times blocks had to be re-read from the
            device.  This value is maintained since the Tape Hardware Interface
            driver was loaded.

            Re-read errors may occasionally occur.  If this value should rise
            dramatically, you may need to clean the device.  If you continue
            to have re-reads, you may have a problem.  Some common causes
            include radio frequency interference (RFI) on the bus cables,
            bad or missing terminating resisters on the drives or having more
            than one device with the same SCSI ID.  Insure the bus cable is
            free of obstructions and that the devices on the bus are properly
            configured."
        ::= { cpqTapeCountersEntry 6 }

    cpqTapeCountersTotalErrors OBJECT-TYPE
        SYNTAX  Counter
        ACCESS  read-only
        STATUS  mandatory
        DESCRIPTION
           "Tape Device Total Errors.

            This is the total number of read/write errors encountered.
            This value is maintained since the Tape Hardware Interface
            driver was loaded.

            Errors may occasionally occur.  If this value should rise
            dramatically, you may need to clean the device.  If you continue
            to have errors, you may have a problem.  Some common causes include
            radio frequency interference (RFI) on the bus cables, bad or
            missing terminating resisters on the drives or having more than
            one device with the same SCSI ID.  Insure the bus cable is free
            of obstructions and that the devices on the bus are properly
            configured."
        ::= { cpqTapeCountersEntry 7 }

    cpqTapeCountersTotalUncorrectable OBJECT-TYPE
        SYNTAX  Counter
        ACCESS  read-only
        STATUS  mandatory
        DESCRIPTION
           "Tape Device Total Uncorrectable Errors.

            This is the total number of read and write errors which could not
            be corrected.  This value is maintained since the Tape Hardware
            Interface driver was loaded.

            Errors may occasionally occur.  If this value should rise
            dramatically, you may need to clean the device.  If you continue
            to have errors, you may have a problem.  Some common causes include
            radio frequency interference (RFI) on the bus cables, bad or
            missing terminating resisters on the drives or having more than
            one device with the same SCSI ID.  Insure the bus cable is free
            of obstructions and that the devices on the bus are properly
            configured."
        ::= { cpqTapeCountersEntry 8 }

    cpqTapeCountersTotalBytes OBJECT-TYPE
        SYNTAX  Counter
        ACCESS  read-only
        STATUS  mandatory
        DESCRIPTION
           "Tape Device Total Bytes.

            This is the number total number of bytes read/written to the tape
            currently installed in the device.  This value is reset whenever
            a new tape is inserted into the device."
        ::= { cpqTapeCountersEntry 9 }


-- ****************************************************************************
--    Tape Library Group
--    ===================
--
-- The compaq enterprise               (1.3.6.1.4.1.232)
--      cpqTape Group                  (1.3.6.1.4.1.232.5)
--       cpqTapeComponent Group        (1.3.6.1.4.1.232.5.4)
--        cpqTapeLibrary Group         (1.3.6.1.4.1.232.5.4.3)
--         cpqTapeLibraryTable         (1.3.6.1.4.1.232.5.4.3.1)
--
--  The Tape library group describes the tape autoloader devices and information about
--  the Tape bus targets (devices) in the autoloader.
--
--  Implementation of the Tape library group is mandatory for all agents
--  supporting the Tape Group.
--
-- ****************************************************************************

    cpqTapeLibraryTable OBJECT-TYPE
        SYNTAX  SEQUENCE OF CpqTapeLibraryEntry
        ACCESS  not-accessible
        STATUS  mandatory
        DESCRIPTION
           "Tape Library Table."
        ::= { cpqTapeLibrary 1 }

    cpqTapeLibraryEntry OBJECT-TYPE
        SYNTAX  CpqTapeLibraryEntry
        ACCESS  not-accessible
        STATUS  mandatory
        DESCRIPTION
           "Tape Library Entry."
        INDEX   { cpqTapeLibraryCntlrIndex, cpqTapeLibraryBusIndex,
                 cpqTapeLibraryScsiIdIndex, cpqTapeLibraryLunIndex }
        ::= { cpqTapeLibraryTable 1 }

        CpqTapeLibraryEntry ::= SEQUENCE
        {
             cpqTapeLibraryCntlrIndex         INTEGER,
             cpqTapeLibraryBusIndex           INTEGER,
             cpqTapeLibraryScsiIdIndex        INTEGER,
             cpqTapeLibraryLunIndex           INTEGER,
             cpqTapeLibraryCondition          INTEGER,
             cpqTapeLibraryStatus             INTEGER,
             cpqTapeLibraryDoorStatus         INTEGER,
             cpqTapeLibraryStatHours          Counter,
             cpqTapeLibraryStatMoves          Counter,
             cpqTapeLibraryName               DisplayString,
             cpqTapeLibrarySerialNumber       DisplayString,
             cpqTapeLibraryDriveList          OCTET STRING,
             cpqTapeLibraryState              INTEGER,
             cpqTapeLibraryTemperature        INTEGER,
             cpqTapeLibraryRedundancy         INTEGER,
             cpqTapeLibraryHotSwap            INTEGER,
             cpqTapeLibraryFwRev              DisplayString,
             cpqTapeLibraryTapeList           OCTET STRING
        }

    cpqTapeLibraryCntlrIndex OBJECT-TYPE
        SYNTAX  INTEGER
        ACCESS  read-only
        STATUS  mandatory
        DESCRIPTION
           "SCSI Library Controller Index.

            The controller index indicates to which SCSI adapter instance
            this table entry belongs.  The controller index is the physical
            slot in the computer system where the adapter is located."
        ::= { cpqTapeLibraryEntry 1 }

    cpqTapeLibraryBusIndex OBJECT-TYPE
        SYNTAX  INTEGER (0..255)
        ACCESS  read-only
        STATUS  mandatory
        DESCRIPTION
           "SCSI Library Bus Index.

            The bus index indicates to which SCSI bus instance on an
            adapter card this table entry belongs.  The instances start
            at one and increment for each SCSI bus on a card."
        ::= { cpqTapeLibraryEntry 2 }

    cpqTapeLibraryScsiIdIndex OBJECT-TYPE
        SYNTAX  INTEGER (0..255)
        ACCESS  read-only
        STATUS  mandatory
        DESCRIPTION
           "SCSI Library Device Index.

            The device index indicates to which device instance on a
            SCSI bus this table entry belongs.  The device index
            is the SCSI ID being used by that device."
        ::= { cpqTapeLibraryEntry 3 }

    cpqTapeLibraryLunIndex OBJECT-TYPE
        SYNTAX  INTEGER (0..255)
        ACCESS  read-only
        STATUS  mandatory
        DESCRIPTION
           "SCSI Library Logical Unit Index.

            The logical unit index indicates to which Lun device instance
            on a SCSI bus this table entry belongs.  The logical unit
            index is the Lun being used by that device."
        ::= { cpqTapeLibraryEntry 4 }

    cpqTapeLibraryCondition OBJECT-TYPE
        SYNTAX  INTEGER
        {
           other(1),
           ok(2),
           degraded(3),
           failed(4)
        }
        ACCESS  read-only
        STATUS  mandatory
        DESCRIPTION
           "Tape Library Status.

            The library can be in one of the following states:

            other(1)
              The library is in a state other than one of those listed
              below.

            ok(2)
              Indicates that the library is in normal operation mode.
              No user action is necessary.

            degraded(3)
              Indicates that the library has degraded in some manner.

            failed(4)
              Indicates that the library has failed and can no longer
              return data.  When convenient, you should bring down the server
              and run diagnostics to help identify the problem.
              The library may need to be replaced."

       ::= { cpqTapeLibraryEntry 5 }

    cpqTapeLibraryStatus OBJECT-TYPE
        SYNTAX  INTEGER (0..64535)
        ACCESS  read-only
        STATUS  mandatory
        DESCRIPTION
            "Error code returned by the last library error."

        ::= { cpqTapeLibraryEntry 6 }

    cpqTapeLibraryDoorStatus OBJECT-TYPE
        SYNTAX  INTEGER
        {
           other(1),
           closed(2),
           open(3),
           notSupported(4)
        }
        ACCESS read-only
        STATUS mandatory
        DESCRIPTION
            "Status of the library door.

            The door can be in one of the following states:

            other(1)
              The door is in a state other than one of those listed
              below.

            closed(2)
              The door is closed.

            open(3)
              The door is open.

            notSupported(4)
              The door status is not supported by the device."

        ::= { cpqTapeLibraryEntry 7 }

    cpqTapeLibraryStatHours OBJECT-TYPE
        SYNTAX  Counter
        ACCESS  read-only
        STATUS  mandatory
        DESCRIPTION
           "The number of hours of operation for the library."

        ::= { cpqTapeLibraryEntry 8 }

    cpqTapeLibraryStatMoves OBJECT-TYPE
        SYNTAX  Counter
        ACCESS  read-only
        STATUS  mandatory
        DESCRIPTION
           "The number of tape moves for the library loader arm."

        ::= { cpqTapeLibraryEntry 9 }

    cpqTapeLibraryName OBJECT-TYPE
        SYNTAX  DisplayString (SIZE (0..128))
        ACCESS  read-only
        STATUS  mandatory
        DESCRIPTION
            "Tape Library Name."

        ::= { cpqTapeLibraryEntry 10 }

    cpqTapeLibrarySerialNumber OBJECT-TYPE
        SYNTAX  DisplayString (SIZE (0..64))
        ACCESS  read-only
        STATUS  mandatory
        DESCRIPTION
            "Tape Library Serial Number.

            This is the unit serial number for the library.  It
            can be used for identification purposes."
        ::= { cpqTapeLibraryEntry 11 }

    cpqTapeLibraryDriveList OBJECT-TYPE
        SYNTAX  OCTET STRING (SIZE (0..320))
        ACCESS  read-only
        STATUS  deprecated
        DESCRIPTION
           "Tape Library Drive List

            This is a data structure containing the list of tape drive ids
            that are present in this library.  The format is:

              BYTE    Controller Number
              BYTE    Bus Number
              BYTE    SCSI ID
              BYTE    Logical Unit Number

            There will be 1 structure for each drive present in the library."

        ::= { cpqTapeLibraryEntry 12 }

    cpqTapeLibraryState OBJECT-TYPE
        SYNTAX  INTEGER
        {
           other(1),
           ok(2),
           degraded(3),
           failed(4),
           offline(5)
        }
        ACCESS  read-only
        STATUS  mandatory
        DESCRIPTION
           "Tape Library Status.

            The library can be in one of the following states:

            other(1)
              The library is in a state other than one of those listed
              below.

            ok(2)
              Indicates that the library is in normal operation mode.
              No user action is necessary.

            degraded(3)
              Indicates that the library has degraded in some manner.

            failed(4)
              Indicates that the library has failed and can no longer
              return data.  When convenient, you should bring down the server
              and run diagnostics to help identify the problem.
              The library may need to be replaced.

            offline(5)
              Indicates that the agents can no longer communicate with
              the library.  This could be caused by a cabling problem or the
              library may be powered off."

       ::= { cpqTapeLibraryEntry 13 }

    cpqTapeLibraryTemperature OBJECT-TYPE
        SYNTAX  INTEGER
        {
           other(1),
           notSupported(2),
           ok(3),
           safeTempExceeded(4),
           maxTempExceeded(5)
        }
        ACCESS  read-only
        STATUS  mandatory
        DESCRIPTION
           "Tape Library Temperature Status.

            The library temperature can be in one of the following states:

            other(1)
              The library temperature status is unknown.

            notSupported(2)
              Indicates that the library cannot detect or report temperature.

            ok(3)
              Indicates that the temperature of the library is within normal
              operating limits.

            safeTempExceeded(4)
              Indicates that the temperature of the library has exceeded the
              safe operational temperature. The library will continue to
              operate under this warning.

            maxTempExceeded(5)
              Indicates that the temperature of the library has exceeded
              normal operating limits to the extent that the library may
              no longer function."

       ::= { cpqTapeLibraryEntry 14 }

    cpqTapeLibraryRedundancy OBJECT-TYPE
        SYNTAX  INTEGER
        {
           other(1),
           notSupported(2),
           capable(3),
           notCapable(4),
           active(5)
        }
        ACCESS  read-only
        STATUS  mandatory
        DESCRIPTION
           "Tape Library Redundancy Status.

            Redundancy status denotes the presence of internal redundant
            components such as fans, power supplies, etc. The library
            redundancy can be in one of the following states:

            other(1)
              The library redundancy status is unknown.

            notSupported(2)
              Indicates that the library cannot detect or report redundancy
              status.

            capable(3)
              Indicates that the library is capable of detecting and reporting
              redundant components but there are not enough redundant units
              installed to make redundancy active.

            notCapable(4)
              Indicates that the library is capable of detecting and reporting
              redundant components but there are no components that support
              redundancy.

            active(5)
              Indicates that the library is capable of detecting and reporting
              redundant components, there are enough redundant units installed,
              and redundancy is active."

       ::= { cpqTapeLibraryEntry 15 }

    cpqTapeLibraryHotSwap OBJECT-TYPE
        SYNTAX  INTEGER
        {
           other(1),
           notSupported(2),
           capable(3),
           notCapable(4)
        }
        ACCESS  read-only
        STATUS  mandatory
        DESCRIPTION
           "Tape Library Hot Swap Status.

            Hot swap status denotes the presence of hot swappable internal
            components such as drives, fans, power supplies, etc. The library
            hot swap status can be in one of the following states:

            other(1)
              The library hot swap status is unknown.

            notSupported(2)
              Indicates that the library cannot detect or report hot swap
              status.

            capable(3)
              Indicates that the library is capable of detecting and reporting
              hot swappable internal components and has at least one hot
              swappable component.

            notCapable(4)
              Indicates that the library is capable of detecting and reporting
              hot swappable internal components but there are no hot swappable
              components installed."

       ::= { cpqTapeLibraryEntry 16 }

   cpqTapeLibraryFwRev OBJECT-TYPE
        SYNTAX  DisplayString (SIZE (0..8))
        ACCESS  read-only
        STATUS  mandatory
        DESCRIPTION
            "Tape Library Firmware Revision.

             This is the revision level of the tape library firmware as
             returned by the SCSI inquiry command.  This can be used for
             identification purposes."
        ::= { cpqTapeLibraryEntry 17 }

    cpqTapeLibraryTapeList OBJECT-TYPE
        SYNTAX  OCTET STRING (SIZE (0..560))
        ACCESS  read-only
        STATUS  mandatory
        DESCRIPTION
           "Tape Library Drive List

            This is a data structure containing the list of tape drive ids
            that are present in this library.  The format is:

              ULONG   Controller Number
              BYTE    Bus Number
              BYTE    SCSI ID
              BYTE    Logical Unit Number

            There will be 1 structure for each drive present in the library."

        ::= { cpqTapeLibraryEntry 18 }


-- ****************************************************************************
--    SAS Host Bus Adapter Group
--    ==========================
--
-- The compaq enterprise               (1.3.6.1.4.1.232)
--      cpqSas Group                   (1.3.6.1.4.1.232.5)
--       cpqSasComponent Group         (1.3.6.1.4.1.232.5.5)
--        cpqSasHba Group              (1.3.6.1.4.1.232.5.5.1)
--         cpqSasHbaTable              (1.3.6.1.4.1.232.5.5.1.1)
--
--
--  The SAS host bus adapter group contains configuration and statistical
--  information for the SAS HBA.
--
--  Implementation of the SAS host bus adapter group is mandatory for all
--  agents that support the SCSI MIB.
--
-- ****************************************************************************

    cpqSasHbaTable OBJECT-TYPE
        SYNTAX  SEQUENCE OF CpqSasHbaEntry
        ACCESS  not-accessible
        STATUS  mandatory
        DESCRIPTION
           "SAS Host Bus Adapter Table."
        ::= { cpqSasHba 1 }

    cpqSasHbaEntry OBJECT-TYPE
        SYNTAX  CpqSasHbaEntry
        ACCESS  not-accessible
        STATUS  mandatory
        DESCRIPTION
           "SAS Controller Table Entry."
        INDEX   { cpqSasHbaIndex }
        ::= { cpqSasHbaTable 1 }

        CpqSasHbaEntry ::= SEQUENCE
        {
              cpqSasHbaIndex              INTEGER,
              cpqSasHbaHwLocation         DisplayString,
              cpqSasHbaModel              INTEGER,
              cpqSasHbaStatus             INTEGER,
              cpqSasHbaCondition          INTEGER,
              cpqSasHbaOverallCondition   INTEGER,
              cpqSasHbaSerialNumber       DisplayString,
              cpqSasHbaFwVersion          DisplayString,
              cpqSasHbaBiosVersion        DisplayString
        }

    cpqSasHbaIndex OBJECT-TYPE
        SYNTAX  INTEGER
        ACCESS  read-only
        STATUS  mandatory
        DESCRIPTION
           "SAS Host Bus Adapter Index.

            The HBA index indicates to which SAS adapter instance this table
            entry belongs."
        ::= { cpqSasHbaEntry 1 }

    cpqSasHbaHwLocation OBJECT-TYPE
        SYNTAX  DisplayString (SIZE (0..255))
        ACCESS  read-only
        STATUS  optional
        DESCRIPTION
           "SAS Host Bus Adapter Hardware Location.

            A text description of the hardware location of the HBA.
            A NULL string indicates that the hardware location could not
            be determined or is irrelevant."
        ::= { cpqSasHbaEntry 2 }

    cpqSasHbaModel OBJECT-TYPE
        SYNTAX  INTEGER
        {
           other(1),
           generic(2),
           sas8int(3),
           sas4int(4),
           sasSc44Ge(5),
           sasSc40Ge(6),
           sasSc08Ge(7)
        }
        ACCESS  read-only
        STATUS  mandatory
        DESCRIPTION
           "SAS Host Bus Adapter Model.

            This is the HBA model and can be used for identification
            purposes.  The following values are defined:

            other(1)       The management agent does not recognize this model.
                           You may need to upgrade your software.
            generic(2)     SAS HBA
            sas8int(3)     HP 8 Internal Port SAS HBA with RAID
            sas4int(4)     HP 4 Internal Port SAS HBA with RAID
            sasSc44Ge(5)   HP SC44Ge Host Bus Adapter
            sasSc40Ge(6)   HP SC40Ge HBA
            sasSc08Ge(7)   HP SC08Ge Host Bus Adapter"
        ::= { cpqSasHbaEntry 3 }

    cpqSasHbaStatus OBJECT-TYPE
        SYNTAX  INTEGER
        {
           other(1),
           ok(2),
           failed(3)
        }
        ACCESS  read-only
        STATUS  mandatory
        DESCRIPTION
           "SAS Host Bus Adapter Status.

            This is the current status of the HBA. The following values are
            currently defined:

            other(1)
              The management agent does not recognize the status as one of
              those listed below.

            ok(2)
              The HBA is operating normally.

            failed(3)
              The HBA has failed and is no longer operating."
        ::= { cpqSasHbaEntry 4 }

    cpqSasHbaCondition OBJECT-TYPE
        SYNTAX  INTEGER
        {
           other(1),
           ok(2),
           degraded(3),
           failed(4)
        }
        ACCESS  read-only
        STATUS  mandatory
        DESCRIPTION
           "SAS Host Bus Adapter Condition.

            This is the condition of the HBA hardware."
       ::= { cpqSasHbaEntry 5 }

    cpqSasHbaOverallCondition OBJECT-TYPE
        SYNTAX  INTEGER
        {
           other(1),
           ok(2),
           degraded(3),
           failed(4)
        }
        ACCESS  read-only
        STATUS  mandatory
        DESCRIPTION
           "SAS Host Bus Adapter Overall Condition.

            This is the overall condition of the HBA and all of the logical
            drives and physical drives controlled by it."
       ::= { cpqSasHbaEntry 6 }

    cpqSasHbaSerialNumber OBJECT-TYPE
        SYNTAX  DisplayString (SIZE (0..80))
        ACCESS  read-only
        STATUS  mandatory
        DESCRIPTION
           "SAS Host Bus Adapter Serial Number.

            This is the serial number assigned to the HBA.  This can be used
            for identification purposes.  This field will be a null (size 0)
            string if the management agent cannot provide the serial number."
        ::= { cpqSasHbaEntry 7 }

    cpqSasHbaFwVersion OBJECT-TYPE
        SYNTAX  DisplayString
        ACCESS  read-only
        STATUS  mandatory
        DESCRIPTION
           "SAS Host Bus Adapter Firmware Version.

            This is the version of the firmware on the SAS HBA.
            This field will be a null (size 0) string if the management
            agent cannot provide the BIOS version."
        ::= { cpqSasHbaEntry 8 }

    cpqSasHbaBiosVersion OBJECT-TYPE
        SYNTAX  DisplayString
        ACCESS  read-only
        STATUS  mandatory
        DESCRIPTION
           "SAS Host Bus Adapter BIOS Version.

            This is the version of the BIOS on the SAS HBA.
            This field will be a null (size 0) string if the management
            agent cannot provide the BIOS version."
        ::= { cpqSasHbaEntry 9 }


-- ****************************************************************************
--    SAS Physical Drive Group
--    ========================
--
-- The compaq enterprise               (1.3.6.1.4.1.232)
--      cpqSas Group                   (1.3.6.1.4.1.232.5)
--       cpqSasComponent Group         (1.3.6.1.4.1.232.5.5)
--        cpqSasPhyDrv Group           (1.3.6.1.4.1.232.5.5.2)
--         cpqSasPhyDrvTable           (1.3.6.1.4.1.232.5.5.2.1)
--
--
--  The SAS physical drive group contains configuration and statistical
--  information for physical drives attached to a SAS HBA.
--
--  Implementation of the SAS physical drive group is mandatory for all
--  agents that support the SCSI MIB.
--
-- ****************************************************************************

    cpqSasPhyDrvTable OBJECT-TYPE
        SYNTAX  SEQUENCE OF CpqSasPhyDrvEntry
        ACCESS  not-accessible
        STATUS  mandatory
        DESCRIPTION
           "SAS Physical Drive Table."
        ::= { cpqSasPhyDrv 1 }

    cpqSasPhyDrvEntry OBJECT-TYPE
        SYNTAX  CpqSasPhyDrvEntry
        ACCESS  not-accessible
        STATUS  mandatory
        DESCRIPTION
           "SAS Physical Drive Entry."
        INDEX   { cpqSasPhyDrvHbaIndex, cpqSasPhyDrvIndex }
        ::= { cpqSasPhyDrvTable 1 }

        CpqSasPhyDrvEntry ::= SEQUENCE
        {
              cpqSasPhyDrvHbaIndex              INTEGER,
              cpqSasPhyDrvIndex                 INTEGER,
              cpqSasPhyDrvLocationString        DisplayString,
              cpqSasPhyDrvModel                 DisplayString,
              cpqSasPhyDrvStatus                INTEGER,
              cpqSasPhyDrvCondition             INTEGER,
              cpqSasPhyDrvFWRev                 DisplayString,
              cpqSasPhyDrvSize                  INTEGER,
              cpqSasPhyDrvUsedReallocs          Counter,
              cpqSasPhyDrvSerialNumber          DisplayString,
              cpqSasPhyDrvMemberLogDrv          INTEGER,
              cpqSasPhyDrvRotationalSpeed       INTEGER,
              cpqSasPhyDrvOsName                DisplayString,
              cpqSasPhyDrvPlacement             INTEGER,
              cpqSasPhyDrvHotPlug               INTEGER,
              cpqSasPhyDrvType                  INTEGER,
              cpqSasPhyDrvSasAddress            DisplayString
        }

    cpqSasPhyDrvHbaIndex OBJECT-TYPE
        SYNTAX  INTEGER
        ACCESS  read-only
        STATUS  mandatory
        DESCRIPTION
           "SAS Physical Drive HBA Index.

            The HBA index indicates to which SAS adapter instance this table
            entry belongs."
        ::= { cpqSasPhyDrvEntry 1 }

    cpqSasPhyDrvIndex OBJECT-TYPE
        SYNTAX  INTEGER
        ACCESS  read-only
        STATUS  mandatory
        DESCRIPTION
           "SAS Physical Drive Index.

            The physical drive index indicates to which physical drive
            instance this table entry belongs."
        ::= { cpqSasPhyDrvEntry 2 }

     cpqSasPhyDrvLocationString OBJECT-TYPE
        SYNTAX  DisplayString (SIZE (0..255))
        ACCESS  read-only
        STATUS  mandatory
        DESCRIPTION
           "SAS Physical Drive Location String.

            This string describes the location of the drive in relation to
            the HBA.  If the location string cannot be determined, the agent
            will return a NULL string."
        ::= { cpqSasPhyDrvEntry 3 }

    cpqSasPhyDrvModel OBJECT-TYPE
        SYNTAX  DisplayString (SIZE (0..40))
        ACCESS  read-only
        STATUS  mandatory
        DESCRIPTION
           "SAS Physical Drive Model.

            This is a physical drive's model name.  It can be used for
            identification purposes."
        ::= { cpqSasPhyDrvEntry 4 }

    cpqSasPhyDrvStatus OBJECT-TYPE
        SYNTAX  INTEGER
        {
           other(1),
           ok(2),
           predictiveFailure(3),
           offline(4),
           failed(5),
           missingWasOk(6),
           missingWasPredictiveFailure(7),
           missingWasOffline(8),
           missingWasFailed(9)
        }
        ACCESS  read-only
        STATUS  mandatory
        DESCRIPTION
           "SAS Physical Drive Status.

            The physical drive can be in one of the following states:

            other(1)
              The drive is in a state other than one of those listed
              below.

            ok(2)
              Indicates that the physical drive is in normal operation mode.
              No user action is necessary.

            predictiveFailure(3)
              Indicates that the physical drive has exceeded a threshold
              value for one of it's predictive indicators.

            offline(4)
              Indicates that the physical drive is offline and can no longer
              return data.  No further status is available.

            failed(5)
              Indicates that the physical drive has failed and can no longer
              return data.

            missingWasOk(6)
              Indicates that a physical drive had a status of ok(2) and is
              no longer present.  The drive has been removed.

            missingWasPredictiveFailure(7)
              Indicates that a physical drive had a status of
              predictiveFailure(3) and is no longer present.  The drive has
              been removed.

            missingWasOffline(8)
              Indicates that a physical drive had a status of offline(4) and
              is no longer present.  The drive has been removed.

            missingWasFailed(9)
              Indicates that a physical drive had a status of failed(5) and
              is no longer present.  The drive has been removed."
       ::= { cpqSasPhyDrvEntry 5 }

    cpqSasPhyDrvCondition OBJECT-TYPE
        SYNTAX  INTEGER
        {
           other(1),
           ok(2),
           degraded(3),
           failed(4)
        }
        ACCESS  read-only
        STATUS  mandatory
        DESCRIPTION
           "SAS Physical Drive Condition.

            This is the overall condition of the physical drive.
            The following values are defined:

            other(1)
              The agent does not recognize the status.  You may need
              to upgrade your software.

            ok(2)
              The physical drive is operating normally.  No user action
              is required.

            degraded(3)
              The physical drive is degraded.

            failed(4)
              The physical drives has failed."
       ::= { cpqSasPhyDrvEntry 6 }

    cpqSasPhyDrvFWRev OBJECT-TYPE
        SYNTAX  DisplayString (SIZE (0..8))
        ACCESS  read-only
        STATUS  mandatory
        DESCRIPTION
           "SAS Physical Drive Firmware Revision.

            This is the firmware revision of the physical drive."
        ::= { cpqSasPhyDrvEntry 7 }

    cpqSasPhyDrvSize OBJECT-TYPE
        SYNTAX  INTEGER (0..2147483647)
        ACCESS  read-only
        STATUS  mandatory
        DESCRIPTION
           "SAS Physical Drive Size in MB.

            This is the size of the physical drive in megabytes.
            This value is calculated using the value 1,048,576 (2^20) as
            a megabyte.  Drive manufacturers sometimes use the number
            1,000,000 as a megabyte when giving drive capacities so this
            value may differ from the advertised size of a drive."
        ::= { cpqSasPhyDrvEntry 8 }

    cpqSasPhyDrvUsedReallocs OBJECT-TYPE
        SYNTAX  Counter
        ACCESS  read-only
        STATUS  mandatory
        DESCRIPTION
           "SAS Physical Drive Used Reallocation Sectors.

            This shows the number of sectors of the reallocation area that
            have been used by the physical drive over the life of the drive."
        ::= { cpqSasPhyDrvEntry 9 }

    cpqSasPhyDrvSerialNumber OBJECT-TYPE
        SYNTAX  DisplayString (SIZE (0..40))
        ACCESS  read-only
        STATUS  mandatory
        DESCRIPTION
           "SAS Physical Drive Serial Number.

            This is the serial number assigned to the physical drive."
        ::= { cpqSasPhyDrvEntry 10 }

    cpqSasPhyDrvMemberLogDrv OBJECT-TYPE
        SYNTAX  INTEGER
        {
           other(1),
           member(2),
           spare(3),
           nonMember(4)
        }
        ACCESS  read-only
        STATUS  mandatory
        DESCRIPTION
           "The Physical Drive is a Member of a Logical Drive.

            This is an indication of whether the physical drive is
            a member of a logical drive.

            This variable can be in one of the following states:

            other(1)
              The agent is unable to determine if the physical drive is a
              member of a logical drive.

            member(2)
              The physical drive is a member of a logical drive.

            spare(2)
              The physical drive is a spare drive for a logical drive.

            nonMember(4)
              The physical drive is not a logical drive member or spare."
        ::= { cpqSasPhyDrvEntry 11 }

    cpqSasPhyDrvRotationalSpeed OBJECT-TYPE
        SYNTAX  INTEGER
        {
           other(1),
           rpm7200(2),
           rpm10K(3),
           rpm15K(4)
        }
        ACCESS  read-only
        STATUS  mandatory
        DESCRIPTION
           "SAS Physical Drive Rotational Speed.

            The following values are defined:

            other(1)
              The agent is unable to determine the rotational speed for
              this drive.

           rpm7200(2)
             The rotational speed for this drive is 7200 rpm.

           rpm10K(3)
             The rotational speed for this drive is 10000 rpm.

           rpm15K(4)
             The rotational speed for this drive is 15000 rpm."
       ::= { cpqSasPhyDrvEntry 12 }

    cpqSasPhyDrvOsName OBJECT-TYPE
        SYNTAX  DisplayString (SIZE (0..255))
        ACCESS  read-only
        STATUS  mandatory
        DESCRIPTION
            "SAS Physical Drive OS Name.

            The OS name for this SAS physical drive.  This field will be
            a null (size 0) string if the agent does not support OS name."
        ::= { cpqSasPhyDrvEntry 13 }

    cpqSasPhyDrvPlacement OBJECT-TYPE
        SYNTAX  INTEGER
        {
           other(1),
           internal(2),
           external(3)
        }
        ACCESS  read-only
        STATUS  mandatory
        DESCRIPTION
           "SAS Physical Drive Placement.

            The following values are defined:

            other(1)
              The agent is unable to determine if the drive is internal or
              external.

            internal(2)
              The drive is located in an internal system chassis.

            external(3)
              The drive is located in an external storage system."
        ::= { cpqSasPhyDrvEntry 14 }

    cpqSasPhyDrvHotPlug OBJECT-TYPE
        SYNTAX  INTEGER
        {
           other(1),
           hotPlug(2),
           nonHotPlug(3)
        }
        ACCESS  read-only
        STATUS  mandatory
        DESCRIPTION
           "SAS Physical Drive Hot Plug Support Status.

            The following values are defined:

            other(1)
              The agent is unable to determine if this drive
              supports hot plug replacement.

            hotPlug(2)
              The drive supports hot plug replacement.

            nonhotPlug(3)
              The drive does not support hot plug replacement."
        ::= { cpqSasPhyDrvEntry 15 }

    cpqSasPhyDrvType OBJECT-TYPE
        SYNTAX  INTEGER
        {
           other(1),
           sas(2),
           sata(3)
        }
        ACCESS  read-only
        STATUS  mandatory
        DESCRIPTION
           "SAS Physical Drive Type.

            The following values are defined:

            other(1)
              The agent is unable to determine the type for this drive.

            sas(2)
              The drive type is Serial Attached SCSI.

            sata(3)
              The drive type is Serial ATA."
        ::= { cpqSasPhyDrvEntry 16 }

    cpqSasPhyDrvSasAddress OBJECT-TYPE
        SYNTAX  DisplayString (SIZE (0..16))
        ACCESS  read-only
        STATUS  mandatory
        DESCRIPTION
            "SAS Physical Drive SAS Address.

            The SAS address this SAS physical drive.  A null (size 0) string
            will be returned if the value cannot be determined."
        ::= { cpqSasPhyDrvEntry 17 }


-- ****************************************************************************
--    SAS Logical Drive Group
--    =======================
--
-- The compaq enterprise               (1.3.6.1.4.1.232)
--      cpqSas Group                   (1.3.6.1.4.1.232.5)
--       cpqSasComponent Group         (1.3.6.1.4.1.232.5.5)
--        cpqSasLogDrv Group           (1.3.6.1.4.1.232.5.5.3)
--         cpqSasLogDrvTable           (1.3.6.1.4.1.232.5.5.3.1)
--
--
--  The SAS logical drive group contains configuration and statistical
--  information for logical drives on a SAS HBA.
--
--  Implementation of the SAS logical drive group is mandatory for all
--  agents that support the SCSI MIB.
--
-- ****************************************************************************

    cpqSasLogDrvTable OBJECT-TYPE
        SYNTAX  SEQUENCE OF CpqSasLogDrvEntry
        ACCESS  not-accessible
        STATUS  mandatory
        DESCRIPTION
           "SAS Logical Drive Table."
        ::= { cpqSasLogDrv 1 }

    cpqSasLogDrvEntry OBJECT-TYPE
        SYNTAX  CpqSasLogDrvEntry
        ACCESS  not-accessible
        STATUS  mandatory
        DESCRIPTION
           "SAS Logical Drive Entry."
        INDEX   { cpqSasLogDrvHbaIndex, cpqSasLogDrvIndex }
        ::= { cpqSasLogDrvTable 1 }

        CpqSasLogDrvEntry ::= SEQUENCE
        {
              cpqSasLogDrvHbaIndex          INTEGER,
              cpqSasLogDrvIndex             INTEGER,
              cpqSasLogDrvRaidLevel         INTEGER,
              cpqSasLogDrvStatus            INTEGER,
              cpqSasLogDrvCondition         INTEGER,
              cpqSasLogDrvRebuildingDisk    INTEGER,
              cpqSasLogDrvCapacity          INTEGER,
              cpqSasLogDrvStripeSize        INTEGER,
              cpqSasLogDrvPhyDrvIds         OCTET STRING,
              cpqSasLogDrvSpareIds          OCTET STRING,
              cpqSasLogDrvOsName            DisplayString,
              cpqSasLogDrvRebuildingPercent Gauge
        }

    cpqSasLogDrvHbaIndex OBJECT-TYPE
        SYNTAX  INTEGER
        ACCESS  read-only
        STATUS  mandatory
        DESCRIPTION
           "SAS Logical Drive HBA Index.

            The controller index indicates to which SAS adapter instance
            this table entry belongs."
        ::= { cpqSasLogDrvEntry 1 }

    cpqSasLogDrvIndex OBJECT-TYPE
        SYNTAX  INTEGER
        ACCESS  read-only
        STATUS  mandatory
        DESCRIPTION
           "SAS Logical Drive Index.

            The logical drive index indicates to which logical drive instance
            this table entry belongs."
        ::= { cpqSasLogDrvEntry 2 }

    cpqSasLogDrvRaidLevel OBJECT-TYPE
        SYNTAX  INTEGER
        {
           other(1),
           raid0(2),
           raid1(3),
           raid0plus1(4),
           raid5(5),
           raid15(6),
           volume(7)
        }
        ACCESS  read-only
        STATUS  mandatory
        DESCRIPTION
           "SAS Logical Drive RAID Level.

            The following RAID levels are defined:

            other(1)
             The agent cannot determine the RAID level of this logical drive.

            raid0(2)
             The logical drive is configured with RAID level 0.

            raid1(3)
             The logical drive is configured with RAID level 1."
        ::= { cpqSasLogDrvEntry 3 }

    cpqSasLogDrvStatus OBJECT-TYPE
        SYNTAX  INTEGER
        {
           other(1),
           ok(2),
           degraded(3),
           rebuilding(4),
           failed(5),
           offline(6)
        }
        ACCESS  read-only
        STATUS  mandatory
        DESCRIPTION
           "SAS Logical Drive Status.

            The logical drive can be in one of the following states:

            other(1)
              The management agent does not recognize the status.
              You may need to upgrade your software.

            ok(2)
              Indicates that the logical drive is in normal operation mode.
              No user action is required.

            degraded(3)
              Indicates that the logical drive is in a degraded state.

            rebuilding(4)
              Indicates that the logical drive is currently resynchronizing
              the data accross the physical drives in the logical drive.

            failed(5)
              Indicates that more physical drives have failed than the
              fault tolerance mode of the logical drive can handle without
              data loss.

            offline(6)
              Indicates that the logical drive is offline from the operating
              system.  User action may be required to bring the logical
              drive online."
        ::= { cpqSasLogDrvEntry 4 }

    cpqSasLogDrvCondition OBJECT-TYPE
        SYNTAX  INTEGER
        {
           other(1),
           ok(2),
           degraded(3),
           failed(4)
        }
        ACCESS  read-only
        STATUS  mandatory
        DESCRIPTION
           "SAS Logical Drive Condition.

            This is the condition of the logical drive."
       ::= { cpqSasLogDrvEntry 5 }

    cpqSasLogDrvRebuildingDisk OBJECT-TYPE
        SYNTAX  INTEGER
        ACCESS  read-only
        STATUS  mandatory
        DESCRIPTION
            "SAS Logical Drive Rebuilding Disk.

            This is the disk that is in the process of rebuilding.  If no
            drive is currently rebuilding, a value of -1 will be returned."
        ::= { cpqSasLogDrvEntry 6 }

    cpqSasLogDrvCapacity OBJECT-TYPE
        SYNTAX  INTEGER (0..2147483647)
        ACCESS  read-only
        STATUS  mandatory
        DESCRIPTION
           "SAS Logical Drive Size.

            This is the capacity of the logical drive in megabytes.
            This value is calculated using the value 1,048,576 (2^20) as
            a megabyte.  Drive manufacturers sometimes use the
            number 1,000,000 as a megabyte when giving drive capacities
            so this value may differ from the advertised size of a drive."
        ::= { cpqSasLogDrvEntry 7 }

    cpqSasLogDrvStripeSize OBJECT-TYPE
        SYNTAX  INTEGER
        ACCESS  read-only
        STATUS  mandatory
        DESCRIPTION
            "SAS Logical Drive Stripe Size.

            This is the size of a logical drive stripe in kilobytes."
        ::= { cpqSasLogDrvEntry 8 }

    cpqSasLogDrvPhyDrvIds OBJECT-TYPE
        SYNTAX  OCTET STRING (SIZE (0..64))
        ACCESS  read-only
        STATUS  mandatory
        DESCRIPTION
           "SAS Logical Drive Physical Drive IDs.

            This lists the physical drive ID's associated with this logical
            drive.  Each 4 octets of the string can be used as an index
            (cpqSasPhyDrvIndex) into the SAS physical drive table.  These 4
            octets are repeated for each drive in the list.  For n disk
            drives in the list, the string is 4 * n octets long."
        ::= { cpqSasLogDrvEntry 9 }

     cpqSasLogDrvSpareIds OBJECT-TYPE
        SYNTAX  OCTET STRING (SIZE (0..64))
        ACCESS  read-only
        STATUS  mandatory
        DESCRIPTION
            "SAS Logical Drive Spare Drive IDs.

            This lists the spare drive ID's associated with this logical
            drive.  Each 4 octets of the string can be used as an index
            (cpqSasPhyDrvIndex) into the SAS physical drive table.  These 4
            octets are repeated for each drive in the list.  For n disk
            drives in the list, the string is 4 * n octets long."
        ::= { cpqSasLogDrvEntry 10 }

     cpqSasLogDrvOsName OBJECT-TYPE
        SYNTAX  DisplayString (SIZE (0..255))
        ACCESS  read-only
        STATUS  mandatory
        DESCRIPTION
            "SAS Logical Drive OS Name.

            This is the OS name for the logical drive.  This field will be
            a null (size 0) string if the agent does not support OS name."
        ::= { cpqSasLogDrvEntry 11 }

     cpqSasLogDrvRebuildingPercent OBJECT-TYPE
        SYNTAX  Gauge
        ACCESS  read-only
        STATUS  mandatory
        DESCRIPTION
            "Logical Drive Percent Rebuild.

            After a failed physical drive has been replaced, the physical
            drive must have its data rebuilt.  This value is the percent
            complete of the rebuild.  When the value reaches 100, the
            rebuilding process is complete.  The array continues to
            operate in interim recovery mode while the disk is rebuilding.

            This value is only valid if the Logical Drive Status is
            rebuilding(4).

            If the value cannot be determined or a rebuild is not active,
            the value is set to 4,294,967,295."
        ::= { cpqSasLogDrvEntry 12 }


-- ****************************************************************************
--    SAS Tape Drive Group
--    ====================
--
-- The compaq enterprise               (1.3.6.1.4.1.232)
--      cpqSas Group                   (1.3.6.1.4.1.232.5)
--       cpqSasComponent Group         (1.3.6.1.4.1.232.5.5)
--        cpqSasTapeDrv Group          (1.3.6.1.4.1.232.5.5.4)
--         cpqSasTapeDrvTable          (1.3.6.1.4.1.232.5.5.4.1)
--
--
--  The SAS tape drive group contains configuration and statistical
--  information for tape drives attached to a SAS HBA.
--
--  Implementation of the SAS tape drive group is mandatory for all
--  agents that support the SCSI MIB.
--
-- ****************************************************************************

    cpqSasTapeDrvTable OBJECT-TYPE
        SYNTAX  SEQUENCE OF CpqSasTapeDrvEntry
        ACCESS  not-accessible
        STATUS  mandatory
        DESCRIPTION
           "SAS Physical Drive Table."
        ::= { cpqSasTapeDrv 1 }

    cpqSasTapeDrvEntry OBJECT-TYPE
        SYNTAX  CpqSasTapeDrvEntry
        ACCESS  not-accessible
        STATUS  mandatory
        DESCRIPTION
           "SAS Physical Drive Entry."
        INDEX   { cpqSasTapeDrvHbaIndex, cpqSasTapeDrvIndex }
        ::= { cpqSasTapeDrvTable 1 }

        CpqSasTapeDrvEntry ::= SEQUENCE
        {
              cpqSasTapeDrvHbaIndex             INTEGER,
              cpqSasTapeDrvIndex                INTEGER,
              cpqSasTapeDrvLocationString       DisplayString,
              cpqSasTapeDrvName                 DisplayString,
              cpqSasTapeDrvStatus               INTEGER,
              cpqSasTapeDrvCondition            INTEGER,
              cpqSasTapeDrvFWRev                DisplayString,
              cpqSasTapeDrvSerialNumber         DisplayString,
              cpqSasTapeDrvSasAddress           DisplayString
        }

    cpqSasTapeDrvHbaIndex OBJECT-TYPE
        SYNTAX  INTEGER
        ACCESS  read-only
        STATUS  mandatory
        DESCRIPTION
           "SAS Tape Drive HBA Index.

            The HBA index indicates to which SAS adapter instance this table
            entry belongs."
        ::= { cpqSasTapeDrvEntry 1 }

    cpqSasTapeDrvIndex OBJECT-TYPE
        SYNTAX  INTEGER
        ACCESS  read-only
        STATUS  mandatory
        DESCRIPTION
           "SAS Tape Drive Index.

            The tape drive index indicates to which tape drive instance
            this table entry belongs."
        ::= { cpqSasTapeDrvEntry 2 }

     cpqSasTapeDrvLocationString OBJECT-TYPE
        SYNTAX  DisplayString (SIZE (0..255))
        ACCESS  read-only
        STATUS  mandatory
        DESCRIPTION
           "SAS Tape Drive Location String.

            This string describes the location of the drive in relation to
            the HBA.  If the location string cannot be determined, the agent
            will return a NULL string."
        ::= { cpqSasTapeDrvEntry 3 }

    cpqSasTapeDrvName OBJECT-TYPE
        SYNTAX  DisplayString (SIZE (0..40))
        ACCESS  read-only
        STATUS  mandatory
        DESCRIPTION
           "SAS Tape Drive Name.

            This is a combination of the vendor ID and the product ID as
            returned by the SCSI inquiry command.  This can be used for
            identification purposes."
        ::= { cpqSasTapeDrvEntry 4 }

    cpqSasTapeDrvStatus OBJECT-TYPE
        SYNTAX  INTEGER
        {
           other(1),
           ok(2),
           offline(3)
        }
        ACCESS  read-only
        STATUS  mandatory
        DESCRIPTION
           "SAS Physical Drive Status.

            The physical drive can be in one of the following states:

            other(1)
              The tape drive is in a state other than one of those listed
              below.

            ok(2)
              Indicates that the tape drive is in normal operation mode.
              No user action is necessary.

            offline(3)
              Indicates that the tape drive is offline and can no longer
              return data.  No further status is available."
       ::= { cpqSasTapeDrvEntry 5 }

    cpqSasTapeDrvCondition OBJECT-TYPE
        SYNTAX  INTEGER
        {
           other(1),
           ok(2),
           degraded(3),
           failed(4)
        }
        ACCESS  read-only
        STATUS  mandatory
        DESCRIPTION
           "SAS Tape Drive Condition.

            This is the overall condition of the tape drive.
            The following values are defined:

            other(1)
              The agent does not recognize the status.  You may need
              to upgrade your software.

            ok(2)
              The tape drive is operating normally.  No user action is
              required.

            degraded(3)
              The tape drive is degraded.

            failed(4)
              The tape drives has failed."
       ::= { cpqSasTapeDrvEntry 6 }

    cpqSasTapeDrvFWRev OBJECT-TYPE
        SYNTAX  DisplayString (SIZE (0..8))
        ACCESS  read-only
        STATUS  mandatory
        DESCRIPTION
           "SAS Tape Drive Firmware Revision.

            This is the firmware revision of the tape drive."
        ::= { cpqSasTapeDrvEntry 7 }

    cpqSasTapeDrvSerialNumber OBJECT-TYPE
        SYNTAX  DisplayString (SIZE (0..40))
        ACCESS  read-only
        STATUS  mandatory
        DESCRIPTION
           "SAS Tape Drive Serial Number.

            This is the serial number assigned to the tape drive."
        ::= { cpqSasTapeDrvEntry 8 }

    cpqSasTapeDrvSasAddress OBJECT-TYPE
        SYNTAX  DisplayString (SIZE (0..16))
        ACCESS  read-only
        STATUS  mandatory
        DESCRIPTION
            "SAS Tape Drive SAS Address.

            The SAS address of this SAS tape drive.  A null (size 0) string
            will be returned if the value cannot be determined."
        ::= { cpqSasTapeDrvEntry 9 }


-- ****************************************************************************
--  SCSI Trap Definitions
--  ======================
--
--  The SNMP trap messages must not be bigger than 484 octets (bytes).
--
--  Trap support in an SNMP agent implementation is optional.  An SNMP
--  agent implementation may support all, some, or none of the traps.
--  If traps are supported, The user should be provided with the option of
--  disabling traps.
--
-- **************************************************************************

    cpqScsiCntlrStatusChange TRAP-TYPE
        ENTERPRISE cpqScsi
        VARIABLES  { cpqScsiCntlrStatus }
        DESCRIPTION
           "SCSI Controller Status Change.

            The agent has detected a change in the controller
            status of a SCSI Controller.  The variable
            cpqScsiCntlrStatus indicates the current controller status."

              --#TYPE "SCSI Controller Status Change (1)"
              --#SUMMARY "Status is now %d."
              --#ARGUMENTS {0}
              --#SEVERITY CRITICAL
              --#TIMEINDEX 99

        ::= 1

    cpqScsiLogDrvStatusChange TRAP-TYPE
        ENTERPRISE cpqScsi
        VARIABLES  { cpqScsiLogDrvStatus }
        DESCRIPTION
           "Logical Drive Status Change.

            The agent has detected a change in the Logical Drive
            Status of a SCSI logical drive.  The current logical
            drive status is indicated by the cpqScsiLogDrvStatus variable."

              --#TYPE "SCSI Logical Drive Status Change (2)"
              --#SUMMARY "Status is now %d."
              --#ARGUMENTS {0}
              --#SEVERITY CRITICAL
              --#TIMEINDEX 99

        ::= 2

    cpqScsiPhyDrvStatusChange TRAP-TYPE
        ENTERPRISE cpqScsi
        VARIABLES  { cpqScsiPhyDrvStatus }
        DESCRIPTION
           "Physical Drive Status Change.

            The agent has detected a change in the status of a
            SCSI physical drive.  The current physical drive
            status is indicated in the cpqScsiPhyDrvStatus variable."

              --#TYPE "SCSI Physical Drive Status Change (3)"
              --#SUMMARY "Status is now %d."
              --#ARGUMENTS {0}
              --#SEVERITY CRITICAL
              --#TIMEINDEX 99

        ::= 3

    cpqScsi2CntlrStatusChange TRAP-TYPE
        ENTERPRISE compaq
        VARIABLES  { cpqScsiCntlrStatus }
        DESCRIPTION
           "SCSI Controller Status Change.

            The agent has detected a change in the controller
            status of a SCSI Controller.  The variable
            cpqScsiCntlrStatus indicates the current controller status."

              --#TYPE "SCSI Controller Status Change (5001)"
              --#SUMMARY "Status is now %d."
              --#ARGUMENTS {0}
              --#SEVERITY CRITICAL
              --#TIMEINDEX 99

        ::= 5001

    cpqScsi2LogDrvStatusChange TRAP-TYPE
        ENTERPRISE compaq
        VARIABLES  { cpqScsiLogDrvStatus }
        DESCRIPTION
           "Logical Drive Status Change.

            The agent has detected a change in the Logical Drive
            Status of a SCSI logical drive.  The current logical
            drive status is indicated by the cpqScsiLogDrvStatus variable."

              --#TYPE "SCSI Logical Drive Status Change (5002)"
              --#SUMMARY "Status is now %d."
              --#ARGUMENTS {0}
              --#SEVERITY CRITICAL
              --#TIMEINDEX 99

        ::= 5002

    cpqScsi2PhyDrvStatusChange TRAP-TYPE
        ENTERPRISE compaq
        VARIABLES  { cpqScsiPhyDrvStatus }
        DESCRIPTION
           "Physical Drive Status Change.

            The agent has detected a change in the status of a
            SCSI physical drive.  The current physical drive
            status is indicated in the cpqScsiPhyDrvStatus variable."

              --#TYPE "SCSI Physical Drive Status Change (5003)"
              --#SUMMARY "Status is now %d."
              --#ARGUMENTS {0}
              --#SEVERITY CRITICAL
              --#TIMEINDEX 99

         ::= 5003

    cpqTapePhyDrvStatusChange TRAP-TYPE
        ENTERPRISE compaq
        VARIABLES  { cpqTapePhyDrvCondition }
        DESCRIPTION
           "Tape Drive Status Change.

            The agent has detected a change in the status of a
            Tape drive.  The current physical drive status is
            indicated in the cpqTapePhyDrvCondition variable."

              --#TYPE "Tape Drive Status Change (5004)"
              --#SUMMARY "Status is now %d."
              --#ARGUMENTS {0}
              --#SEVERITY CRITICAL
              --#TIMEINDEX 99

         ::= 5004


    cpqScsi3CntlrStatusChange TRAP-TYPE
        ENTERPRISE compaq
        VARIABLES  { sysName, cpqHoTrapFlags, cpqScsiCntlrStatus }
        DESCRIPTION
           "SCSI Controller Status Change.

            The agent has detected a change in the controller
            status of a SCSI Controller.  The variable
            cpqScsiCntlrStatus indicates the current controller status."

              --#TYPE "SCSI Controller Status Change (5005)"
              --#SUMMARY "Status is now %d."
              --#ARGUMENTS {2}
              --#SEVERITY CRITICAL
              --#TIMEINDEX 99
              --#VARBINDSEVERITY 2

        ::= 5005

    cpqScsi3PhyDrvStatusChange TRAP-TYPE
        ENTERPRISE compaq
        VARIABLES  { sysName, cpqHoTrapFlags, cpqScsiPhyDrvStatus }
        DESCRIPTION
           "Physical Drive Status Change.

            The agent has detected a change in the status of a
            SCSI physical drive.  The current physical drive
            status is indicated in the cpqScsiPhyDrvStatus variable."

              --#TYPE "SCSI Physical Drive Status Change (5006)"
              --#SUMMARY "Status is now %d."
              --#ARGUMENTS {2}
              --#SEVERITY CRITICAL
              --#TIMEINDEX 99

         ::= 5006


    cpqTape3PhyDrvStatusChange TRAP-TYPE
        ENTERPRISE compaq
        VARIABLES  { sysName, cpqHoTrapFlags, cpqTapePhyDrvCondition }
        DESCRIPTION
           "Tape Drive Status Change.

            The agent has detected a change in the status of a
            Tape drive.  The current physical drive status is
            indicated in the cpqTapePhyDrvCondition variable."

              --#TYPE "Tape Drive Status Change (5007)"
              --#SUMMARY "Status is now %d."
              --#ARGUMENTS {2}
              --#SEVERITY CRITICAL
              --#TIMEINDEX 99

         ::= 5007


    cpqTape3PhyDrvCleaningRequired TRAP-TYPE
        ENTERPRISE compaq
        VARIABLES  { sysName, cpqHoTrapFlags, cpqTapePhyDrvCondition }
        DESCRIPTION
           "Tape Drive Cleaning Required trap.

            The agent has detected a tape drive that needs to have
            a cleaning tape inserted and run.  This will cause the tape drive
            heads to be cleaned."

              --#TYPE "Tape Drive Cleaning Required (5008)"
              --#SUMMARY "Status is now %d."
              --#ARGUMENTS {2}
              --#SEVERITY MAJOR
              --#TIMEINDEX 99

         ::= 5008

    cpqTape3PhyDrvCleanTapeReplace TRAP-TYPE
        ENTERPRISE compaq
        VARIABLES  { sysName, cpqHoTrapFlags, cpqTapePhyDrvCondition }
        DESCRIPTION
           "Tape Drive Cleaning Tape Needs Replacing.

            The agent has detected that an autoloader tape unit has
            a cleaning tape that has been fully used and therefore needs to
            be replaced with a new cleaning tape."

              --#TYPE "Tape Drive Cleaning Tape Needs Replacing (5009)"
              --#SUMMARY "Status is now %d."
              --#ARGUMENTS {2}
              --#SEVERITY MAJOR
              --#TIMEINDEX 99

         ::= 5009

    cpqTape3LibraryFailed TRAP-TYPE
        ENTERPRISE compaq
        VARIABLES  { sysName, cpqHoTrapFlags, cpqTapeLibrarySerialNumber }
        DESCRIPTION
           "Tape Library Error

            The agent has detected that an autoloader unit has
            an encountered an error."

              --#TYPE "Tape Library Error (5010)"
              --#SUMMARY "Tape library %s is not operational."
              --#ARGUMENTS {2}
              --#SEVERITY MAJOR
              --#TIMEINDEX 99

         ::= 5010


    cpqTape3LibraryOkay TRAP-TYPE
        ENTERPRISE compaq
        VARIABLES  { sysName, cpqHoTrapFlags, cpqTapeLibrarySerialNumber }
        DESCRIPTION
           "Tape Library Okay

            The agent has detected that an autoloader unit has
            recovered from errors."

              --#TYPE "Tape Library Okay (5011)"
              --#SUMMARY "Tape Library %s Recovered"
              --#ARGUMENTS {2}
              --#SEVERITY INFORMATIONAL
              --#TIMEINDEX 99

         ::= 5011


    cpqTape3LibraryDegraded TRAP-TYPE
        ENTERPRISE compaq
        VARIABLES  { sysName, cpqHoTrapFlags, cpqTapeLibrarySerialNumber }
        DESCRIPTION
           "Tape Library Degraded

            The agent has detected that an autoloader unit is
            in a degraded condition."

              --#TYPE "Tape Library Degraded (5012)"
              --#SUMMARY "Tape library %s is in a degraded condition."
              --#ARGUMENTS {2}
              --#SEVERITY CRITICAL
              --#TIMEINDEX 99

         ::= 5012


    cpqTape3LibraryDoorOpen TRAP-TYPE
        ENTERPRISE compaq
        VARIABLES  { sysName, cpqHoTrapFlags, cpqTapeLibrarySerialNumber }
        DESCRIPTION
           "Tape Library Door Open

            The agent has detected that the door on an autoloader
            is open so the unit is not operational."

              --#TYPE "Tape Library Door Opened (5013)"
              --#SUMMARY "Tape library %s door opened"
              --#ARGUMENTS {2}
              --#SEVERITY CRITICAL
              --#TIMEINDEX 99

         ::= 5013

    cpqTape3LibraryDoorClosed TRAP-TYPE
        ENTERPRISE compaq
        VARIABLES  { sysName, cpqHoTrapFlags, cpqTapeLibrarySerialNumber }
        DESCRIPTION
           "Tape Library Door Closed

            The agent has detected that the door on a an autoloader
            has closed."

              --#TYPE "Tape Library Door Closed (5014)"
              --#SUMMARY "Tape library %s door closed"
              --#ARGUMENTS {2}
              --#SEVERITY INFORMATIONAL
              --#TIMEINDEX 99

         ::= 5014

    cpqScsiCdLibraryStatusChange TRAP-TYPE
        ENTERPRISE compaq
        VARIABLES  { sysName, cpqHoTrapFlags, cpqCdLibraryCntlrIndex,
                     cpqCdLibraryBusIndex, cpqCdLibraryScsiIdIndex,
                     cpqCdLibraryStatus }
        DESCRIPTION
           "CD Library Status Change.

            The agent has detected a change in the status of a
            CD Library device.  The current CD Library status is
            indicated in the cpqScsiCdLibraryCondition variable."

              --#TYPE "CD Library Status Change (5015)"
              --#SUMMARY "Status is now %d."
              --#ARGUMENTS {5}
              --#SEVERITY CRITICAL
              --#TIMEINDEX 99
              --#VARBINDSEVERITY 2

         ::= 5015

    cpqTape4PhyDrvStatusChange TRAP-TYPE
        ENTERPRISE compaq
        VARIABLES  { sysName, cpqHoTrapFlags, cpqTapePhyDrvCntlrIndex,
                     cpqTapePhyDrvBusIndex, cpqTapePhyDrvScsiIdIndex,
                     cpqTapePhyDrvStatus }
        DESCRIPTION
           "Tape Drive Status Change.

            The Storage Agent has detected a change in the status of a
            Tape drive.  The current physical drive status is
            indicated in the cpqTapePhyDrvStatus variable."

              --#TYPE "Tape Drive Status Change (5016)"
              --#SUMMARY "Status is now %d."
              --#ARGUMENTS {5}
              --#SEVERITY CRITICAL
              --#TIMEINDEX 99

         ::= 5016


    cpqScsi4PhyDrvStatusChange TRAP-TYPE
        ENTERPRISE compaq
        VARIABLES  { sysName, cpqHoTrapFlags, cpqScsiPhyDrvStatus,
                     cpqScsiPhyDrvCntlrIndex, cpqScsiPhyDrvBusIndex,
                     cpqScsiPhyDrvIndex, cpqScsiPhyDrvVendor,
                     cpqScsiPhyDrvModel, cpqScsiPhyDrvFWRev,
                     cpqScsiPhyDrvSerialNum }
        DESCRIPTION
           "Physical Drive Status Change.

            The Storage Agent has detected a change in the status of a
            SCSI physical drive.  The current physical drive
            status is indicated in the cpqScsiPhyDrvStatus variable."

              --#TYPE "SCSI Physical Drive Status Change (5017)"
              --#SUMMARY "Status is now %d."
              --#ARGUMENTS {2}
              --#SEVERITY CRITICAL
              --#TIMEINDEX 99

         ::= 5017


    cpqTapeLibraryStatusChange TRAP-TYPE
        ENTERPRISE compaq
        VARIABLES  { sysName, cpqHoTrapFlags, cpqTapeLibraryCntlrIndex,
                     cpqTapeLibraryBusIndex, cpqTapeLibraryScsiIdIndex,
                     cpqTapeLibraryLunIndex, cpqTapeLibraryName,
                     cpqTapeLibraryFwRev, cpqTapeLibrarySerialNumber,
                     cpqTapeLibraryState }
        DESCRIPTION
           "Tape Library Status Change

            The Storage Agent has detected a change in the status of a
            tape library.  The current tape library status is
            indicated in the cpqTapeLibraryState variable."

              --#TYPE "Tape Library Status Change (5018)"
              --#SUMMARY "Status is now %d."
              --#ARGUMENTS {9}
              --#SEVERITY CRITICAL
              --#TIMEINDEX 99
              --#VARBINDSEVERITY 2

         ::= 5018

    cpqTape5PhyDrvStatusChange TRAP-TYPE
        ENTERPRISE compaq
        VARIABLES  { sysName, cpqHoTrapFlags, cpqTapePhyDrvCntlrIndex,
                     cpqTapePhyDrvBusIndex, cpqTapePhyDrvScsiIdIndex,
                     cpqTapePhyDrvLunIndex, cpqTapePhyDrvName,
                     cpqTapePhyDrvFwRev, cpqTapePhyDrvSerialNumber,
                     cpqTapePhyDrvStatus }
        DESCRIPTION
           "Tape Drive Status Change.

            The Storage Agent has detected a change in the status of a
            tape drive.  The current physical drive status is
            indicated in the cpqTapePhyDrvStatus variable."

              --#TYPE "Tape Drive Status Change (5019)"
              --#SUMMARY "Status is now %d."
              --#ARGUMENTS {9}
              --#SEVERITY CRITICAL
              --#TIMEINDEX 99
              --#VARBINDSEVERITY 2

         ::= 5019

    cpqScsi5PhyDrvStatusChange TRAP-TYPE
        ENTERPRISE compaq
        VARIABLES  { sysName, cpqHoTrapFlags, cpqScsiPhyDrvStatus,
                     cpqScsiPhyDrvCntlrIndex, cpqScsiPhyDrvBusIndex,
                     cpqScsiPhyDrvIndex, cpqScsiPhyDrvVendor,
                     cpqScsiPhyDrvModel, cpqScsiPhyDrvFWRev,
                     cpqScsiPhyDrvSerialNum, cpqScsiPhyDrvOsName }
        DESCRIPTION
           "Physical Drive Status Change.

            The Storage Agent has detected a change in the status of a
            SCSI physical drive.  The current physical drive
            status is indicated in the cpqScsiPhyDrvStatus variable."

              --#TYPE "SCSI Physical Drive Status Change (5020)"
              --#SUMMARY "Status is now %d."
              --#ARGUMENTS {2}
              --#SEVERITY CRITICAL
              --#TIMEINDEX 99
              --#VARBINDSEVERITY 2

         ::= 5020

    cpqScsi3LogDrvStatusChange TRAP-TYPE
        ENTERPRISE compaq
        VARIABLES  { sysName, cpqHoTrapFlags, cpqScsiLogDrvStatus,
                     cpqScsiLogDrvCntlrIndex, cpqScsiLogDrvBusIndex,
                     cpqScsiLogDrvIndex, cpqScsiLogDrvOsName }
        DESCRIPTION
           "Logical Drive Status Change.

            The Storage Agent has detected a change in the status of a
            SCSI logical drive.  The current logical drive status is
            indicated in the cpqScsiLogDrvStatus variable."

              --#TYPE "SCSI Logical Drive Status Change (5021)"
              --#SUMMARY "Status is now %d."
              --#ARGUMENTS {2}
              --#SEVERITY CRITICAL
              --#TIMEINDEX 99
              --#VARBINDSEVERITY 2

         ::= 5021

    cpqSasPhyDrvStatusChange TRAP-TYPE
        ENTERPRISE compaq
        VARIABLES  { sysName, cpqHoTrapFlags, cpqSasHbaHwLocation,
                     cpqSasPhyDrvLocationString, cpqSasPhyDrvHbaIndex,
                     cpqSasPhyDrvIndex, cpqSasPhyDrvStatus,
                     cpqSasPhyDrvType, cpqSasPhyDrvModel, cpqSasPhyDrvFWRev,
                     cpqSasPhyDrvSerialNumber, cpqSasPhyDrvSasAddress }
        DESCRIPTION
           "Physical Drive Status Change.

            The Storage Agent has detected a change in the status of a
            SAS or SATA physical drive.  The current physical drive status
            is indicated in the cpqSasPhyDrvStatus variable."

              --#TYPE "SAS/SATA Physical Drive Status Change (5022)"
              --#SUMMARY "Status is now %d."
              --#ARGUMENTS {6}
              --#SEVERITY CRITICAL
              --#TIMEINDEX 99
              --#VARBINDSEVERITY 2

         ::= 5022

    cpqSasLogDrvStatusChange TRAP-TYPE
        ENTERPRISE compaq
        VARIABLES  { sysName, cpqHoTrapFlags, cpqSasHbaHwLocation,
                     cpqSasLogDrvHbaIndex, cpqSasLogDrvIndex,
                     cpqSasLogDrvStatus, cpqSasLogDrvOsName }
        DESCRIPTION
           "Logical Drive Status Change.

            The Storage Agent has detected a change in the status of a
            SAS or SATA logical drive.  The current logical drive status is
            indicated in the cpqSasLogDrvStatus variable."

              --#TYPE "SAS/SATA Logical Drive Status Change (5023)"
              --#SUMMARY "Status is now %d."
              --#ARGUMENTS {5}
              --#SEVERITY CRITICAL
              --#TIMEINDEX 99
              --#VARBINDSEVERITY 2

         ::= 5023

    cpqSas2TapeDrvStatusChange TRAP-TYPE
        ENTERPRISE compaq
        VARIABLES  { sysName, cpqHoTrapFlags, cpqSasHbaHwLocation,
                     cpqSasTapeDrvLocationString, cpqSasTapeDrvHbaIndex,
                     cpqSasTapeDrvIndex, cpqSasTapeDrvName,
                     cpqSasTapeDrvFWRev, cpqSasTapeDrvSerialNumber,
                     cpqSasTapeDrvSasAddress, cpqSasTapeDrvStatus }
        DESCRIPTION
           "SAS Tape Drive Status Change.

            The Storage Agent has detected a change in the status of a
            SAS tape drive.  The current tape drive status is
            indicated in the cpqSasTapeDrvStatus variable."

              --#TYPE "SAS Tape Drive Status Change (5025)"
              --#SUMMARY "Status is now %d."
              --#ARGUMENTS {10}
              --#SEVERITY CRITICAL
              --#TIMEINDEX 99
              --#VARBINDSEVERITY 2

         ::= 5025

END
